FME workspace NB_FGP_XML_BUILDER_PROD_08.fmw

Parameters:
- ACTIVATE_GEO = Yes
- ACTIVATE_NON_GEO = Yes
- ACTIVATE_TRANSLATION = No
- CATALOGUE_READER_SELECT = No
- FORCED_PYCSW_URL =
- IN_FFS_TESTING_FILE = $(FME_SHAREDRESOURCE_DATA)\PT_Harvester\NB\source_17nov.ffs
- IN_CSV_LOOKUPTABLES_DIR = $(FME_SHAREDRESOURCE_DATA)\PT_Harvester\LOOKUP_TABLES   # Lookup Tables Directory
- IN_GMD_XML_TEMPLATE_DIR = $(FME_SHAREDRESOURCE_DATA)\PT_Harvester\XML_TEMPLATES
- LOCAL_SOURCE_METADATA_DELTA_FINDER = Yes
- LOCAL_WRITER = Yes
- OUT_XLS_NOTIFICATION_DIR = $(FME_SHAREDRESOURCE_DATA)\PT_Harvester\NB\XLS
- OUT_XML_FAILED_DIR = $(FME_SHAREDRESOURCE_DATA)\PT_Harvester\NB\XML_FAILED
- OUT_XML_LOCAL_DIR = $(FME_SHAREDRESOURCE_DATA)\PT_Harvester\NB\XML_LOCAL
- OUT_XML_PASSED_DIR = $(FME_SHAREDRESOURCE_DATA)\PT_Harvester\NB\XML_PASSED
- P-T_ABBR = NB
- PYCSW_OVERWRITE = YES
- LOG_FILE = $(FME_SHAREDRESOURCE_DATA)\PT_Harvester\NB\LOG\NB.log
- IN_TBS_JSON_TEMPLATE_DIR = $(FME_SHAREDRESOURCE_DATA)\PT_Harvester\JSON_TEMPLATES
- OUT_JSON_LOCAL_DIR = $(FME_SHAREDRESOURCE_DATA)\PT_Harvester\NB\JSON_LOCAL
- URL_VALIDATION = No
- FME_SHAREDRESOURCE_DATA = C:\DavidH\NRCan\Data   # FME Server Resource Data

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(OUT_XLS_NOTIFICATION_DIR)
- TEXTLINE_4: TEXTLINE to $(OUT_JSON_LOCAL_DIR)

Note: NB_GeoDataTypes
LOOKUP_TABLES_READER_2 [off]
    CSV_ENCODING = utf-8
    CSV_PATH = $(IN_CSV_LOOKUPTABLES_DIR)
    FEATURE_TYPE = NB_GeoDataTypes
    PT = NB
TestFilter_2
    DEFAULT_VALUE = <UNFILTERED>
    TEST_LIST = "BOOL_OP,OR,COMPOSITE_TEST,""""""1"""""",TEST_CLAUSE,TEST @LowerCase($(ACTIVATE_NON_GEO)) = yes",NON-GEO_ACTIVATE
    NON-GEO_ACTIVATE -> AttributeRemover_5
TestFilter
    DEFAULT_VALUE = <UNFILTERED>
    TEST_LIST = "BOOL_OP,OR,COMPOSITE_TEST,""""""1"""""",TEST_CLAUSE,TEST @LowerCase($(ACTIVATE_GEO)) = yes",GEO_ACTIVATE
    GEO_ACTIVATE -> Socrata_BoundingBoxExtractor [feature_input]
Note: Extraction des coordonnées du BBOX
Socrata_BoundingBoxExtractor: SOCRATA_BOUNDING_BOX_EXTRACTOR
    DOMAIN = https://gnb.socrata.com
    SocrataAppToken = FL3Cxsebg0Vf6JQ0CnbMujHkQ
    feature_output -> METADATA_VALUE_MAPPER_5 [DATA_INPUT]
Note: PyCSW_config
LOOKUP_TABLES_READER_17
    CSV_ENCODING = utf-8
    CSV_PATH = $(IN_CSV_LOOKUPTABLES_DIR)
    FEATURE_TYPE = PyCSW_config
    PT = NB
    -> PYCSW_URL_MAPPER [PYCSW_CONFIG]
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer
VariableRetriever_12
    SCOPE = Global
    VALUE_ATTR = _timestamp
    VARNAME = _timestamp
    -> invalid_metadata (writer XLSXW_1)
invalid_metadata (writer XLSXW_1)
    attributes: id auto(20)

Bookmark: lecture des données du portail socrata, filtrage de licence et fusion des métadonnées de vue externe
Creator_3
    GEOMTYPE = Geometry Object
    NUM = 1
    CREATED -> DateTimeStamper
DateTimeStamper
    DATETIME_ATTR = _toto
    STAMP_TYPE = date
    TIMEZONE = local
    -> VariableSetter
VariableSetter
    SCOPE = Global
    VALUE = @Value(_toto)
    VARNAME = _timestamp
    -> Tester_6
Tester_6
    BOOL_OP = OR
    COMPOSITE_TEST = 1
    TEST_CLAUSE = TEST $(CATALOGUE_READER_SELECT) = Yes
    TEST_MODE = TEST
    PASSED -> Socrata_Reader
    FAILED -> FeatureReader_2 [INITIATOR]
Note: new CT
Socrata_Reader: SOCRATA_READER
    DOMAIN = https://gnb.socrata.com
    -> AttributeExposer_3
FeatureReader_2
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> AttributeExposer_3
AttributeExposer_3
    ATTR_LIST = licenseId,id,title
    -> LICENSE_FILTER
LOOKUP_TABLES_READER_19
    CSV_ENCODING = utf-8
    CSV_PATH = $(IN_CSV_LOOKUPTABLES_DIR)
    FEATURE_TYPE = License_NB
    PT = NB
    -> LICENSE_FILTER [LOOKUP_TABLE_INPUT]
LICENSE_FILTER
    LICENSE_ATT = @Value(licenseId)
    LICENSE_FILTER_PASSED -> SOCRATA_METADATA_MERGER
    UNKNOWN_LICENSE -> VariableRetriever_8
SOCRATA_METADATA_MERGER
    DOMAIN = https://gnb.socrata.com
    -> DEFAULT_ATTRIBUTE_MAPPER
    UnmergedAdvancedView -> VariableRetriever_4
VariableRetriever_4
    SCOPE = Global
    VALUE_ATTR = _timestamp
    VARNAME = _timestamp
    -> unmergedAdvancedView (writer XLSXW_1)
unmergedAdvancedView (writer XLSXW_1)
    attributes: url string(200), format string(200), _seriesID string(200), _timestamp string(200)
VariableRetriever_8
    SCOPE = Global
    VALUE_ATTR = _timestamp
    VARNAME = _timestamp
    -> unknown_licence (writer XLSXW_1)
unknown_licence (writer XLSXW_1)
    attributes: license_id string(200), id string(200), title string(200)

Bookmark: Transformation vers modèle de travail et ajout des valeurs par défeauts
Note: Default_NB
LOOKUP_TABLES_READER_7
    CSV_ENCODING = utf-8
    CSV_PATH = $(IN_CSV_LOOKUPTABLES_DIR)
    FEATURE_TYPE = Default_NB
    PT = NB
    -> DEFAULT_ATTRIBUTE_MAPPER [LOOKUP_TABLE_INPUT]
Note: Creating default values for NB
DEFAULT_ATTRIBUTE_MAPPER
    -> NB_ATTRIBUTE_MANAGER
Note: Attributes adjustement
NB_ATTRIBUTE_MANAGER
    -> SECTOR_MAPPER
    error_datetime_output -> VariableRetriever_7
VariableRetriever_7
    SCOPE = Global
    VALUE_ATTR = _timestamp
    VARNAME = _timestamp
    -> Error_Datetime (writer XLSXW_1)
Error_Datetime (writer XLSXW_1)
    attributes: nom_organisation_fr string(200), nom_organisation_en string(200), sector string(200), sector_fr string(200), org_name_temp string(200), spatialref__.projection_name string(200), spatialref__.projection_system string(200), spatialref__.projection_system_version string(200), id string(200), UNIQUE_ATT string(200), resource.id string(200), resource.type string(200), assetType string(200), default_domain_tag string(200), tags__ string(200), metadata.custom_fields.Department / Ministère.Department / Ministère string(200), attribution string(200), default_sector_en string(200), default_sector_fr string(200), default_projection_name string(200), default_projection_system_version string(200), default_reference_system string(200), category string(200), default_category string(200), p-t_entity string(200), p-t_entity_fr string(200), _list__ string(200), _element_count number(20), publicationDate string(200), createdAt string(200),
      viewLastModified string(200), fme_rejection_code string(20), _timestamp string(200)

Bookmark: Sector filtering/mapping (Drop federal dataset)
Note: Sector_NB
LOOKUP_TABLES_READER_27
    CSV_ENCODING = utf-8
    CSV_PATH = $(IN_CSV_LOOKUPTABLES_DIR)
    FEATURE_TYPE = Sector_NB
    PT = NB
    -> SECTOR_MAPPER [LOOKUP_TABLE_INPUT]
SECTOR_MAPPER
    -> NB_FrenchEnglishAttributeSeparator [Feature_Input]
    UNMAPPED_OUTPUT -> VariableRetriever_16
VariableRetriever_16
    SCOPE = Global
    VALUE_ATTR = _timestamp
    VARNAME = _timestamp
    -> SECTOR_NB_missing_sector (writer XLSXW_1)
SECTOR_NB_missing_sector (writer XLSXW_1)
    attributes: Socrata_id string(20), link string(20), description string(20), datetime string(20)

Bookmark: Gestion des champs bilingues pour distinguer le contenu FR versus EN
Note: NB_SlashCountSeparatorForDesc
LOOKUP_TABLES_READER_18
    CSV_ENCODING = utf-8
    CSV_PATH = $(IN_CSV_LOOKUPTABLES_DIR)
    FEATURE_TYPE = NB_SlashCountSeparatorForDesc
    PT = NB
    -> NB_FrenchEnglishAttributeSeparator [SlashLocationSheet]
Note: Description to Notes
NB_FrenchEnglishAttributeSeparator
    ATTRIBUTE_TO_SPLIT = description
    Feature_Output -> AttributeRenamer
    MULTIPLE_UNCAUGHT_SLASH_IN_ATT -> VariableRetriever_6
AttributeRenamer
    ATTR_TABLE:
      RENAME_SET_DEFAULT splited_attr_en > notes
      RENAME_SET_DEFAULT splited_attr_fr > notes_fr
    -> NB_FrenchEnglishAttributeSeparator_2 [Feature_Input]
VariableRetriever_6
    SCOPE = Global
    VALUE_ATTR = _timestamp
    VARNAME = _timestamp
    -> NB_MULTIPLE_SLASH_IN_DESCRIPTION (writer XLSXW_1)
NB_MULTIPLE_SLASH_IN_DESCRIPTION (writer XLSXW_1)
    attributes: Socrata_id string(20), link string(20), description string(20), datetime string(20)
Note: only changed attribute names
Note: NB_SlashCountSeparatorForName
LOOKUP_TABLES_READER_22
    CSV_ENCODING = utf-8
    CSV_PATH = $(IN_CSV_LOOKUPTABLES_DIR)
    FEATURE_TYPE = NB_SlashCountSeparatorForName
    PT = NB
    -> NB_FrenchEnglishAttributeSeparator_2 [SlashLocationSheet]
Note: Name to Title
NB_FrenchEnglishAttributeSeparator_2
    ATTRIBUTE_TO_SPLIT = name
    Feature_Output -> AttributeRenamer_2
    MULTIPLE_UNCAUGHT_SLASH_IN_ATT -> VariableRetriever_15
AttributeRenamer_2
    ATTR_TABLE:
      RENAME_SET_DEFAULT splited_attr_en > title
      RENAME_SET_DEFAULT splited_attr_fr > title_fr
    -> NB_TAGS_MANAGER [feature_input]
VariableRetriever_15
    SCOPE = Global
    VALUE_ATTR = _timestamp
    VARNAME = _timestamp
    -> NB_MULTIPLE_SLASH_IN_NAME (writer XLSXW_1)
NB_MULTIPLE_SLASH_IN_NAME (writer XLSXW_1)
    attributes: Socrata_id string(20), link string(20), description string(20), datetime string(20)
Note: NB_Keywords
LOOKUP_TABLES_READER_3
    CSV_ENCODING = utf-8
    CSV_PATH = $(IN_CSV_LOOKUPTABLES_DIR)
    FEATURE_TYPE = NB_Keywords
    PT = NB
    -> NB_TAGS_MANAGER [TAG_LOOKUP_TABLE]
Note: Tags management
NB_TAGS_MANAGER
    -> GEOPORTAL_WEBLINK_ADDER
    TAG_NOT_FOUND -> VariableRetriever_10
VariableRetriever_10
    SCOPE = Global
    VALUE_ATTR = _timestamp
    VARNAME = _timestamp
    -> TAG_NOT_FOUND (writer XLSXW_1)
TAG_NOT_FOUND (writer XLSXW_1)
    attributes: Socrata_id string(20), link string(20), description string(20), datetime string(20)

Bookmark: Création de la liste des ressources pour les jeux de données
Note: NB_LINKBUILDER_GEO
LOOKUP_TABLES_READER_8
    CSV_ENCODING = utf-8
    CSV_PATH = $(IN_CSV_LOOKUPTABLES_DIR)
    FEATURE_TYPE = NB_LINKBUILDER_GEO
    PT = NB
    -> SOCRATA_INSIDE_DB_EXTRACTOR [linkbuilder_geo]
Note: NB_LINKBUILDER_NONGEO
LOOKUP_TABLES_READER_9
    CSV_ENCODING = utf-8
    CSV_PATH = $(IN_CSV_LOOKUPTABLES_DIR)
    FEATURE_TYPE = NB_LINKBUILDER_NONGEO
    PT = NB
    -> SOCRATA_INSIDE_DB_EXTRACTOR [LinkBuilderNonGeo]
Note: NB_FIELDTYPE_NG
LOOKUP_TABLES_READER
    CSV_ENCODING = utf-8
    CSV_PATH = $(IN_CSV_LOOKUPTABLES_DIR)
    FEATURE_TYPE = NB_FieldType_NG
    PT = NB
    -> SOCRATA_INSIDE_DB_EXTRACTOR [Field_datatype]
Note: NB_GEODATAFIELDNAME
LOOKUP_TABLES_READER_28
    CSV_ENCODING = utf-8
    CSV_PATH = $(IN_CSV_LOOKUPTABLES_DIR)
    FEATURE_TYPE = NB_GeoDataFieldName
    PT = NB
    -> SOCRATA_INSIDE_DB_EXTRACTOR [Field_name]
Note: GeoportalWeblink_NB
LOOKUP_TABLES_READER_4
    CSV_ENCODING = utf-8
    CSV_PATH = $(IN_CSV_LOOKUPTABLES_DIR)
    FEATURE_TYPE = GeoportalWeblink_NB
    PT = NB
    -> GEOPORTAL_WEBLINK_ADDER [LOOKUP_TABLE_INPUT]
Note: Cération de la liste / resources
GEOPORTAL_WEBLINK_ADDER
    URL_VALIDATION = $(URL_VALIDATION)
    WEBLINK_WILDCARD = @Value(resource.id)
    -> SOCRATA_ADDITIONAL_ACCESS_POINTS_RESOURCES_EXTRACTOR
Note: Extraction des ressources dans additional access points / Crée la liste / additional_access_points_resources
SOCRATA_ADDITIONAL_ACCESS_POINTS_RESOURCES_EXTRACTOR
    -> SOCRATA_ATTACHEMENTS_EXTRACTOR
Note: Extraction des resources dans les attachements / Crée la liste attachement_resources
SOCRATA_ATTACHEMENTS_EXTRACTOR
    SBN_URL_ROOT = https://gnb.socrata.com
    -> SOCRATA_ADVANCED_VIEW_EXTRACTOR
Note: Extraction des ressources dans les vues avanacées / Crée la liste advancedview_resources
SOCRATA_ADVANCED_VIEW_EXTRACTOR
    -> SOCRATA_INSIDE_DB_EXTRACTOR
SOCRATA_INSIDE_DB_EXTRACTOR
    DOMAIN = https://gnb.socrata.com
    URL_VALIDATION = no
    -> AttributeExposer_5
Note: Extraction du format
EMPTY_FORMAT_MAPPER
    DATA_OUTPUT -> AttributeExposer_7

Bookmark: Fusion des listes de resources dans une seule liste
AttributeExposer_5
    ATTR_LIST = resources{}.url
    -> ListCopier
ListCopier
    DEST_LIST = resources_copy
    SRC_LIST = resources{}
    -> AttributeRemover
AttributeRemover
    LIST_ATTRS = resources{}
    -> PythonCaller_3
PythonCaller_3
    NEW_ATTRIBUTES = resources{}.name resources{}.url resources{}.format resources{}.name_fr
    PYTHONSOURCE:
      import fme
      import fmeobjects
      logger = fmeobjects.FMELogFile()
      # Template Function interface:
      # When using this function, make sure its name is set as the value of
      # the 'Class or Function to Process Features' transformer parameter
      def processFeature(feature):
          list_list_name=[r'resources_copy',r'socrata_db_resources',r'advancedview_resources',r'additional_access_points_resources',r'attachement_resources']
          list_attr_name=[r'format',r'url',r'name',r'name_fr',r'spatial_type']

          i=0





          for list_name in list_list_name:

              #Extracting number of resources
              list_url=feature.getAttribute('%s{}.url'%(list_name))
              if list_url:
                  #Looping in resources
                  for j in range(len(list_url)):
                      #Looping in attributes
                      for attr_name in list_attr_name:
                          feature.setAttribute('resources{%i}.%s'%(i,attr_name),feature.getAttribute('%s{%i}.%s'%(list_name,j,attr_name)))

                      #Changing index feature where new features
                      i=i+1
    PYTHONSYMBOL = processFeature
    -> ListDuplicateRemover_2
Note: Removing dupplicates on URL
ListDuplicateRemover_2
    SRC_LIST = resources{}.url
    -> EMPTY_FORMAT_MAPPER [DATA_INPUT]

Bookmark: Création d'une liste avec les catégories pour pouvoir fouiller dedans avec le Geospatial data validator
AttributeExposer_7
    ATTR_LIST = category
    -> AttributeCreator_6
AttributeCreator_6
    ATTR_TABLE = SET_TO category{0}.value = @LowerCase(@Value(category))
    -> GEOSPATIAL_DATA_VALIDATOR

Bookmark: Filtrage geo / non-geo
Note: NB_TOPICS_DATASET
LOOKUP_TABLES_READER_21
    CSV_ENCODING = utf-8
    CSV_PATH = $(IN_CSV_LOOKUPTABLES_DIR)
    FEATURE_TYPE = GeospatialValidation
    PT = NB
    -> GEOSPATIAL_DATA_VALIDATOR [LOOKUP_TABLE_INPUT]
Note: Avec recherche supplémentaire dans les catégories
GEOSPATIAL_DATA_VALIDATOR
    KEYWORD_SEARCH = lidar|geographic
    LIST_SEARCH_ATTRIBUTE = category{}.value
    GEOSPATIAL -> AttributeExposer_8
    NON-GEOSPATIAL -> AttributeExposer_9
    UNKNOWN_FORMAT -> VariableRetriever_13
AttributeExposer_8
    ATTR_LIST = category{}
    -> AttributeRemover_3
Note: Suppression de la liste temporaire
AttributeRemover_3
    LIST_ATTRS = category{}
    -> AttributeExposer_4
VariableRetriever_13
    SCOPE = Global
    VALUE_ATTR = _timestamp
    VARNAME = _timestamp
    -> unknown_format (writer XLSXW_1)
unknown_format (writer XLSXW_1)
    attributes: format auto(20)
AttributeExposer_9
    ATTR_LIST = category{}
    -> AttributeRemover_4
Note: Suppression de la liste temporaire
AttributeRemover_4
    LIST_ATTRS = category{}
    -> MANUAL_GEOSPATIAL_SETTER [DATA_INPUT]
Note: UnmappedGeoData_NB
LOOKUP_TABLES_READER_6
    CSV_ENCODING = utf-8
    CSV_PATH = $(IN_CSV_LOOKUPTABLES_DIR)
    FEATURE_TYPE = UnmappedGeoData_NB
    PT = NB
    -> MANUAL_GEOSPATIAL_SETTER [LOOKUP_TABLE_INPUT]
MANUAL_GEOSPATIAL_SETTER
    GEOSPATIAL -> AttributeCreator_13
    NON-GEOSPATIAL -> AttributeCreator_14
    UNMAPPED_DATA -> VariableRetriever_14
Note: _typedataset = NONGEO
AttributeCreator_14
    ATTR_TABLE = SET_TO _typedataset = NONGEO
    -> TestFilter_2
VariableRetriever_14
    SCOPE = Global
    VALUE_ATTR = _timestamp
    VARNAME = _timestamp
    -> unknow_geo_non_geo (writer XLSXW_1)
unknow_geo_non_geo (writer XLSXW_1)
    attributes: id string(200), notes string(200), title string(200), url string(200), _timestamp string(200)
Note: _typedataset = GEO
AttributeCreator_13
    ATTR_TABLE = SET_TO _typedataset = GEO
    -> TestFilter

Bookmark: Adding spatial type manually
AttributeExposer_4
    ATTR_LIST = id,resource.id
    -> AttributeCreator_3
AttributeCreator_3
    ATTR_TABLE = SET_TO id_temp = @Value(id)
    -> AttributeCreator_4
AttributeCreator_4
    ATTR_TABLE = SET_TO id = @Value(resource.id)
    -> SPATIAL_TYPE_MAPPER [DATA_INPUT]
Note: SpatialType_NB
LOOKUP_TABLES_READER_10
    CSV_ENCODING = utf-8
    CSV_PATH = $(IN_CSV_LOOKUPTABLES_DIR)
    FEATURE_TYPE = SpatialType_NB
    PT = NB
    -> SPATIAL_TYPE_MAPPER [LOOKUP_TABLE_INPUT]
SPATIAL_TYPE_MAPPER
    DATA_OUTPUT_PASSED -> AttributeCreator_5
AttributeCreator_5
    ATTR_TABLE = SET_TO id = @Value(id_temp)
    -> AttributeRemover_2
AttributeRemover_2
    REMOVE_ATTRS = id_temp
    -> AttributeCreator_13

Bookmark: Metadata Value Mapping - NONGEO
AttributeRemover_5
    LIST_ATTRS = approvals{} columns{} flags{} owner.flags{} socrata_db_resources{} tableAuthor.flags{} query.filterCondition.children{} query.filterCondition.children{}.children{} query.filterCondition.children{}.children{}.children{} query.filterCondition.children{}.children{}.children{}.columnFieldName query.filterCondition.children{}.children{}.children{}.columnId query.filterCondition.children{}.children{}.children{}.type query.filterCondition.children{}.children{}.children{}.value query.filterCondition.children{}.children{}.metadata.freeform query.filterCondition.children{}.children{}.type query.filterCondition.children{}.children{}.value query.filterCondition.children{}.metadata.operator query.filterCondition.children{}.metadata.tableColumnId.18389368 query.filterCondition.children{}.type query.filterCondition.children{}.value
    -> AttributeExposer_11
AttributeExposer_11
    ATTR_LIST = category,tbs_default_category,tags_eng{}.display_name,default_category
    -> AttributeTrimmer
AttributeTrimmer
    SRC_ATTRS = category
    TRIM_TO_NONE = Yes
    TRIM_TYPE = Both
    -> Tester_2
Tester_2
    BOOL_OP = OR
    COMPOSITE_TEST = 1
    TEST_CLAUSE = TEST @Value(category) != @Value(default_category)
    TEST_MODE = TEST
    PASSED -> AttributeCreator_11
    FAILED -> AttributeCreator_10
AttributeCreator_11
    ATTR_TABLE = SET_TO tbs_category = @Value(category)
    -> AttributeCreator_9
AttributeCreator_10
    ATTR_TABLE = SET_TO tbs_category = @Value(tbs_default_category)
    -> AttributeCreator_9
ATTRIBUTE_UNEXPOSER
    -> METADATA_VALUE_MAPPER_8 [DATA_INPUT]
Note: UpdateFrequency_TBS
LOOKUP_TABLES_READER_23
    CSV_ENCODING = utf-8
    CSV_PATH = $(IN_CSV_LOOKUPTABLES_DIR)
    FEATURE_TYPE = UpdateFrequency_TBS
    PT = $(P-T_ABBR)
    -> METADATA_VALUE_MAPPER_8 [LOOKUP_TABLE_INPUT]
METADATA_VALUE_MAPPER_8
    ATT_TO_MAP = update_frequency
    CODE_REFRESH = NO
    ENGLISH_REFRESH = YES
    ERROR_NOT_MAPPED = YES
    FRENCH_REFRESH = NO
    -> METADATA_FORMAT_MAPPER_2 [DATA_INPUT]
Note: Format_TBS
LOOKUP_TABLES_READER_25
    CSV_ENCODING = utf-8
    CSV_PATH = $(IN_CSV_LOOKUPTABLES_DIR)
    FEATURE_TYPE = Format_TBS
    PT = $(P-T_ABBR)
    -> METADATA_FORMAT_MAPPER_2 [LOOKUP_TABLE_INPUT]
METADATA_FORMAT_MAPPER_2
    ATT_TO_MAP = resources{}.format
    ERROR_NOT_MAPPED = YES
    REAL_VALUE_REFRESH = YES
    RES_TYPE_EN_REFRESH = YES
    RES_TYPE_FR_REFRESH = YES
    -> METADATA_VALUE_MAPPER_ERROR_MANAGER_2
METADATA_VALUE_MAPPER_ERROR_MANAGER_2
    ERROR_OUTPUT -> VariableRetriever
    DATA_OUTPUT -> AttributeExposer_16
VariableRetriever
    SCOPE = Global
    VALUE_ATTR = _timestamp
    VARNAME = _timestamp
    -> ATTRIBUTE_MAPPING_ERRORS00_NONGEO (writer XLSXW_1)
ATTRIBUTE_MAPPING_ERRORS00_NONGEO (writer XLSXW_1)
    attributes: error string(200), id string(200), _element_index string(200), _timestamp string(200)

Bookmark: Generating Tbs Topic based on category
AttributeCreator_9
    ATTR_TABLE = SET_TO TBS_Topic_temp{0}.display_name = @Value(tbs_category)
    -> METADATA_VALUE_MAPPER_ONE2MANY_2 [DATA_INPUT]
Note: Topic_TBS
LOOKUP_TABLES_READER_24
    CSV_ENCODING = utf-8
    CSV_PATH = $(IN_CSV_LOOKUPTABLES_DIR)
    FEATURE_TYPE = Topic_TBS
    PT = $(P-T_ABBR)
    -> METADATA_VALUE_MAPPER_ONE2MANY_2 [LOOKUP_TABLE_INPUT]
Note: Mappging to TBS values
METADATA_VALUE_MAPPER_ONE2MANY_2
    ATT_TO_MAP = TBS_Topic_temp{}.display_name
    CODE_REFRESH = NO
    ENGLISH_REFRESH = YES
    ERROR_NOT_MAPPED = YES
    FRENCH_REFRESH = NO
    -> AttributeExposer_15
AttributeExposer_15
    ATTR_LIST = TBS_Topic_temp{}.display_name
    -> ListDuplicateRemover_4
ListDuplicateRemover_4
    SRC_LIST = TBS_Topic_temp{}.display_name
    -> PythonCaller_4
Note: Dropping topic to ignore
PythonCaller_4
    NEW_ATTRIBUTES = TBS_Topic{}.value
    PYTHONSOURCE:
      import fme
      import fmeobjects
      # Template Function interface:
      # When using this function, make sure its name is set as the value of
      # the 'Class or Function to Process Features' transformer parameter
      def processFeature(feature):
          i=0
          if feature.getAttribute('TBS_Topic_temp{}.display_name'):
              for elem in feature.getAttribute('TBS_Topic_temp{}.display_name'):
                  if elem != 'ignore':
                      feature.setAttribute('TBS_Topic{%d}.value'%(i),elem)
                      i=i+1
    PYTHONSYMBOL = processFeature
    -> AttributeRemover_7
AttributeRemover_7
    LIST_ATTRS = TBS_Topic_temp{}
    -> AttributeCreator_12

Bookmark: Metadata Value Mapping
Note: Topic
LOOKUP_TABLES_READER_5
    CSV_ENCODING = utf-8
    CSV_PATH = $(IN_CSV_LOOKUPTABLES_DIR)
    FEATURE_TYPE = Topic
    PT = NB
    -> METADATA_VALUE_MAPPER_5 [LOOKUP_TABLE_INPUT]
Note: Category contains topic
METADATA_VALUE_MAPPER_5
    ATT_TO_MAP = category
    CODE_REFRESH = NO
    ENGLISH_REFRESH = YES
    ERROR_NOT_MAPPED = YES
    FRENCH_REFRESH = NO
    -> METADATA_VALUE_MAPPER [DATA_INPUT]
Note: Role
LOOKUP_TABLES_READER_12
    CSV_ENCODING = utf-8
    CSV_PATH = $(IN_CSV_LOOKUPTABLES_DIR)
    FEATURE_TYPE = Role
    PT = NB
    -> METADATA_VALUE_MAPPER [LOOKUP_TABLE_INPUT]
METADATA_VALUE_MAPPER
    ATT_TO_MAP = contacts{}.role
    CODE_REFRESH = YES
    ENGLISH_REFRESH = YES
    ERROR_NOT_MAPPED = YES
    FRENCH_REFRESH = YES
    -> METADATA_VALUE_MAPPER_2 [DATA_INPUT]
Note: Update
LOOKUP_TABLES_READER_13
    CSV_ENCODING = utf-8
    CSV_PATH = $(IN_CSV_LOOKUPTABLES_DIR)
    FEATURE_TYPE = Update
    PT = NB
    -> METADATA_VALUE_MAPPER_2 [LOOKUP_TABLE_INPUT]
METADATA_VALUE_MAPPER_2
    ATT_TO_MAP = update_frequency
    CODE_REFRESH = YES
    ENGLISH_REFRESH = YES
    ERROR_NOT_MAPPED = YES
    FRENCH_REFRESH = YES
    -> METADATA_VALUE_MAPPER_3 [DATA_INPUT]
Note: Progress
LOOKUP_TABLES_READER_14
    CSV_ENCODING = utf-8
    CSV_PATH = $(IN_CSV_LOOKUPTABLES_DIR)
    FEATURE_TYPE = Progress
    PT = NB
    -> METADATA_VALUE_MAPPER_3 [LOOKUP_TABLE_INPUT]
METADATA_VALUE_MAPPER_3
    ATT_TO_MAP = progress_code
    CODE_REFRESH = YES
    ENGLISH_REFRESH = YES
    ERROR_NOT_MAPPED = YES
    FRENCH_REFRESH = YES
    -> METADATA_VALUE_MAPPER_4 [DATA_INPUT]
Note: SpatialRepresentation
LOOKUP_TABLES_READER_15
    CSV_ENCODING = utf-8
    CSV_PATH = $(IN_CSV_LOOKUPTABLES_DIR)
    FEATURE_TYPE = SpatialRepresentation
    PT = NB
    -> METADATA_VALUE_MAPPER_4 [LOOKUP_TABLE_INPUT]
METADATA_VALUE_MAPPER_4
    ATT_TO_MAP = spatial_representation_type
    CODE_REFRESH = YES
    ENGLISH_REFRESH = YES
    ERROR_NOT_MAPPED = YES
    FRENCH_REFRESH = YES
    -> METADATA_FORMAT_MAPPER [DATA_INPUT]
Note: Format
LOOKUP_TABLES_READER_16
    CSV_ENCODING = utf-8
    CSV_PATH = $(IN_CSV_LOOKUPTABLES_DIR)
    FEATURE_TYPE = Format
    PT = NB
    -> METADATA_FORMAT_MAPPER [LOOKUP_TABLE_INPUT]
METADATA_FORMAT_MAPPER
    ATT_TO_MAP = resources{}.format
    ERROR_NOT_MAPPED = YES
    REAL_VALUE_REFRESH = YES
    RES_TYPE_EN_REFRESH = YES
    RES_TYPE_FR_REFRESH = YES
    -> METADATA_VALUE_MAPPER_ERROR_MANAGER
METADATA_VALUE_MAPPER_ERROR_MANAGER
    ERROR_OUTPUT -> VariableRetriever_11
    DATA_OUTPUT -> AttributeRemover_6
VariableRetriever_11
    SCOPE = Global
    VALUE_ATTR = _timestamp
    VARNAME = _timestamp
    -> ATTRIBUTE_MAPPING_ERRORS (writer XLSXW_1)
ATTRIBUTE_MAPPING_ERRORS (writer XLSXW_1)
    attributes: error string(200), id string(200), _element_index string(200), _timestamp string(200)
Note: Removing error list
AttributeRemover_6
    LIST_ATTRS = mapping_errors{}
    -> RESOURCE_NAME_UNDERSCORE_REMOVER

Bookmark: Generating TBS_SUBJECT list based on category
AttributeCreator_12
    ATTR_TABLE = SET_TO TBS_Subject_temp{0}.display_name = @Value(tbs_category)
    -> METADATA_VALUE_MAPPER_ONE2MANY [DATA_INPUT]
Note: Subject_TBS
LOOKUP_TABLES_READER_26
    CSV_ENCODING = utf-8
    CSV_PATH = $(IN_CSV_LOOKUPTABLES_DIR)
    FEATURE_TYPE = Subject_TBS
    PT = $(P-T_ABBR)
    -> METADATA_VALUE_MAPPER_ONE2MANY [LOOKUP_TABLE_INPUT]
Note: Mappging to TBS values
METADATA_VALUE_MAPPER_ONE2MANY
    ATT_TO_MAP = TBS_Subject_temp{}.display_name
    CODE_REFRESH = NO
    ENGLISH_REFRESH = YES
    ERROR_NOT_MAPPED = YES
    FRENCH_REFRESH = NO
    -> AttributeExposer_10
AttributeExposer_10
    ATTR_LIST = TBS_Subject_temp{}.display_name
    -> ListDuplicateRemover_5
Note: Removeing duplicates on subject value
ListDuplicateRemover_5
    SRC_LIST = TBS_Subject_temp{}.display_name
    -> PythonCaller_5
Note: Dropping subject to ignore
PythonCaller_5
    NEW_ATTRIBUTES = TBS_Subject{}.value
    PYTHONSOURCE:
      import fme
      import fmeobjects
      # Template Function interface:
      # When using this function, make sure its name is set as the value of
      # the 'Class or Function to Process Features' transformer parameter
      def processFeature(feature):
          i=0
          if feature.getAttribute('TBS_Subject_temp{}.display_name'):
              for elem in feature.getAttribute('TBS_Subject_temp{}.display_name'):
                  if elem != 'ignore':
                      feature.setAttribute('TBS_Subject{%d}.value'%(i),elem)
                      i=i+1
    PYTHONSYMBOL = processFeature
    -> AttributeRemover_8
AttributeRemover_8
    LIST_ATTRS = TBS_Subject_temp{}
    REMOVE_ATTRS = tbs_category
    -> ATTRIBUTE_UNEXPOSER

Bookmark: Remove all underscores from resources{}.name attributes
RESOURCE_NAME_UNDERSCORE_REMOVER
    DATA_OUTPUT -> REMOVE_BROKEN_URL_WMS_ESRI_REST

Bookmark: Drop Broken Web Services
REMOVE_BROKEN_URL_WMS_ESRI_REST
    -> WMS_REST_LANGUAGE_FORMATTER
    FAULTY_URL_OUTPUT -> VariableRetriever_2
VariableRetriever_2
    SCOPE = Global
    VALUE_ATTR = _timestamp
    VARNAME = _timestamp
    -> MAP_SERVICE_URL_ERRORMAP (writer XLSXW_1)
MAP_SERVICE_URL_ERRORMAP (writer XLSXW_1)
    attributes: id string(200), url string(200), format string(200), _url_failure_message string(200), _timestamp string(200)

Bookmark: HNAP RULES
WMS_REST_LANGUAGE_FORMATTER
    -> DUPLICATE_SERVICE_REMOVER
DUPLICATE_SERVICE_REMOVER
    -> GMD_SECTION_DATA_EXTRACTION
GMD_SECTION_DATA_EXTRACTION
    -> PYCSW_URL_MAPPER

Bookmark: Default value for resources language
AttributeExposer_16
    ATTR_LIST = resources{},default_res_language
    -> ListElementCounter
ListElementCounter
    CNT_ATTR = _element_count
    LIST_NAME = resources{}
    -> PythonCaller
PythonCaller
    PYTHONSOURCE:
      import fme
      import fmeobjects
      # Template Class Interface:
      # When using this class, make sure its name is set as the value of
      # the 'Class or Function to Process Features' transformer parameter
      def FeatureProcessor(feature):
          split_list = str(feature.getAttribute('default_resource_language')).split(";")
          resource_language = '['

          for i in range(len(split_list)):
              if i == len(split_list) - 1:
                  resource_language = resource_language + '"' + split_list[i] + '"'
              else:
                  resource_language = resource_language + '"' + split_list[i] + '",'

          resource_language = resource_language + ']'

          for i in range(int(feature.getAttribute('_element_count'))):
              feature.setAttribute('resources{%d}.language_list'%(i),str(resource_language))
    PYTHONSYMBOL = FeatureProcessor
    -> AttributeRemover_10
AttributeRemover_10
    REMOVE_ATTRS = _element_count
    -> METADATA_DELTA_FINDER_2

Bookmark: Delta Finder -NONGEO
Note: Searches existing PyCSW for new, updated or obsolete data
METADATA_DELTA_FINDER_2
    ABSTRACT_ATT_NEW = notes
    ABSTRACT_ATT_REF = notes_translated.en
    DATESTAMP_ATT_NEW = record_last_modified
    DATESTAMP_ATT_REF = federated_date_modified
    ID_ATT_NEW = id
    ID_ATT_REF = id
    LOCAL_SOURCE = Yes
    LOCAL_SOURCE_DIR = $(OUT_JSON_LOCAL_DIR)
    LOCAL_SOURCE_FORMAT = JSON
    RES_FORMAT_ATT_NEW = resources{}.format
    RES_FORMAT_ATT_REF = resources{}.format
    RES_NAME_ATT_NEW = resources{}.name
    RES_NAME_ATT_REF = resources{}.name_translated.en
    RES_URL_ATT_NEW = resources{}.url
    RES_URL_ATT_REF = resources{}.url
    TITLE_ATT_NEW = title
    TITLE_ATT_REF = title_translated.en
    -> AttributeExposer

Bookmark: New Bookmark
PYCSW_URL_MAPPER
    FORCED_PYCSW_URL = $(FORCED_PYCSW_URL)
    PROVIDER = $(P-T_ABBR)
    -> AttributeExposer_2
AttributeExposer_2
    ATTR_LIST = search_criteria_pycsw,csw_url
    -> METADATA_DELTA_FINDER
Note: Searches existing PyCSW for new, updated or obsolete data
METADATA_DELTA_FINDER
    ABSTRACT_ATT_NEW = notes
    ABSTRACT_ATT_REF = MD_Metadata.identificationInfo.MD_DataIdentification.abstract.CharacterString
    CSW_FILTER = @Value(search_criteria_pycsw)
    CUSTOM_CSW_CKAN_URL = @Value(csw_url)
    DATESTAMP_ATT_NEW = record_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    -> AttributeExposer
Note: Exposes PyCSW_Transaction attribute
AttributeExposer
    ATTR_LIST = PyCSW_Transaction,id
    -> AttributeFilter
Note: Filters items by PyCSW transaction type
AttributeFilter
    ATTR_NAME = PyCSW_Transaction
    ATTR_VALUES = <Empty>,<Missing>,<Null>,<Unfiltered>,No change,Update,Insert,Delete
    <EMPTY> -> Terminator
    <MISSING> -> Terminator
    <NULL> -> Terminator
    <UNFILTERED> -> Terminator
    No change -> Tester
    Update -> AWS_TRANSLATE_2
    Insert -> AWS_TRANSLATE_2
    Delete -> AttributeKeeper
Terminator
    MESSAGE = ERROR: Unknown _event value from Metadata_Delta
Note: Selects items with no change for publishing, overwriting all existing data
Tester
    BOOL_OP = OR
    COMPOSITE_TEST = 1
    TEST_CLAUSE = TEST $(PYCSW_OVERWRITE) = YES
    TEST_MODE = TEST
    PASSED -> AttributeCreator
    FAILED -> StatisticsCalculator
Note: Reset to update
AttributeCreator
    ATTR_TABLE = SET_TO PyCSW_Transaction = Update
    -> AWS_TRANSLATE_2
Note: Retains ID for list of deleted items
AttributeKeeper
    KEEP_ATTRS = id
    -> VariableRetriever_9
VariableRetriever_9
    SCOPE = Global
    VALUE_ATTR = _timestamp
    VARNAME = _timestamp
    -> DELETEDRECORDS (writer XLSXW_1)
DELETEDRECORDS (writer XLSXW_1)
    attributes: id string(200), _timestamp string(200)
Creator_2
    GEOMTYPE = Geometry Object
    NUM = 1
    CREATED -> StatisticsCalculator
StatisticsCalculator
    COMPUTE_HISTOGRAM = NO
    COUNT_ATTR = _count
    PREPEND_ATTR_NAME_CHOICE = For multiple results only
    STATS_ATTRS = id
    SUMMARY -> AttributeCreator_2
AttributeCreator_2
    ATTR_TABLE = SET_TO _real_count = @Evaluate(@Value(_count)-1)
    -> StatisticsCalculator_Summary
StatisticsCalculator_Summary: Logger
    LOG_FEATURE = NONE
    MAXFEATS = 20
    MESSAGE:
      ************************
      **** Unchanged Report ****
      ************************

      @Value(_real_count) features were unchanged

      ************************
      ************************
      ************************
    SEVERITY = INFO

Bookmark: AWS Translation
Note: English to french / notes, / title, / tags_en / resources name
AWS_TRANSLATE_2
    ACTIVATE_TRANSLATION = $(ACTIVATE_TRANSLATION)
    ATTR_2_Translate = notes,title
    ATTR_LIST_2_Translate = resources{}.name,tags_eng{}.display_name
    MODE = English-->French
    -> AWS_TRANSLATE_3
    TRANSLATION_PROBLEM -> VariableRetriever_5
Note: French to english (tags_fr)
AWS_TRANSLATE_3
    ACTIVATE_TRANSLATION = $(ACTIVATE_TRANSLATION)
    ATTR_LIST_2_Translate = tags_fra{}.display_name
    MODE = French-->English
    -> AttributeExposer_6
    TRANSLATION_PROBLEM -> VariableRetriever_3
VariableRetriever_3
    SCOPE = Global
    VALUE_ATTR = _timestamp
    VARNAME = _timestamp
    -> Translation_errors (writer XLSXW_1)
VariableRetriever_5
    SCOPE = Global
    VALUE_ATTR = _timestamp
    VARNAME = _timestamp
    -> Translation_errors (writer XLSXW_1)
Translation_errors (writer XLSXW_1)
    attributes: id string(20), _timestamp string(20)

Bookmark: Rebuilding tags list
AttributeExposer_6
    ATTR_LIST = tags_eng{},tags_fra{}
    -> ListElementCounter_2
ListElementCounter_2
    CNT_ATTR = _nb_tags_en
    LIST_NAME = tags_eng{}
    -> ListElementCounter_3
ListElementCounter_3
    CNT_ATTR = _nb_tags_fr
    LIST_NAME = tags_fra{}
    -> PythonCaller_2
PythonCaller_2
    NEW_ATTRIBUTES = tags{}.display_name_lower tags{}.display_name_fr_lower
    PYTHONSOURCE:
      import fme
      import fmeobjects
      # Template Function interface:
      # When using this function, make sure its name is set as the value of
      # the 'Class or Function to Process Features' transformer parameter
      def processFeature(feature):
          i=0

          for j in range(int(feature.getAttribute('_nb_tags_en'))):
              feature.setAttribute('tags{%i}.display_name'%(i),feature.getAttribute('tags_eng{%i}.display_name'%(j)))
              feature.setAttribute('tags{%i}.display_name_lower'%(i),feature.getAttribute('tags_eng{%i}.display_name'%(j)).lower())
              feature.setAttribute('tags{%i}.display_name_fr'%(i),feature.getAttribute('tags_eng{%i}.display_name_fr'%(j)))
              feature.setAttribute('tags{%i}.display_name_fr_lower'%(i),feature.getAttribute('tags_eng{%i}.display_name_fr'%(j)).lower())
              i=i+1

          for k in range(int(feature.getAttribute('_nb_tags_fr'))):
              feature.setAttribute('tags{%i}.display_name'%(i),feature.getAttribute('tags_fra{%i}.display_name_en'%(k)))
              feature.setAttribute('tags{%i}.display_name_lower'%(i),feature.getAttribute('tags_fra{%i}.display_name_en'%(k)).lower())
              feature.setAttribute('tags{%i}.display_name_fr'%(i),feature.getAttribute('tags_fra{%i}.display_name'%(k)))
              feature.setAttribute('tags{%i}.display_name_fr_lower'%(i),feature.getAttribute('tags_fra{%i}.display_name'%(k)).lower())
              i=i+1
    PYTHONSYMBOL = processFeature
    -> ListDuplicateRemover
ListDuplicateRemover
    SRC_LIST = tags{}.display_name_lower
    -> ListDuplicateRemover_3
ListDuplicateRemover_3
    SRC_LIST = tags{}.display_name_fr_lower
    -> AttributeExposer_12

Bookmark: GEO - NONGEO FILTER
AttributeExposer_12
    ATTR_LIST = _typedataset
    -> AttributeFilter_2
AttributeFilter_2
    ATTR_NAME = _typedataset
    ATTR_VALUES = <Empty>,<Missing>,<Null>,<Unfiltered>,GEO,NONGEO
    <EMPTY> -> Terminator_2
    <MISSING> -> Terminator_2
    <NULL> -> Terminator_2
    <UNFILTERED> -> Terminator_2
    GEO -> XML_PUBLISHER_2
    NONGEO -> JSON_PUBLISHER_2
Terminator_2
    MESSAGE = Translation Terminated : <Empty>, <Missing>, <Null> or <Unfiltered> value for attribute "_typedataset" (GEO or NONGEO)

Bookmark: XML CREATION AND WRITING
Note: Config_NB
LOOKUP_TABLES_READER_11
    CSV_ENCODING = utf-8
    CSV_PATH = $(IN_CSV_LOOKUPTABLES_DIR)
    FEATURE_TYPE = Config_NB
    PT = NB
    -> XML_PUBLISHER_2 [CONFIG_FILE]
XML_PUBLISHER_2
    LOCAL_WRITER = $(LOCAL_WRITER)
    TEMPLATE_GMD_CITEDRESPONSIBLEPARTY = $(IN_GMD_XML_TEMPLATE_DIR)/GMD_CITEDRESPONSIBLEPARTY.xml
    TEMPLATE_GMD_CONTACT = $(IN_GMD_XML_TEMPLATE_DIR)/GMD_CONTACT.xml
    TEMPLATE_GMD_DISTRIBUTIONFORMAT = $(IN_GMD_XML_TEMPLATE_DIR)/GMD_DISTRIBUTIONFORMAT.xml
    TEMPLATE_GMD_DISTRIBUTOR = $(IN_GMD_XML_TEMPLATE_DIR)/GMD_DISTRIBUTOR.xml
    TEMPLATE_GMD_KEYWORDS = $(IN_GMD_XML_TEMPLATE_DIR)/GMD_KEYWORDS.xml
    TEMPLATE_GMD_MDMETADATA = $(IN_GMD_XML_TEMPLATE_DIR)/GMD_MDMETADATA.xml
    TEMPLATE_GMD_REFERENCESYSTEMINFO = $(IN_GMD_XML_TEMPLATE_DIR)/GMD_REFERENCESYSTEMINFO.xml
    TEMPLATE_GMD_RESOURCEMAINTENANCE = $(IN_GMD_XML_TEMPLATE_DIR)/GMD_RESOURCEMAINTENANCE.xml
    TEMPLATE_GMD_TOPICCATEGORY = $(IN_GMD_XML_TEMPLATE_DIR)/GMD_TOPICCATEGORY.xml
    TEMPLATE_GMD_TRANSFEROPTIONS = $(IN_GMD_XML_TEMPLATE_DIR)/GMD_TRANSFEROPTIONS.xml
    LOCAL -> text_line (writer TEXTLINE_3)
    INSERT_PASSED -> text_line (writer TEXTLINE_1)
    INSERT_FAILED -> text_line (writer TEXTLINE_2)
    UPDATE_PASSED -> text_line (writer TEXTLINE_1)
    InvalidMetadata -> VariableRetriever_12
    UPDATE_FAILED -> text_line (writer TEXTLINE_2)

Bookmark: JSON CREATION AND WRITING
Note: Config_JSON_NB
LOOKUP_TABLES_READER_20
    CSV_ENCODING = utf-8
    CSV_PATH = $(IN_CSV_LOOKUPTABLES_DIR)
    FEATURE_TYPE = Config_JSON_NB
    PT = $(P-T_ABBR)
    -> JSON_PUBLISHER_2 [CONFIG_FILE]
JSON_PUBLISHER_2
    JSON_RESOURCE_TEMPLATE = $(IN_TBS_JSON_TEMPLATE_DIR)/TBS_RESOURCES_TEMPLATE.json
    JSON_ROOT_TEMPLATE = $(IN_TBS_JSON_TEMPLATE_DIR)/TBS_ROOT_TEMPLATE.json
    Keywords_EN = tags{}.display_name
    Keywords_FR = tags{}.display_name_fr
    Subject_LIST = TBS_Subject{}.value
    Topic_LIST = TBS_Topic{}.value
    OUTPUT_LOCAL -> AttributeExposer_17
AttributeExposer_17
    ATTR_LIST = json_file
    -> text_line (writer TEXTLINE_4)
text_line (writer TEXTLINE_4)
    attributes: text_line_data buffer

FME custom transformer ListSlicer_2
Replaces an existing list with a list containing elements of the slicing range which is determined by the starting index and the number of elements.
If the source list was a structured one like "_list{}.foo", "_list{}.bar", all the members belonging to the same base name will be replaced.
Example
When the source list contains:
_list{0}.foo = '0'
_list{1}.foo = '1'
_list{2}.foo = '2'
_list{3}.foo = '3'
_list{4}.foo = '4'
_list{0}.bar = 'A'
_list{1}.bar = 'B'
_list{2}.bar = 'C'
_list{3}.bar = 'D'
_list{4}.bar = 'E'
After slicing with Starting Element Index = 1 and Number of Elements to Slice = 3, the list will be replaced with:
_list{0}.foo = '1'
_list{1}.foo = '2'
_list{2}.foo = '3'
_list{0}.bar = 'B'
_list{1}.bar = 'C'
_list{2}.bar = 'D'
Note: This transformer contains a Python script which was tested with both Python 2.7 interpreter and Python 3.6 interpreter.
Parameters
    Source List Attribute:
Select a source list attribute to be sliced.
    Starting Element Index:
Specify index of the element to start slicing. The index is always 0-based.
If specified index is less than 0, this transformer considers the starting index as 0.
    Number of Elements to Slice:
Specify the number of elements to be sliced.
If specified number is equal to 0, this transformer removes every element from the source list (i.e. removes the source list).
If specified number is less than 0, this transformer considers the number as 0.
    Null Elements Treatment:
Select how treat <null> elements in the slicing range.
"Replace with Empty String" - Every <null> element will be replaced with an empty string.
"Replace with New Value" - Every <null> element will be replaced with a value specified as New Value for Null parameter.
"Replace with Missing" - Every <null> element will be removed. The element will be missing in the resultant list.
"Leave Null" - Every <null> element will be left in the resultant list as <null>.
    New Value for Null:
Specify a value to be used for replacing <null> elements.
This parameter is used only if you selected "Replace with New Value" to Null Elements Treatment. Otherwise, it'll be just ignored.
    Missing Elements Treatment:
Select how treat <missing> elements in the slicing range.
"Replace with Empty String" - Every <missing> element will be replaced with an empty string.
"Replace with New Value" - Every <missing> element will be replaced with a value specified as New Value for Missing parameter.
"Replace with Null" - Every <missing> element will be replaced with <null>.
"Leave Missing" - Every <missing> element will be still missing in the resultant list.
    New Value for Missing:
Specify a value to be used for replacing <missing> elements.
This parameter is used only if you selected "Replace with New Value" to Missing Elements Treatment. Otherwise, it'll be just ignored.

Parameters:
- SRC_LIST =   # " " Source List Attribute
- START_INDEX = 0   # Starting Element Index
- NUM_ELEMENTS =   # Number of Elements to Slice
- NULL_TREATMENT = empty
- NEWVALUE_FOR_NULL =   # New Value for Null
- MISSING_TREATMENT = empty
- NEWVALUE_FOR_MISSING =   # New Value for Missing

Input (input)
    -> ParameterFetcher
ParameterFetcher
    ATTR_LIST = __listslicer.src_list {$(SRC_LIST)} __listslicer.start_index {$(START_INDEX)} __listslicer.num_elements {$(NUM_ELEMENTS)} __listslicer.null_treat {$(NULL_TREATMENT)} __listslicer.newvalue_for_null {$(NEWVALUE_FOR_NULL)} __listslicer.missing_treat {$(MISSING_TREATMENT)} __listslicer.newvalue_for_missing {$(NEWVALUE_FOR_MISSING)}
    -> PythonCaller
PythonCaller
    HIDE_ATTRIBUTES = __listslicer.src_list __listslicer.start_index __listslicer.num_elements __listslicer.null_treat __listslicer.newvalue_for_null __listslicer.missing_treat __listslicer.newvalue_for_missing
    PYTHONSOURCE:
      # 2014-07-27, Takashi Iijima, Original Implementation
      # 2014-08-02, Takashi Iijima, Resolved encoding issue on list name
      # 2018-06-14, Takashi Iijima, Updated to support both Python 2.7 and Python 3.x
      # 2020-04-30, Takashi Iijima, Changed default Python interpreter version to 3.x, saved with FME 2017.1.2.1

      import fmeobjects, re

      class ListSlicer(object):
          def __init__(self):
              import platform
              if platform.python_version_tuple()[0] == '2':
                  import locale
                  loc = locale.getdefaultlocale()
                  enc = loc[1] if loc else 'utf_8'
                  self.toStr = lambda s: s.encode(enc) if isinstance(s, unicode) else s
              else:
                  self.toStr = lambda s: s

          def input(self, feature):
              listName = self.toStr(feature.getAttribute('__listslicer.src_list'))
              prefix = listName[:-2]
              regexListElement = re.compile(r'^%s\{(\d+)\}(.*)$' % prefix)

              # Find maximum element index and collect suffixes of target list members.
              maxIndex = -1
              suffixes = set([])
              for name in [self.toStr(s) for s in feature.getAllAttributeNames()]:
                  m = regexListElement.match(name)
                  if m:
                      if maxIndex < int(m.group(1)):
                          maxIndex = int(m.group(1))
                      suffixes.add(self.toStr(m.group(2)))

              startIndex = int(feature.getAttribute('__listslicer.start_index'))
              if startIndex < 0:
                  startIndex = 0
              numElements = int(feature.getAttribute('__listslicer.num_elements'))
              if numElements < 0:
                  numElements = 0

              nullTreat = feature.getAttribute('__listslicer.null_treat')
              newValueToNull = feature.getAttribute('__listslicer.newvalue_for_null')

              missingTreat = feature.getAttribute('__listslicer.missing_treat')
              newValueToMissing = feature.getAttribute('__listslicer.newvalue_for_missing')

              for suffix in suffixes:
                  # Move elements from slicing range to head of the list.
                  for i in range(numElements):
                      srcName = '%s{%d}%s' % (prefix, startIndex + i, suffix)
                      destName = '%s{%d}%s' % (prefix, i, suffix)

                      isNull, isMissing, type = feature.getAttributeNullMissingAndType(srcName)
                      if isNull:
                          if nullTreat == 'empty':
                              feature.setAttribute(destName, '')
                          elif nullTreat == 'newvalue':
                              feature.setAttribute(destName, newValueToNull)
                          elif nullTreat == 'missing':
                              feature.removeAttribute(destName)
                          elif nullTreat == 'as_is':
                              feature.setAttributeNullWithType(destName, type)
                          else:
                              raise fmeobjects.FMEException('Debug error: Null Treatment')

                      elif isMissing:
                          if missingTreat == 'empty':
                              feature.setAttribute(destName, '')
                          elif missingTreat == 'newvalue':
                              feature.setAttribute(destName, newValueToMissing)
                          elif missingTreat == 'null':
                              feature.setAttributeNullWithType(destName, type)
                          elif missingTreat == 'as_is':
                              feature.removeAttribute(destName)
                          else:
                              raise fmeobjects.FMEException('Debug error: Missing Treatment')

                      else:
                          feature.setAttribute(destName, feature.getAttribute(srcName))

                  # Remove excess elements.
                  for i in range(numElements, maxIndex + 1):
                      feature.removeAttribute('%s{%d}%s' % (prefix, i, suffix))

              feature.removeAttrsWithPrefix('__listslicer.')
              self.pyoutput(feature)

          def close(self):
              pass
    PYTHONSYMBOL = ListSlicer
    -> Output (output)
Output (output)
