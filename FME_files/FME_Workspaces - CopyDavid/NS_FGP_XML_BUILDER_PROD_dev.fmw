FME workspace NS_FGP_XML_BUILDER_PROD_dev.fmw

Parameters:
- ACTIVATE_TRANSLATION = No
- CATALOGUE_READER_SELECT = Yes
- GEOPORTAL_WEBLINK_ADDER_SELECT = Yes
- FORCED_PYCSW_URL =
- IN_FFS_TESTING_FILE = C:\DavidH\NRCan\Data\PT_Harvest\NS\Setup_FeatureReader2_juillet21.ffs
- IN_FFS_TESTING_FILE_2 = C:\DavidH\NRCan\Data\PT_Harvest\NS\Setup_GeoPortal_Weblink_Addder_Aout17.ffs
- IN_CSV_LOOKUPTABLES_DIR = C:\DavidH\NRCan\fgp-metadata-proxy\FME_files\LOOKUP_TABLES   # Lookup Tables Directory
- IN_GMD_XML_TEMPLATE_DIR = C:\DavidH\NRCan\Data\PT_Harvest\XML_TEMPLATES
- LOCAL_SOURCE_METADATA_DELTA_FINDER = Yes
- LOCAL_WRITER = Yes
- OUT_XLS_NOTIFICATION_DIR = C:\DavidH\NRCan\Data\PT_Harvest\NS\XLS
- OUT_XML_FAILED_DIR = C:\DavidH\NRCan\Data\PT_Harvest\NS\XML_FAILED
- OUT_XML_LOCAL_DIR = C:\DavidH\NRCan\Data\PT_Harvest\NS\XML_LOCAL
- OUT_XML_PASSED_DIR = C:\DavidH\NRCan\Data\PT_Harvest\NS\XML_PASSED
- P-T_ABBR = NS
- PYCSW_OVERWRITE = YES
- LOG_FILE = C:\DavidH\NRCan\Data\PT_Harvest\NS\LOG\NS.log
- DestDataset_CSV2 = C:\DavidH\NRCan\Data\PT_Harvest\NS   # Destination CSV (Comma Separated Value) Folder

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(OUT_XLS_NOTIFICATION_DIR)
- CSV2_1: CSV2 to $(DestDataset_CSV2)

Creator_3
    GEOMTYPE = Geometry Object
    NUM = 1
    CREATED -> DateTimeStamper
DateTimeStamper
    DATETIME_ATTR = _toto
    STAMP_TYPE = date
    TIMEZONE = local
    -> VariableSetter
Note: Can you adjust the way you are reading data. / There are 270 records avalaible on https://gnb.socrata.com/en/browse but this reader gives only 156. Can we are 270 records and split geo vs non geo after / Why the parameter unit test ?
VariableSetter
    SCOPE = Global
    VALUE = @Value(_toto)
    VARNAME = _timestamp
    -> Tester_6
NB_HrefResourcesExtractor_2: NB_HREF_RESOURCES_EXTRACTOR [off]
    -> NB_advancedViewResourceMapper [off]
Note: new CT, assigns resource values for advanced views in the same format as the other resources
NB_advancedViewResourceMapper: NB_ADVANCED_VIEW_RESOURCE_MAPPER [off]
    -> NB_AttachementManager [off]
NB_AttachementManager [off]
    SBN_URL_ROOT = https://data.novascotia.ca
Note: PyCSW_config
LOOKUP_TABLES_READER_17
    CSV_ENCODING = utf-8
    CSV_PATH = $(IN_CSV_LOOKUPTABLES_DIR)
    FEATURE_TYPE = PyCSW_config
    PT = NB
    -> PYCSW_URL_MAPPER [PYCSW_CONFIG]
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer
VariableRetriever_12
    SCOPE = Global
    VALUE_ATTR = _timestamp
    VARNAME = _timestamp
    -> invalid_metadata (writer XLSXW_1)
invalid_metadata (writer XLSXW_1)
    attributes: id auto(20)

Bookmark: Initial Setup and Read from Socrata
Tester_6
    BOOL_OP = OR
    COMPOSITE_TEST = 1
    TEST_CLAUSE = TEST $(CATALOGUE_READER_SELECT) = Yes
    TEST_MODE = TEST
    PASSED -> Socrata_Reader
    FAILED -> FeatureReader_2 [INITIATOR]
Socrata_Reader: SOCRATA_READER
    DOMAIN = http://data.novascotia.ca
    -> ATTRIBUTE_VALUE_TEXT_CLEANER
FeatureReader_2
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> ATTRIBUTE_VALUE_TEXT_CLEANER
ATTRIBUTE_VALUE_TEXT_CLEANER
    -> AttributeExposer_3
AttributeExposer_3
    ATTR_LIST = id
    -> Tester_4
Tester_4
    BOOL_OP = OR
    COMPOSITE_TEST = 1
    TEST_CLAUSE = TEST @Value(id) = knwz-4bap
    TEST_MODE = TEST
    PASSED -> NullAttributeMapper
    FAILED -> NullAttributeMapper
NullAttributeMapper
    ATTRCHOICE = Selected Attributes
    ATTRLIST = licenseId
    NEW_VALUE = none
    NULL_TREATMENT = New Value
    SOURCE_ATTR_VAL = Null Empty "Missing (Selected Attributes Only)"
    -> LICENSE_FILTER
LOOKUP_TABLES_READER_19
    CSV_ENCODING = utf-8
    CSV_PATH = $(IN_CSV_LOOKUPTABLES_DIR)
    FEATURE_TYPE = License_NS
    PT = NS
    -> LICENSE_FILTER [LOOKUP_TABLE_INPUT]
LICENSE_FILTER
    LICENSE_ATT = @Value(licenseId)
    LICENSE_FILTER_PASSED -> NB_MetadataMerger [off]
    LICENSE_FILTER_PASSED -> Socrata_MetadataMerger
Socrata_MetadataMerger: SOCRATA_METADATA_MERGER
    DOMAIN = http://data.novascotia.ca
    -> DEFAULT_ATTRIBUTE_MAPPER
    UnmergedAdvancedView -> VariableRetriever_4
Note: I changed the output of the advanced views resources list to output to its own separate list. format and name are handled in later CT
Note: On peut utilser le custom de NB. Par contre, il faudrait publier domaine utiisé pour générer l'URL pour la liste des advanced view. / Aussi, en même temps, modifier le FeatureMerger pour créer la liste avant le merge, comme montré dans cette version
NB_MetadataMerger [off]
    -> DEFAULT_ATTRIBUTE_MAPPER [off]
    UnmergedAdvancedView -> VariableRetriever_4 [off]
VariableRetriever_4
    SCOPE = Global
    VALUE_ATTR = _timestamp
    VARNAME = _timestamp
    -> unmergedAdvancedView (writer XLSXW_1)
unmergedAdvancedView (writer XLSXW_1)
    attributes: url string(200), format string(200), _seriesID string(200), _timestamp string(200)
Note: Default_NB
LOOKUP_TABLES_READER_7
    CSV_ENCODING = utf-8
    CSV_PATH = $(IN_CSV_LOOKUPTABLES_DIR)
    FEATURE_TYPE = Default_NS
    PT = NS
    -> DEFAULT_ATTRIBUTE_MAPPER [LOOKUP_TABLE_INPUT]
DEFAULT_ATTRIBUTE_MAPPER
    -> NS_ATTRIBUTE_MANAGER
Note: Nouveau custom pour NS, / Inspiré de celui de NB
NS_ATTRIBUTE_MANAGER
    -> TestFilter
    error_datetime_output -> VariableRetriever_7
VariableRetriever_7
    SCOPE = Global
    VALUE_ATTR = _timestamp
    VARNAME = _timestamp
    -> Error_Datetime (writer XLSXW_1)
Error_Datetime (writer XLSXW_1)
    attributes: sector string(200), notes string(200), title string(200), record_publish_date string(200), record_last_modified string(200), record_create_date string(200), spatialref__.projection_name string(200), spatialref__.projection_system string(200), spatialref__.projection_system_version string(200), id string(200), UNIQUE_ATT string(200), resource.id string(200), resource.type string(200), socrataDomainURL string(200), _response_body string(200), _http_status_code string(200), licenseId string(200), assetType string(200), modifyingViewUid string(200), url string(200), format string(200), _seriesID string(200), advancedViewResources__.url string(200), advancedViewResources__.format string(200), contacts__.email string(200), contacts__.name string(200), contacts__.role string(200), iso_topic__ string(200), iso_topic__.topic_value string(200), projectionList__.codespace string(200),
      projectionList__.projection_name string(200), projectionList__.version string(200), resources__.data_collection_end_date string(200), resources__.data_collection_start_date string(200), resources__.format string(200), resources__.name string(200), resources__.resource_update_cycle string(200), resources__.url string(200), default_domain_tag string(200), default_projection_name string(200), default_projection_system_version string(200), default_reference_system string(200), metadata.custom_fields.Detailed Metadata.Department string(200), description string(200), name string(200), publicationDate string(200), viewLastModified string(200), createdAt string(200), tags__.display_name string(200), fme_rejection_code string(20), _timestamp string(200)
Note: NB_TOPICS_DATASET
LOOKUP_TABLES_READER_4
    CSV_ENCODING = utf-8
    CSV_PATH = $(IN_CSV_LOOKUPTABLES_DIR)
    FEATURE_TYPE = GeoportalWeblink_NS
    PT = NS
    -> GEOPORTAL_WEBLINK_ADDER [LOOKUP_TABLE_INPUT]
Creator_4
    GEOMTYPE = Geometry Object
    NUM = 1
    CREATED -> TestFilter
TestFilter
    DEFAULT_VALUE = <UNFILTERED>
    TEST_LIST:
      "BOOL_OP,AND,COMPOSITE_TEST,""""""1 AND 2"""""",TEST_CLAUSE,TEST $(GEOPORTAL_WEBLINK_ADDER_SELECT) = Yes
      TEST id ATTRIBUTE_HAS_A_VALUE """,Attribute Manager,"BOOL_OP,AND,COMPOSITE_TEST,""""""1 AND 2"""""",TEST_CLAUSE,TEST $(GEOPORTAL_WEBLINK_ADDER_SELECT) != Yes
      TEST id ATTRIBUTE_IS_MISSING """,Feature Reader
    Attribute Manager -> GEOPORTAL_WEBLINK_ADDER
    Feature Reader -> FeatureReader_3 [INITIATOR]
Note: On garde le même custom. / j'ai temporairement désactivé la validation du lien pour accèlérer de le developpmentn / On pourrait renommer le custom Provincial portal webb link adder
Note: Nouveau custom inspiré du NB reserouces merger. / Vérifier si on peut faire de quoi de générique
GEOPORTAL_WEBLINK_ADDER
    WEBLINK_WILDCARD = @Value(resource.id)
    -> ChildViewAttributeTypeExtractor
FeatureReader_3
    ATTRIBUTES = ProvincialPortal_WeblinkAdder_OUTPUT,"sector,notes,title,record_publish_date,record_last_modified,record_create_date,id,UNIQUE_ATT,resource.id,resource.type,socrataDomainURL,_response_body,_http_status_code,licenseId,assetType,modifyingViewUid,url,format,_seriesID,default_domain_tag,default_projection_name,default_projection_system_version,default_reference_system,""metadata.custom_fields.Detailed Metadata.Department"",description,name,publicationDate,viewLastModified,createdAt,_element_count_res,_error,fme_rejection_code"
    ATTR_ACCUM_MODE = Only Use Result
    COMBINE_GEOM = Use Result
    DATASET = $(IN_FFS_TESTING_FILE_2)
    FFS_USE_SEARCH_ENVELOPE = NO
    FORMAT = FFS
    INTERACT = <No Spatial Filter>
    OUTPUT_FEATURES_DISPLAY = Schema and Data Features
    ProvincialPortal_WeblinkAdder_OUTPUT -> ChildViewAttributeTypeExtractor
GEOPORTAL_WEBLINK_ADDER_LINKED [off]
    WEBLINK_WILDCARD = @Value(resource.id)
Note: Creer une grosse liste en fusionnant la liste columms de l'entité et la liste des childview. / Pour la liste de l'entité, on ajoute le id du datasets comme layerdi / Prétraitement fairt pour utilise leGeospatialFilter_AttributeType
PythonCaller_4
    NEW_ATTRIBUTES = _contains_geo
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              self.keyword=r'lidar|dem|dtm|elevation|geoscientific'.split('|')
          def input(self,feature):
              isgeo=0
              list_tags=feature.getAttribute('tags{}.display_name')
              for elem in self.keyword:
                  for tags in list_tags:

                      for tags_word in tags.split(' '):

                          if tags_word==elem:

                              isgeo=1

              feature.setAttribute('_contains_geo',isgeo)
              self.pyoutput(feature)
          def close(self):
              pass
    PYTHONSYMBOL = FeatureProcessor
    -> Tester_2
Note: Nouveau custom pour filter les données selon le type d'attribu dans un portail de type socrata. / Le rendre générique, probalerment que le portail ESRI de SK et MB pourra avoir de l'info sur la même swing,
AttributeCreator_6
    ATTR_TABLE = SET_TO id_temp = @Value(id)
    -> AttributeCreator_7
AttributeCreator_7
    ATTR_TABLE = SET_TO id = @Value(resource.id)
    -> MANUAL_GEOSPATIAL_SETTER [DATA_INPUT]
Note: NB_TOPICS_DATASET
LOOKUP_TABLES_READER_3
    CSV_ENCODING = utf-8
    CSV_PATH = $(IN_CSV_LOOKUPTABLES_DIR)
    FEATURE_TYPE = UUID_Spatial_NS
    PT = NS
    -> MANUAL_GEOSPATIAL_SETTER [LOOKUP_TABLE_INPUT]
MANUAL_GEOSPATIAL_SETTER
    GEOSPATIAL -> AttributeCreator_5
Note: NB_TOPICS_DATASET
Note: Il faut modifier le progamme pour publier le nom de liste contenant le type spatial
LOOKUP_TABLES_READER_10
    CSV_ENCODING = utf-8
    CSV_PATH = $(IN_CSV_LOOKUPTABLES_DIR)
    FEATURE_TYPE = SpatialType_NS
    PT = NS
    -> SPATIAL_TYPE_MAPPER [LOOKUP_TABLE_INPUT]
SPATIAL_TYPE_MAPPER_DATA_OUTPUT_FAILED: Inspector
File1 (writer CSV2_1)
    attributes: id string, notes string, title string, url string
manually add data (writer CSV2_1)
    attributes: spatial_representation_type string, id string
AttributeCreator_5
    ATTR_TABLE = SET_TO id = @Value(id_temp)
    -> AttributeRemover_2
AttributeRemover_2
    REMOVE_ATTRS = id_temp
    -> PythonCaller_5
Note: Créer une nouvelle liste en conservant uniquement les attributs de type geo
PythonCaller_5
    NEW_ATTRIBUTES = geom_att{}.geomcol geom_att{}.layerid
    PYTHONSOURCE:
      import fme
      import fmeobjects
      # Template Function interface:
      # When using this function, make sure its name is set as the value of
      # the 'Class or Function to Process Features' transformer parameter
      def processFeature(feature):
          j=0

          if feature.getAttribute('global_list_attribute_type{}.geo'):

              for i in range(len(feature.getAttribute('global_list_attribute_type{}.geo'))):
                  if feature.getAttribute('global_list_attribute_type{%i}.geo'%(i)).lower()=='yes':
                      feature.setAttribute('geom_att{%i}.geomcol'%(j),feature.getAttribute('global_list_attribute_type{%i}.fieldName'%(i)))
                      feature.setAttribute('geom_att{%i}.layerid'%(j),feature.getAttribute('global_list_attribute_type{%i}.layerid'%(i)))
                      j+=1



      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> Socrata_BoundingBoxExtractor [feature_input]
Socrata_BoundingBoxExtractor: SOCRATA_BOUNDING_BOX_EXTRACTOR
    DOMAIN = http://data.novascotia.ca
    SocrataAppToken = FL3Cxsebg0Vf6JQ0CnbMujHkQ
    feature_output -> Socrata_HrefResourcesExtractor [AttributeExposer_Input]
Note: Revoir le code pour avoir de quoi de générique / Ajuster le programme de NB pour utiliser le CT de manière générique
NB_BoundingBoxExtractor: NB_BOUNDING_BOX_EXTRACTOR [off]
    SocrataAppToken = FL3Cxsebg0Vf6JQ0CnbMujHkQ
    Socrata_Domain = https://data.novascotia.ca

Bookmark: Cpde de remplacement pour le NB_RESOURCE_TYPE_FILTER
ChildViewAttributeTypeExtractor
    DOMAIN = https://data.novascotia.ca
    -> AttributeExposer_4
AttributeExposer_4
    ATTR_LIST = columns{}.dataTypeName,AttributeTypeChildView{}.dataTypeName,columns{}.fieldName,AttributeTypeChildView{}.fieldName,tags{}.display_name,AttributeTypeChildView{}.layerid
    -> ListElementCounter
ListElementCounter
    CNT_ATTR = _element_count_columns
    LIST_NAME = columns{}
    -> ListElementCounter_4
ListElementCounter_4
    CNT_ATTR = _element_count_childview
    LIST_NAME = AttributeTypeChildView{}
    -> PythonCaller
PythonCaller
    NEW_ATTRIBUTES = global_list_attribute_type{}.dataTypeName
    PYTHONSOURCE:
      import fme
      import fmeobjects
      # Template Function interface:
      # When using this function, make sure its name is set as the value of
      # the 'Class or Function to Process Features' transformer parameter
      def processFeature(feature):
          #Traitement de la section première liste columns
          j=0
          for i in range(int(feature.getAttribute('_element_count_columns'))):
              temp=feature.getAttribute('columns{%i}.dataTypeName'%(i))
              if temp:
                  feature.setAttribute('global_list_attribute_type{%i}.dataTypeName'%(i),temp)
                  feature.setAttribute('global_list_attribute_type{%i}.fieldName'%(i),feature.getAttribute('columns{%i}.fieldName'%(i)))
                  feature.setAttribute('global_list_attribute_type{%i}.layerid'%(i),feature.getAttribute('resource.id'))
                  j+=1
          #Traitement de la deuxième liste
          for i in range(int(feature.getAttribute('_element_count_childview'))):
              temp=feature.getAttribute('AttributeTypeChildView{%i}.dataTypeName'%(i))
              if temp:
                  feature.setAttribute('global_list_attribute_type{%i}.dataTypeName'%(i),temp)
                  feature.setAttribute('global_list_attribute_type{%i}.fieldName'%(i),feature.getAttribute('AttributeTypeChildView{%i}.fieldName'%(i)))
                  feature.setAttribute('global_list_attribute_type{%i}.layerid'%(i),feature.getAttribute('AttributeTypeChildView{%i}.layerid'%(i)))
                  j+=1





      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> AttributeExposer_6
AttributeExposer_6
    ATTR_LIST = global_list_attribute_type{}.spatial_type,id,resource.id
    -> GeospatialFilter_AttributeType
Note: NB_GeoDataTypes
LOOKUP_TABLES_READER_2
    CSV_ENCODING = utf-8
    CSV_PATH = $(IN_CSV_LOOKUPTABLES_DIR)
    FEATURE_TYPE = GeospatialValidation-AttributeType
    PT = NS
    -> GeospatialFilter_AttributeType [AttributeType]
GeospatialFilter_AttributeType
    ATTR_NAME_ATTR_TYPE = dataTypeName
    LIST_NAME = global_list_attribute_type{}
    Geospatial -> AttributeCreator_3
    NonGeospatial -> PythonCaller_4
Tester_2
    BOOL_OP = OR
    COMPOSITE_TEST = 1
    TEST_CLAUSE = TEST @Value(_contains_geo) = 1
    TEST_MODE = TEST
    PASSED -> AttributeCreator_3
    FAILED -> AttributeCreator_6
AttributeCreator_3
    ATTR_TABLE = SET_TO id_temp = @Value(id)
    -> AttributeCreator_4

Bookmark: Adding
AttributeCreator_4
    ATTR_TABLE = SET_TO id = @Value(resource.id)
    -> SPATIAL_TYPE_MAPPER [DATA_INPUT]
SPATIAL_TYPE_MAPPER
    FEATURE_LIST_SEARCH = Yes
    DATA_OUTPUT_FAILED -> File1 (writer CSV2_1)
    DATA_OUTPUT_FAILED -> SPATIAL_TYPE_MAPPER_DATA_OUTPUT_FAILED
    DATA_OUTPUT_PASSED -> AttributeCreator_5
    MANUAL_ITEMS_OUTPUT -> manually add data (writer CSV2_1)

Bookmark: Resource Mapping
Note: C'est le même code source que celui de NB. Il faut vérifier chaque CT pour s'assurer que â fionctionne comme du monde... / Il y en a pas d'autres à ajouter
Socrata_HrefResourcesExtractor: SOCRATA_HREF_RESOURCES_EXTRACTOR
    -> Socrata_AdvancedViewResourceMapper
Socrata_AdvancedViewResourceMapper: SOCRATA_ADVANCED_VIEW_RESOURCE_MAPPER
    -> Socrata_AtachmentManager
Socrata_AtachmentManager: SOCRATA_ATTACHMENT_MANAGER
    SBN_URL_ROOT = http://data.novascotia.ca
    -> SOCRATA_RESOURCE_MAPPER
Note: NB_LINKBUILDER_GEO
LOOKUP_TABLES_READER_8
    CSV_ENCODING = utf-8
    CSV_PATH = $(IN_CSV_LOOKUPTABLES_DIR)
    FEATURE_TYPE = NS_LINKBUILDER_GEO
    PT = NS
    -> SOCRATA_RESOURCE_MAPPER [linkbuilder_geo]
Note: NB_LINKBUILDER_NONGEO
LOOKUP_TABLES_READER_9
    CSV_ENCODING = utf-8
    CSV_PATH = $(IN_CSV_LOOKUPTABLES_DIR)
    FEATURE_TYPE = NS_LINKBUILDER_NONGEO
    PT = NS
    -> SOCRATA_RESOURCE_MAPPER [LinkBuilderNonGeo]
Note: only changed attribute names
SOCRATA_RESOURCE_MAPPER
    DOMAIN = https://data.novascotia.ca
    -> AttributeExposer_5
AttributeExposer_5
    ATTR_LIST = resources{}.url
    -> ListCopier
ListCopier
    DEST_LIST = resources_copy
    SRC_LIST = resources{}
    -> AttributeRemover
AttributeRemover
    LIST_ATTRS = resources{}
    -> PythonCaller_3
Note: New Script, Merge Resources from [r'resources_copy',r'res_api',r'advancedViewResources',r'additionalAccessPointsList']
PythonCaller_3
    NEW_ATTRIBUTES = resources{}.name resources{}.url resources{}.format resources{}.name_fr
    PYTHONSOURCE:
      import fme
      import fmeobjects
      logger = fmeobjects.FMELogFile()
      # Template Function interface:
      # When using this function, make sure its name is set as the value of
      # the 'Class or Function to Process Features' transformer parameter
      def processFeature(feature):
          list_list_name=[r'resources_copy',r'res_api',r'advancedViewResources',r'additionalAccessPointsList',r'file_attachment']
          list_attr_name=[r'format',r'url',r'name',r'name_fr']

          i=0





          for list_name in list_list_name:

              #Extracting number of resources
              list_url=feature.getAttribute('%s{}.url'%(list_name))
              if list_url:
                  #Looping in resources
                  for j in range(len(list_url)):
                      #Looping in attributes
                      for attr_name in list_attr_name:
                          feature.setAttribute('resources{%i}.%s'%(i,attr_name),feature.getAttribute('%s{%i}.%s'%(list_name,j,attr_name)))

                      #Changing index feature where new features
                      i=i+1
    PYTHONSYMBOL = processFeature
    -> ListDuplicateRemover_2
Note: Removing dupplicates on URL
ListDuplicateRemover_2
    SRC_LIST = resources{}.url
    -> EMPTY_FORMAT_MAPPER [DATA_INPUT]
EMPTY_FORMAT_MAPPER
    DATA_OUTPUT -> METADATA_VALUE_MAPPER [DATA_INPUT]

Bookmark: Metadata Value Mapping
Note: Role
LOOKUP_TABLES_READER_12
    CSV_ENCODING = utf-8
    CSV_PATH = $(IN_CSV_LOOKUPTABLES_DIR)
    FEATURE_TYPE = Role
    PT = NB
    -> METADATA_VALUE_MAPPER [LOOKUP_TABLE_INPUT]
METADATA_VALUE_MAPPER
    ATT_TO_MAP = contacts{}.role
    CODE_REFRESH = YES
    ENGLISH_REFRESH = YES
    ERROR_NOT_MAPPED = YES
    FRENCH_REFRESH = YES
    -> METADATA_VALUE_MAPPER_2 [DATA_INPUT]
Note: Update
LOOKUP_TABLES_READER_13
    CSV_ENCODING = utf-8
    CSV_PATH = $(IN_CSV_LOOKUPTABLES_DIR)
    FEATURE_TYPE = Update
    PT = NB
    -> METADATA_VALUE_MAPPER_2 [LOOKUP_TABLE_INPUT]
METADATA_VALUE_MAPPER_2
    ATT_TO_MAP = update_frequency
    CODE_REFRESH = YES
    ENGLISH_REFRESH = YES
    ERROR_NOT_MAPPED = YES
    FRENCH_REFRESH = YES
    -> METADATA_VALUE_MAPPER_3 [DATA_INPUT]
Note: Progress
LOOKUP_TABLES_READER_14
    CSV_ENCODING = utf-8
    CSV_PATH = $(IN_CSV_LOOKUPTABLES_DIR)
    FEATURE_TYPE = Progress
    PT = NB
    -> METADATA_VALUE_MAPPER_3 [LOOKUP_TABLE_INPUT]
METADATA_VALUE_MAPPER_3
    ATT_TO_MAP = progress_code
    CODE_REFRESH = YES
    ENGLISH_REFRESH = YES
    ERROR_NOT_MAPPED = YES
    FRENCH_REFRESH = YES
    -> METADATA_VALUE_MAPPER_4 [DATA_INPUT]
Note: SpatialRepresentation
LOOKUP_TABLES_READER_15
    CSV_ENCODING = utf-8
    CSV_PATH = $(IN_CSV_LOOKUPTABLES_DIR)
    FEATURE_TYPE = SpatialRepresentation
    PT = NB
    -> METADATA_VALUE_MAPPER_4 [LOOKUP_TABLE_INPUT]
METADATA_VALUE_MAPPER_4
    ATT_TO_MAP = spatial_representation_type
    CODE_REFRESH = YES
    ENGLISH_REFRESH = YES
    ERROR_NOT_MAPPED = YES
    FRENCH_REFRESH = YES
    -> METADATA_FORMAT_MAPPER [DATA_INPUT]
Note: Format
LOOKUP_TABLES_READER_16
    CSV_ENCODING = utf-8
    CSV_PATH = $(IN_CSV_LOOKUPTABLES_DIR)
    FEATURE_TYPE = Format
    PT = NB
    -> METADATA_FORMAT_MAPPER [LOOKUP_TABLE_INPUT]
METADATA_FORMAT_MAPPER
    ATT_TO_MAP = resources{}.format
    ERROR_NOT_MAPPED = YES
    REAL_VALUE_REFRESH = YES
    RES_TYPE_EN_REFRESH = YES
    RES_TYPE_FR_REFRESH = YES
    -> METADATA_VALUE_MAPPER_ERROR_MANAGER
METADATA_VALUE_MAPPER_ERROR_MANAGER
    ERROR_OUTPUT -> VariableRetriever_11
    DATA_OUTPUT -> AttributeRemover_6
VariableRetriever_11
    SCOPE = Global
    VALUE_ATTR = _timestamp
    VARNAME = _timestamp
    -> ATTRIBUTE_MAPPING_ERRORS (writer XLSXW_1)
ATTRIBUTE_MAPPING_ERRORS (writer XLSXW_1)
    attributes: id string(200), error string(200), _element_index string(200), _timestamp string(200)
Note: Removing error list
AttributeRemover_6
    LIST_ATTRS = mapping_errors{}
    -> RESOURCE_NAME_UNDERSCORE_REMOVER

Bookmark: Remove all underscores from resources{}.name attributes
RESOURCE_NAME_UNDERSCORE_REMOVER
    DATA_OUTPUT -> REMOVE_BROKEN_URL_WMS_ESRI_REST

Bookmark: Drop Broken Web Services
REMOVE_BROKEN_URL_WMS_ESRI_REST
    -> WMS_REST_LANGUAGE_FORMATTER
    FAULTY_URL_OUTPUT -> VariableRetriever_2
VariableRetriever_2
    SCOPE = Global
    VALUE_ATTR = _timestamp
    VARNAME = _timestamp
    -> MAP_SERVICE_URL_ERRORMAP (writer XLSXW_1)
MAP_SERVICE_URL_ERRORMAP (writer XLSXW_1)
    attributes: id string(200), url string(200), format string(200), _url_failure_message string(200), _timestamp string(200)

Bookmark: HNAP RULES
WMS_REST_LANGUAGE_FORMATTER
    -> DUPLICATE_SERVICE_REMOVER
DUPLICATE_SERVICE_REMOVER
    -> GMD_SECTION_DATA_EXTRACTION
GMD_SECTION_DATA_EXTRACTION
    -> PYCSW_URL_MAPPER

Bookmark: New Bookmark
PYCSW_URL_MAPPER
    FORCED_PYCSW_URL = $(FORCED_PYCSW_URL)
    PROVIDER = $(P-T_ABBR)
    -> AttributeExposer_2
AttributeExposer_2
    ATTR_LIST = search_criteria_pycsw
    -> METADATA_DELTA_FINDER
Note: Searches existing PyCSW for new, updated or obsolete data
METADATA_DELTA_FINDER
    ABSTRACT_ATT_NEW = notes
    ABSTRACT_ATT_REF = MD_Metadata.identificationInfo.MD_DataIdentification.abstract.CharacterString
    CSW_FILTER = @Value(search_criteria_pycsw)
    CUSTOM_CSW_CKAN_URL = @Value(csw_url)
    DATESTAMP_ATT_NEW = record_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    -> AttributeExposer
Note: Exposes PyCSW_Transaction attribute
AttributeExposer
    ATTR_LIST = PyCSW_Transaction
    -> AttributeFilter
Note: Filters items by PyCSW transaction type
AttributeFilter
    ATTR_NAME = PyCSW_Transaction
    ATTR_VALUES = <Empty>,<Missing>,<Null>,<Unfiltered>,No change,Update,Insert,Delete
    <EMPTY> -> Terminator
    <MISSING> -> Terminator
    <NULL> -> Terminator
    <UNFILTERED> -> Terminator
    No change -> Tester
    Update -> AWS_TRANSLATE_2
    Insert -> AWS_TRANSLATE_2
    Delete -> AttributeKeeper
Terminator
    MESSAGE = ERROR: Unknown _event value from Metadata_Delta
Note: Selects items with no change for publishing, overwriting all existing data
Tester
    BOOL_OP = OR
    COMPOSITE_TEST = 1
    TEST_CLAUSE = TEST $(PYCSW_OVERWRITE) = YES
    TEST_MODE = TEST
    PASSED -> AttributeCreator
    FAILED -> StatisticsCalculator
Note: Reset to update
AttributeCreator
    ATTR_TABLE = SET_TO PyCSW_Transaction = Update
    -> AWS_TRANSLATE_2
Note: Retains ID for list of deleted items
AttributeKeeper
    KEEP_ATTRS = id
    -> VariableRetriever_9
VariableRetriever_9
    SCOPE = Global
    VALUE_ATTR = _timestamp
    VARNAME = _timestamp
    -> DELETEDRECORDS (writer XLSXW_1)
DELETEDRECORDS (writer XLSXW_1)
    attributes: id string(200), _timestamp string(200)
Creator_2
    GEOMTYPE = Geometry Object
    NUM = 1
    CREATED -> StatisticsCalculator
StatisticsCalculator
    COMPUTE_HISTOGRAM = NO
    COUNT_ATTR = _count
    PREPEND_ATTR_NAME_CHOICE = For multiple results only
    STATS_ATTRS = id
    SUMMARY -> AttributeCreator_2
AttributeCreator_2
    ATTR_TABLE = SET_TO _real_count = @Evaluate(@Value(_count)-1)
    -> StatisticsCalculator_Summary
StatisticsCalculator_Summary: Logger
    LOG_FEATURE = NONE
    MAXFEATS = 20
    MESSAGE:
      ************************
      **** Unchanged Report ****
      ************************

      @Value(_real_count) features were unchanged

      ************************
      ************************
      ************************
    SEVERITY = INFO

Bookmark: AWS Translation
Note: English to french / notes, / title, / tags_en / resources name
AWS_TRANSLATE_2
    ACTIVATE_TRANSLATION = $(ACTIVATE_TRANSLATION)
    ATTR_2_Translate = notes,title
    ATTR_LIST_2_Translate = resources{}.name,tags{}.display_name
    MODE = English-->French
    -> XML_PUBLISHER_2
    -> AWS_TRANSLATE_2_OUTPUT
    TRANSLATION_PROBLEM -> VariableRetriever_5
AWS_TRANSLATE_2_OUTPUT: Inspector
VariableRetriever_5
    SCOPE = Global
    VALUE_ATTR = _timestamp
    VARNAME = _timestamp
    -> Translation_errors (writer XLSXW_1)
Translation_errors (writer XLSXW_1)
    attributes: id string(20), _timestamp string(20)

Bookmark: XML CREATION AND WRITING
Note: Config_NB
LOOKUP_TABLES_READER_11
    CSV_ENCODING = utf-8
    CSV_PATH = $(IN_CSV_LOOKUPTABLES_DIR)
    FEATURE_TYPE = Config_NS
    PT = NS
    -> XML_PUBLISHER_2 [CONFIG_FILE]
XML_PUBLISHER_2
    LOCAL_WRITER = $(LOCAL_WRITER)
    TEMPLATE_GMD_CITEDRESPONSIBLEPARTY = $(IN_GMD_XML_TEMPLATE_DIR)/GMD_CITEDRESPONSIBLEPARTY.xml
    TEMPLATE_GMD_CONTACT = $(IN_GMD_XML_TEMPLATE_DIR)/GMD_CONTACT.xml
    TEMPLATE_GMD_DISTRIBUTIONFORMAT = $(IN_GMD_XML_TEMPLATE_DIR)/GMD_DISTRIBUTIONFORMAT.xml
    TEMPLATE_GMD_DISTRIBUTOR = $(IN_GMD_XML_TEMPLATE_DIR)/GMD_DISTRIBUTOR.xml
    TEMPLATE_GMD_KEYWORDS = $(IN_GMD_XML_TEMPLATE_DIR)/GMD_KEYWORDS.xml
    TEMPLATE_GMD_MDMETADATA = $(IN_GMD_XML_TEMPLATE_DIR)/GMD_MDMETADATA.xml
    TEMPLATE_GMD_REFERENCESYSTEMINFO = $(IN_GMD_XML_TEMPLATE_DIR)/GMD_REFERENCESYSTEMINFO.xml
    TEMPLATE_GMD_RESOURCEMAINTENANCE = $(IN_GMD_XML_TEMPLATE_DIR)/GMD_RESOURCEMAINTENANCE.xml
    TEMPLATE_GMD_TOPICCATEGORY = $(IN_GMD_XML_TEMPLATE_DIR)/GMD_TOPICCATEGORY.xml
    TEMPLATE_GMD_TRANSFEROPTIONS = $(IN_GMD_XML_TEMPLATE_DIR)/GMD_TRANSFEROPTIONS.xml
    LOCAL -> text_line (writer TEXTLINE_3)
    INSERT_PASSED -> text_line (writer TEXTLINE_1)
    INSERT_FAILED -> text_line (writer TEXTLINE_2)
    UPDATE_PASSED -> text_line (writer TEXTLINE_1)
    UPDATE_FAILED -> text_line (writer TEXTLINE_2)
    InvalidMetadata -> VariableRetriever_12

FME custom transformer NB_ADVANCED_VIEW_RESOURCE_MAPPER

Input (input)
    -> AttributeExposer
AttributeExposer
    ATTR_LIST = advancedViewResources{},title,title_fr
    -> UUIDGenerator
UUIDGenerator
    UUID_ATTR = adviewuuid
    -> Tester
Tester
    BOOL_OP = OR
    COMPOSITE_TEST = 1
    TEST_CLAUSE = TEST advancedViewResources{0}.url ATTRIBUTE_HAS_A_VALUE ""
    TEST_MODE = TEST
    PASSED -> AttributeRemover
    PASSED -> AttributeKeeper
    FAILED -> Output (output)
AttributeRemover
    LIST_ATTRS = advancedViewResources{}
    -> FeatureMerger [REQUESTOR]
AttributeKeeper
    KEEP_ATTRS = title,adviewuuid,title_fr
    KEEP_LIST = advancedViewResources{}
    -> ListExploder
ListExploder
    ATTR_ACCUM_MODE = Merge List Attributes
    ATTR_CONFLICT_RES = Use List Attribute Values
    INDEX_ATTR = _element_index
    LIST_ATTR = advancedViewResources{}
    ELEMENTS -> AttributeExposer_2
    <REJECTED> -> Terminator
AttributeExposer_2
    ATTR_LIST = url,format
    -> AttributeCreator
AttributeCreator
    ATTR_TABLE = SET_TO name = @Value(title) - Advanced View
    -> Tester_2
Tester_2
    BOOL_OP = OR
    COMPOSITE_TEST = 1
    TEST_CLAUSE = TEST title_fr ATTRIBUTE_HAS_A_VALUE ""
    TEST_MODE = TEST
    PASSED -> AttributeCreator_4
    FAILED -> AttributeCreator_3
AttributeCreator_4
    ATTR_TABLE = SET_TO name_fr = @Value(title_fr) - vue avancée
    -> AttributeKeeper_2
AttributeCreator_3
    ATTR_TABLE = SET_TO name_fr = FME_NULL_VALUE
    -> AttributeKeeper_2
AttributeKeeper_2
    KEEP_ATTRS = name,format,url,name_fr,adviewuuid
    -> FeatureMerger [SUPPLIER]
FeatureMerger
    ATTR_ACCUM_MODE = Merge Supplier
    ATTR_CONFLICT_RES = Use Requestor
    IGNORE_NULLS = No
    JOIN_KEYS = @Value(adviewuuid) @Value(adviewuuid) AUTO
    LIST_ATTRS_TO_INCLUDE = format name name_fr url
    LIST_NAME = advancedViewResources
    MERGE_TYPE = Attributes Only
    PROCESS_DUPS = NO
    REJECT_NULL_MISSING_KEYS = No
    SUPPLIERS_FIRST = No
    MERGED -> Output (output)
Output (output)
Terminator
    MESSAGE = Translation Terminated

FME custom transformer NB_AttachementManager

Parameters:
- SBN_URL_ROOT =

Input (input)
    -> AttributeExposer_4
AttributeExposer_4
    ATTR_LIST = metadata.attachments{}.assetId,metadata.attachments{}.filename,metadata.attachments{}.name,resource.id
    -> UUIDGenerator
UUIDGenerator
    UUID_ATTR = _uuid_attachement
    -> ListExploder
    -> FeatureMerger [REQUESTOR]
ListBuilder
    GROUP_BY = _uuid_attachement
    LIST_ATTRS_TO_INCLUDE = format name protocol url
    LIST_NAME = file_attachment
    -> FeatureMerger [SUPPLIER]
FeatureMerger
    ATTR_ACCUM_MODE = Merge Supplier
    ATTR_CONFLICT_RES = Use Requestor
    IGNORE_NULLS = No
    JOIN_KEYS = @Value(_uuid_attachement) @Value(_uuid_attachement) AUTO
    MERGE_TYPE = Attributes Only
    PROCESS_DUPS = NO
    REJECT_NULL_MISSING_KEYS = No
    SUPPLIERS_FIRST = No
    MERGED -> AttributeRemover
    UNMERGED_REQUESTOR -> AttributeRemover
    UNUSED_SUPPLIER -> Terminator
    <REJECTED> -> Terminator
AttributeRemover
    REMOVE_ATTRS = _uuid_attachement
    -> Output (output)
Output (output)
Terminator
    MESSAGE = Translation Terminated
HTTPCaller_Output: Inspector

Bookmark: Creating file_attachment list bases on metadata attachement section.
ListExploder
    ATTR_ACCUM_MODE = Merge List Attributes
    ATTR_CONFLICT_RES = Use List Attribute Values
    INDEX_ATTR = _element_index
    LIST_ATTR = metadata.attachments{}
    ELEMENTS -> TextEncoder
    <REJECTED> -> Cloner
Note: Enconding filename in URL to avoid issues with accents and spaces
TextEncoder
    DEST_ATTR = filename
    ENCODING_TYPE = URL_ENCODE
    STRING_TO_ENCODE = @Value(filename)
    -> AttributeCreator
Note: Defining attributes. / Format blank
AttributeCreator
    ATTR_TABLE:
      SET_TO url = $(SBN_URL_ROOT)/api/views/@Value(resource.id)/files/@Value(assetId)?download=true&filename=@Value(filename)
      SET_TO name = @Value(name)
      SET_TO format
      SET_TO protocol = HTTPS
    -> HTTPCaller
HTTPCaller
    CONNECTION_TIMEOUT_LENGTH = 60
    ERROR_ATTR = _error
    FOLLOW_REDIRECTS = Yes
    HTTP_METHOD = OPTIONS
    SAVE_FILE = Attribute
    STATUS_CODE_ATTR = _http_status_code
    TARGET_ATTR = _response_body
    TARGET_ATTR_ENCODING = auto-detect
    TARGET_URL = @Value(url)
    TRANSFER_TIMEOUT_LENGTH = 90
    USE_COOKIES = No
    VERIFY_SSL_CERTIFICATES = No
    -> ListBuilder
    -> HTTPCaller_Output
    <REJECTED> -> Cloner_2
Cloner_2
    COPIES = 1
    COPYATT = _copynum
Cloner
    COPIES = 1
    COPYATT = _copynum

FME custom transformer NB_HREF_RESOURCES_EXTRACTOR

AttributeExposer_Input (input)
    -> AttributeExposer
AttributeExposer
    ATTR_LIST = metadata.additionalAccessPoints{}.title
    -> ListElementCounter
ListElementCounter
    CNT_ATTR = _element_count
    LIST_NAME = metadata.additionalAccessPoints{}
    -> Tester
Tester
    BOOL_OP = OR
    COMPOSITE_TEST = 1
    TEST_CLAUSE = TEST @Value(_element_count) != 0
    TEST_MODE = TEST
    PASSED -> UUIDGenerator
    PASSED -> Tester_Passed
    FAILED -> Output (output)
UUIDGenerator
    UUID_ATTR = _uuid_href
    -> AttributeKeeper
    -> AttributeRemover
AttributeRemover
    LIST_ATTRS = metadata.additionalAccessPoints{}
    -> FeatureMerger_3 [REQUESTOR]
AttributeKeeper
    KEEP_ATTRS = _uuid_href
    KEEP_LIST = metadata.additionalAccessPoints{}
    -> ListExploder_2
    -> AttributeKeeper_Output
AttributeKeeper_Output: Inspector
ListExploder_2
    ATTR_ACCUM_MODE = Merge List Attributes
    ATTR_CONFLICT_RES = Use List Attribute Values
    INDEX_ATTR = _element_index
    LIST_ATTR = metadata.additionalAccessPoints{}
    ELEMENTS -> AttributeExploder
AttributeExploder
    ATTR_NAME_LABEL = attName
    ATTR_VALUE_LABEL = attVal
    EXPLODING_TYPE = List
    KEEP_ATTRIBUTES = Yes
    KEEP_GEOMETRY = No
    LIST_NAME = attList
    -> ListSearcher
ListSearcher
    ATTR_VALUE = urls
    INDEX_ATTR = _list_index
    LIST_ATTR = attList{}.attName
    MATCHTYPE = REGULAR_EXPRESSION_ENCODED
    PREFIX = _goodindex
    FOUND -> AttributeCreator
AttributeCreator
    ATTR_TABLE = SET_TO url = @Value(_goodindexattVal)
    -> AttributeSplitter
AttributeSplitter
    ATTR_NAME = title
    DELIMITER = /
    DROP_EMPTY_PARTS = No
    LIST_NAME = _list_title
    TRIM_OPTION = Both
    -> AttributeCreator_2
AttributeCreator_2
    ATTR_TABLE:
      SET_TO name = @Value(_list_title{0})
      SET_TO name_fr = @Value(_list_title{1})
    -> Tester_3
Tester_3
    BOOL_OP = OR
    COMPOSITE_TEST = 1
    TEST_CLAUSE = TEST @Value(url) != ""
    TEST_MODE = TEST
    PASSED -> Tester_2
Tester_2
    BOOL_OP = OR
    COMPOSITE_TEST = 1
    TEST_CLAUSE = CASE_INSENSITIVE_TEST @Value(url) CONTAINS maps.arcgis.com
    TEST_MODE = TEST
    PASSED -> AttributeCreator_3
    FAILED -> AttributeKeeper_2
AttributeCreator_3
    ATTR_TABLE = SET_TO format = Web App
    -> AttributeKeeper_2
AttributeKeeper_2
    KEEP_ATTRS = url,name,name_fr,format,_uuid_href
    -> FeatureMerger_3 [SUPPLIER]
    -> AttributeKeeper_2_Output
FeatureMerger_3
    ATTR_ACCUM_MODE = Merge Supplier
    ATTR_CONFLICT_RES = Use Requestor
    IGNORE_NULLS = No
    JOIN_KEYS = @Value(_uuid_href) @Value(_uuid_href) AUTO
    LIST_ATTRS_TO_INCLUDE = format name name_fr url
    LIST_NAME = additionalAccessPointsList
    MERGE_TYPE = Attributes Only
    PROCESS_DUPS = NO
    REJECT_NULL_MISSING_KEYS = No
    SUPPLIERS_FIRST = No
    MERGED -> AttributeRemover_2
    UNMERGED_REQUESTOR -> AttributeRemover_2
AttributeRemover_2
    REMOVE_ATTRS = _element_count,_uuid_href
    -> Output (output)
Output (output)
AttributeKeeper_2_Output: Inspector
Tester_Passed: Inspector

FME custom transformer NB_MetadataMerger

Input (input)
    -> AttributeExposer_2
Note: Exposing ID and resource.type
AttributeExposer_2
    ATTR_LIST = resource.type,id,modifyingViewUid
    -> Tester
    -> FeatureMerger [REQUESTOR]
    -> AttributeExploder
Note: Creating attributes to be part of resource{} list
AttributeCreator_6
    ATTR_TABLE:
      SET_TO url = https://gnb.socrata.com/datasets/@Value(id)
      SET_TO format = HTML
    -> AttributeKeeper_5
AttributeKeeper_5
    KEEP_ATTRS = name,url,protocol,format,resourceType_fr,_seriesID,resourceType_en
    -> FeatureMerger_2 [SUPPLIER]
    -> AttributKeeper_5_Recorder
AttributKeeper_5_Recorder: Recorder
    COMPRESSION_LEVEL = 6
    CREATE_SPATIAL_INDEX = No
    MODE = RECORD_PASS_THROUGH
    RECFILE = C:\DavidH\NRCan\Data\PT_Harvest\NB\NB_MetadataMerger_AttributKeeper_5_Recorder.ffs
    STORE_SCANNED_METADATA = No
    STORE_SCANNED_SCHEMA = No
DuplicateFilter_2
    INPUT_ORDERED_CHOICE = No
    KEYATTR = id
    UNIQUE -> FeatureMerger [SUPPLIER]
Note: Removing from original record those considaret as an Advanced View of a dataset
FeatureMerger
    ATTR_ACCUM_MODE = Merge Supplier
    ATTR_CONFLICT_RES = Use Requestor
    IGNORE_NULLS = No
    JOIN_KEYS = @Value(id) @Value(id) AUTO
    MERGE_TYPE = Attributes Only
    PROCESS_DUPS = NO
    REJECT_NULL_MISSING_KEYS = No
    SUPPLIERS_FIRST = No
    UNMERGED_REQUESTOR -> FeatureMerger_2 [REQUESTOR]
    UNUSED_SUPPLIER -> Terminator
    <REJECTED> -> Terminator
Note: Transfering additional view to original resource
FeatureMerger_2
    ATTR_ACCUM_MODE = Merge Supplier
    ATTR_CONFLICT_RES = Use Requestor
    IGNORE_NULLS = No
    JOIN_KEYS = @Value(id) @Value(_seriesID) AUTO
    LIST_ATTRS_TO_INCLUDE = format url
    LIST_NAME = advancedViewResources
    MERGE_TYPE = Attributes Only
    PROCESS_DUPS = NO
    REJECT_NULL_MISSING_KEYS = No
    SUPPLIERS_FIRST = No
    MERGED -> Output (output)
    UNMERGED_REQUESTOR -> Output (output)
    UNUSED_SUPPLIER -> UnmergedAdvancedView (output)
    <REJECTED> -> Terminator_2
Output (output)
UnmergedAdvancedView (output)
Terminator_2
    MESSAGE = Translation Terminated
Terminator
    MESSAGE = Translation Terminated

Bookmark: Searching for source dataset in JSON attributes
Tester
    BOOL_OP = OR
    COMPOSITE_TEST = 1
    TEST_CLAUSE = TEST @Value(modifyingViewUid) != ""
    TEST_MODE = TEST
    PASSED -> AttributeRenamer
AttributeRenamer
    ATTR_TABLE = RENAME_SET_DEFAULT modifyingViewUid > _seriesID
    -> DuplicateFilter
    -> DuplicateFilter_2
Note: Exploding attributes to avoid list parser / 1 feature per attribute
AttributeExploder
    ATTR_NAME_LABEL = _attr_name
    ATTR_VALUE_LABEL = _seriesID
    EXPLODING_TYPE = Features
    KEEP_ATTRIBUTES = Yes
    KEEP_GEOMETRY = No
    -> AttributeKeeper_4
Note: Cleanup
AttributeKeeper_4
    KEEP_ATTRS = _seriesID,id,resource.type,_attr_name
    -> StringReplacer
Note: RegEx to remove list / {} in attribute name
StringReplacer
    CASE = NO
    FIND_TEXT = {[0-9]+}
    NO_MATCH = _FME_NO_OP_
    REGEXP = YES
    SRC_ATTRS = _attr_name
    -> Tester_7
Note: Only feature regarding / series.dataSource.datasetUid
Tester_7
    BOOL_OP = OR
    COMPOSITE_TEST = 1
    TEST_CLAUSE = TEST @Value(_attr_name) = displayFormat.visualizationCanvasMetadata.vifs.series.dataSource.datasetUid
    TEST_MODE = TEST
    PASSED -> DuplicateFilter_2
    PASSED -> DuplicateFilter
Note: Removing duplicates / based on / ID, restype,series source
Note: 1 feature by ID
DuplicateFilter
    INPUT_ORDERED_CHOICE = No
    KEYATTR = _seriesID id resource.type
    UNIQUE -> AttributeCreator_6

FME custom transformer SOCRATA_RESOURCE_MAPPER

Parameters:
- DOMAIN = https://data.novascotia.ca

INPUT (input)
    -> AttributeExposer_2
AttributeExposer_2
    ATTR_LIST = resource.id,dataLayers{},title,title_fr,dataLayers{0}.geomcol,dataLayers{0}.geomtype,dataLayers{0}.layerid,columns{},global_list_attribute_type{}.geo
    -> ListElementCounter
ListElementCounter
    CNT_ATTR = _element_count
    LIST_NAME = columns{}
    -> Tester_4
linkbuilder_geo (input)
    -> AttributeExposer_7

Bookmark: NB_RESOURCES_MAPPER
Tester_4
    BOOL_OP = OR
    COMPOSITE_TEST = 1
    TEST_CLAUSE = TEST @Value(_element_count) = 0
    TEST_MODE = TEST
    PASSED -> OUTPUT (output)
    FAILED -> UUIDGenerator_2
UUIDGenerator_2
    UUID_ATTR = uuidjoinkey
    -> FeatureMerger_2 [REQUESTOR]
    -> ListSearcher
    -> FeatureMerger_4 [REQUESTOR]
ListSearcher
    ATTR_VALUE = Yes
    INDEX_ATTR = _list_index
    LIST_ATTR = global_list_attribute_type{}.geo
    MATCHTYPE = FIRST_MATCHED_ENCODED
    FOUND -> AttributeKeeper_4
AttributeKeeper_4
    KEEP_ATTRS = uuidjoinkey,title,resource.id,title_fr
    -> FeatureMerger [REQUESTOR]
AttributeExposer_7
    ATTR_LIST = format,url,titlepart
    -> FeatureMerger [SUPPLIER]
FeatureMerger
    ATTR_ACCUM_MODE = Merge Supplier
    ATTR_CONFLICT_RES = Use Requestor
    IGNORE_NULLS = No
    JOIN_KEYS = 1 1 AUTO
    LIST_ATTRS_TO_INCLUDE = format titlepart url
    LIST_NAME = georesources
    MERGE_TYPE = Attributes Only
    PROCESS_DUPS = NO
    REJECT_NULL_MISSING_KEYS = No
    SUPPLIERS_FIRST = No
    MERGED -> ListExploder_5
ListExploder_5
    ATTR_ACCUM_MODE = Merge List Attributes
    ATTR_CONFLICT_RES = Use List Attribute Values
    INDEX_ATTR = _element_index
    LIST_ATTR = georesources{}
    ELEMENTS -> StringReplacer_4
StringReplacer_4
    CASE = NO
    FIND_TEXT = ($DOMAIN$)
    NO_MATCH = _FME_NO_OP_
    REGEXP = NO
    REPLACE_TEXT = $(DOMAIN)
    SRC_ATTRS = url
    -> StringReplacer_3
StringReplacer_3
    CASE = NO
    FIND_TEXT = ($ID$)
    NO_MATCH = _FME_NO_OP_
    REGEXP = NO
    REPLACE_TEXT = @Value(resource.id)
    SRC_ATTRS = url
    -> AttributeKeeper
LinkBuilderNonGeo (input)
    -> AttributeExposer_5
AttributeExposer_5
    ATTR_LIST = format,url,titlepart
    -> FeatureMerger_4 [SUPPLIER]
FeatureMerger_4
    ATTR_ACCUM_MODE = Merge Supplier
    ATTR_CONFLICT_RES = Use Requestor
    IGNORE_NULLS = No
    JOIN_KEYS = 1 1 AUTO
    LIST_ATTRS_TO_INCLUDE = format titlepart url
    LIST_NAME = nongeoresources
    MERGE_TYPE = Attributes Only
    PROCESS_DUPS = NO
    REJECT_NULL_MISSING_KEYS = No
    SUPPLIERS_FIRST = No
    MERGED -> ListExploder
ListExploder
    ATTR_ACCUM_MODE = Merge List Attributes
    ATTR_CONFLICT_RES = Use List Attribute Values
    INDEX_ATTR = ignoreindex
    LIST_ATTR = nongeoresources{}
    ELEMENTS -> StringReplacer
StringReplacer
    CASE = NO
    FIND_TEXT = ($DOMAIN$)
    NO_MATCH = _FME_NO_OP_
    REGEXP = NO
    REPLACE_TEXT = $(DOMAIN)
    SRC_ATTRS = url
    -> StringReplacer_2
StringReplacer_2
    CASE = NO
    FIND_TEXT = ($trueid$)
    NO_MATCH = _FME_NO_OP_
    REGEXP = NO
    REPLACE_TEXT = @Value(resource.id)
    SRC_ATTRS = url
    -> AttributeKeeper
AttributeKeeper
    KEEP_ATTRS = title,format,title_fr,url,uuidjoinkey,titlepart
    -> AttributeCreator_10
AttributeCreator_10
    ATTR_TABLE = SET_TO name = @Value(title) (@Value(titlepart))
    -> Tester
Tester
    BOOL_OP = OR
    COMPOSITE_TEST = 1
    TEST_CLAUSE = TEST @Value(title_fr) != ""
    TEST_MODE = TEST
    PASSED -> AttributeCreator_2
    FAILED -> AttributeKeeper_5
AttributeCreator_2
    ATTR_TABLE = SET_TO name_fr = @Value(title_fr) (@Value(titlepart))
    -> AttributeKeeper_5
AttributeKeeper_5
    KEEP_ATTRS = name,format,name_fr,url,uuidjoinkey
    -> HTTPCaller
    -> PythonCaller
PythonCaller
    NEW_ATTRIBUTES = url_status_code
    PYTHONSOURCE:
      import fme
      import fmeobjects
      import requests
      # Template Function interface:
      # When using this function, make sure its name is set as the value of
      # the 'Class or Function to Process Features' transformer parameter
      def processFeature(feature):
          with requests.get(feature.getAttribute('url'), stream=True,verify=False) as r:
              feature.setAttribute('url_status_code',r.status_code)


      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> Tester_2
Tester_2
    BOOL_OP = OR
    COMPOSITE_TEST = 1
    TEST_CLAUSE = CASE_SENSITIVE_TEST @Value(url_status_code) CONTAINS_REGEX 2[0-9][0-9]
    TEST_MODE = CASE_SENSITIVE_TEST
    PASSED -> Tester_2_Passed
    PASSED -> FeatureMerger_2 [SUPPLIER]
    FAILED -> Tester_2_Failed
FeatureMerger_2
    ATTR_ACCUM_MODE = Merge Supplier
    ATTR_CONFLICT_RES = Use Requestor
    IGNORE_NULLS = No
    JOIN_KEYS = @Value(uuidjoinkey) @Value(uuidjoinkey) AUTO
    LIST_ATTRS_TO_INCLUDE = format name url name_fr
    LIST_NAME = res_api
    MERGE_TYPE = Attributes Only
    PROCESS_DUPS = NO
    REJECT_NULL_MISSING_KEYS = No
    SUPPLIERS_FIRST = No
    MERGED -> OUTPUT (output)
    UNMERGED_REQUESTOR -> OUTPUT (output)
OUTPUT (output)
Tester_2_Passed: Inspector
Tester_2_Failed: Inspector
HTTPCaller
    CONNECTION_TIMEOUT_LENGTH = 60
    ERROR_ATTR = _error
    FOLLOW_REDIRECTS = Yes
    HTTP_METHOD = OPTIONS
    SAVE_FILE = Attribute
    STATUS_CODE_ATTR = _http_status_code
    TARGET_ATTR = _response_body
    TARGET_ATTR_ENCODING = auto-detect
    TARGET_URL = @Value(url)
    TRANSFER_TIMEOUT_LENGTH = 90
    USE_COOKIES = No
    VERIFY_SSL_CERTIFICATES = No
    <REJECTED> -> Cloner
Cloner
    COPIES = 1
    COPYATT = _copynum

FME custom transformer GeospatialFilter_AttributeType

Parameters:
- LIST_NAME =   # " " List Attribute
- ATTR_NAME_ATTR_TYPE =

AttributeType (input)
    -> AttributeExposer
AttributeExposer
    ATTR_LIST = attribute_type,geo,spatial_type
    -> Tester
Tester
    BOOL_OP = AND
    COMPOSITE_TEST = 1 AND 2
    TEST_CLAUSE:
      TEST @Value(attribute_type) != ""
      TEST @Value(geo) != ""
    TEST_MODE = TEST
    PASSED -> AttributeCreator
AttributeCreator
    ATTR_TABLE = SET_TO _ordre = 1
    -> Sorter
Input (input)
    -> ListElementCounter
ListElementCounter
    CNT_ATTR = _element_count
    LIST_NAME = $(LIST_NAME)
    -> AttributeCreator_2
AttributeCreator_2
    ATTR_TABLE:
      SET_TO _ordre = 2
      SET_TO att_name = $(ATTR_NAME_ATTR_TYPE)
      SET_TO list_name = $(LIST_NAME)
    -> Sampler_Sampled
    -> Tester_4
Sampler_Sampled: Inspector
Tester_4
    BOOL_OP = OR
    COMPOSITE_TEST = 1
    TEST_CLAUSE = TEST @Value(_element_count) != 0
    TEST_MODE = TEST
    PASSED -> Sorter
    FAILED -> NonGeospatial (output)
Sorter
    SORT_PARM = _ordre NUMERIC ASCENDING
    SORTED -> PythonCaller_4
PythonCaller_4
    NEW_ATTRIBUTES = attr_type_not_map{}
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              self.dict={}

          def input(self,feature):
              #Identifier le type feature
              if feature.getAttribute('_ordre')==1:
                  #On est dans la définition du dictionnaire:
                  attr_type=feature.getAttribute('attribute_type')
                  geo=feature.getAttribute('geo').lower()
                  stype=feature.getAttribute('spatial_type')


                  if not attr_type in self.dict.keys():
                      #Ajouter l'élément dans le dictionnaire
                      #print(attr_type)
                      self.dict[attr_type]={'geo':geo,'stype':stype}

                  else:

                      raise 'Presence de doublon dans le fichier de config'
              elif  feature.getAttribute('_ordre')==2:

                  list_name=feature.getAttribute('list_name').replace('{}','')
                  attr_name=feature.getAttribute('att_name')

                  attr_not_mapped=[]
                  for i in range(int(feature.getAttribute('_element_count'))):


                      fattr_type=feature.getAttribute('%s{%i}.%s'%(list_name,i,attr_name))


                      if not fattr_type in self.dict.keys():
                          attr_not_mapped.append(fattr_type)
                      else:
                          feature.setAttribute('%s{%i}.%s'%(list_name,i,'geo'),self.dict[fattr_type]['geo'])
                          feature.setAttribute('%s{%i}.%s'%(list_name,i,'spatial_type'),self.dict[fattr_type]['stype'])

                  if attr_not_mapped:
                      feature.setAttribute('attr_type_not_map',attr_not_mapped)
                  self.pyoutput(feature)


              else:
                  raise 'erreur dans le code python'



          def close(self):
              pass
    PYTHONSYMBOL = FeatureProcessor
    -> Tester_2
Tester_2
    BOOL_OP = OR
    COMPOSITE_TEST = 1
    TEST_CLAUSE = TEST @Value(attr_type_not_map{0}) = ""
    TEST_MODE = TEST
    PASSED -> PythonCaller
    FAILED -> ListExploder
PythonCaller
    NEW_ATTRIBUTES = _contains_geo
    PYTHONSOURCE:
      import fme
      import fmeobjects
      # Template Function interface:
      # When using this function, make sure its name is set as the value of
      # the 'Class or Function to Process Features' transformer parameter
      def processFeature(feature):
          list=feature.getAttribute('%s.geo'%(feature.getAttribute('list_name')))
          if 'yes' in list:
              feature.setAttribute('_contains_geo','yes')
          else:
              feature.setAttribute('_contains_geo','no')



          pass

      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> Tester_3
Tester_3
    BOOL_OP = OR
    COMPOSITE_TEST = 1
    TEST_CLAUSE = TEST @Value(_contains_geo) = yes
    TEST_MODE = TEST
    PASSED -> Geospatial (output)
    FAILED -> NonGeospatial (output)
Geospatial (output)
NonGeospatial (output)
ListExploder
    ATTR_ACCUM_MODE = Merge List Attributes
    ATTR_CONFLICT_RES = Use List Attribute Values
    INDEX_ATTR = _element_index
    LIST_ATTR = attr_type_not_map{}
    ELEMENTS -> DuplicateFilter
    <REJECTED> -> Terminator
DuplicateFilter
    INPUT_ORDERED_CHOICE = No
    KEYATTR = attr_type_not_map
    UNIQUE -> Unknown_attr_type (output)
Unknown_attr_type (output)
Terminator
    MESSAGE = Translation Terminated

FME custom transformer GEOPORTAL_WEBLINK_ADDER

Parameters:
- WEBLINK_WILDCARD =

LOOKUP_TABLE_INPUT (input)
    -> AttributeExposer
INPUT (input)
    -> AttributeExposer_2
OUTPUT (output)

Bookmark: New Bookmark
AttributeExposer
    ATTR_LIST = default_key,default_value
    -> AttributeKeeper
AttributeKeeper
    KEEP_ATTRS = default_value,default_key
    -> AttributeCreator_3
Note: Each default key attribute is turned into an individual attribute
AttributeCreator_3
    ATTR_TABLE = SET_TO @Value(default_key) = @Value(default_value)
    -> FEATURE_MERGER [SUPPLIER]
Note: Exposes attributes required by this transformer
Note: This custom transformer merges an Excel file containing default attribute values common to each dataset
AttributeExposer_2
    ATTR_LIST = resources{},name,id
    -> ListElementCounter
Note: Counts number of elements in dataset
ListElementCounter
    CNT_ATTR = _element_count_res
    LIST_NAME = resources{}
    -> FEATURE_MERGER [REQUESTOR]
Note: Default attributes are merged with each dataset
FEATURE_MERGER: FeatureMerger
    ATTR_ACCUM_MODE = Merge Supplier
    ATTR_CONFLICT_RES = Use Supplier
    CLEANING_TOLERANCE = None
    CONNECT_Z_MODE = First Wins
    GEOM_TYPE = Build Polygons
    IGNORE_NULLS = No
    JOIN_KEYS = 1 1 AUTO
    MERGE_TYPE = Attributes Only
    PROCESS_DUPS = YES
    REJECT_NULL_MISSING_KEYS = Yes
    SUPPLIERS_FIRST = No
    MERGED -> AttributeExposer_3
    UNMERGED_REQUESTOR -> Terminator_3
    <REJECTED> -> Terminator_3
Note: Exposes data from lookup table
AttributeExposer_3
    ATTR_LIST = resources_format,resources_name,resources_protocol,resources_url,resources_format_resourceType_en,resources_format_resourceType_fr,resources_transfer_option_description_language,resources_transfer_option_description_language_other_lang,resources_xlink_role
    -> AttributeCreator_5
Note: Creating URL which contains url to add
AttributeCreator_5
    ATTR_TABLE = SET_TO test_url = @Value(resources_url)/$(WEBLINK_WILDCARD)
    -> AttributeTrimmer
Note: Trimming / , if no values in root url
AttributeTrimmer
    SRC_ATTRS = test_url
    TRIM_CHARS = /
    TRIM_TO_NONE = Yes
    TRIM_TYPE = Left
    -> HTTPCaller [off]
    -> AttributeCreator_4
Note: Test URL connectivity. Only successful connections will proceed through the output port
HTTPCaller
    CONNECTION_TIMEOUT_LENGTH = 60
    ERROR_ATTR = _error
    FOLLOW_REDIRECTS = Yes
    HTTP_METHOD = OPTIONS
    SAVE_FILE = Attribute
    STATUS_CODE_ATTR = _http_status_code
    TARGET_ATTR = _response_body
    TARGET_ATTR_ENCODING = auto-detect
    TARGET_URL = @Value(test_url)
    TRANSFER_TIMEOUT_LENGTH = 90
    USE_COOKIES = No
    VERIFY_SSL_CERTIFICATES = No
    -> AttributeCreator_4
    <REJECTED> -> HTTPCaller_2
Note: Test URL connectivity. Only successful connections will proceed through the output port
HTTPCaller_2
    CONNECTION_TIMEOUT_LENGTH = 60
    ERROR_ATTR = _error
    FOLLOW_REDIRECTS = Yes
    HTTP_METHOD = HEAD
    SAVE_FILE = Attribute
    STATUS_CODE_ATTR = _http_status_code
    TARGET_ATTR = _response_body
    TARGET_ATTR_ENCODING = auto-detect
    TARGET_URL = @Value(test_url)
    TRANSFER_TIMEOUT_LENGTH = 90
    USE_COOKIES = No
    VERIFY_SSL_CERTIFICATES = No
    -> AttributeCreator_4
    <REJECTED> -> Tester
Note: Creates additional entry in resources{} list based upon element count and adds required elements from lookup table data. Concatenate URL to Geoportal Weblink
AttributeCreator_4
    ATTR_TABLE:
      SET_TO resources{@Value(_element_count_res)}.format = @Value(resources_format)
      SET_TO resources{@Value(_element_count_res)}.name = @Value(resources_name)
      SET_TO resources{@Value(_element_count_res)}.protocol = @Value(resources_protocol)
      SET_TO resources{@Value(_element_count_res)}.url = @Value(test_url)
      SET_TO resources{@Value(_element_count_res)}.format_resourceType_en = @Value(resources_format_resourceType_en)
      SET_TO resources{@Value(_element_count_res)}.format_resourceType_fr = @Value(resources_format_resourceType_fr)
      SET_TO resources{@Value(_element_count_res)}.transfer_option_description_language = @Value(resources_transfer_option_description_language)
      SET_TO resources{@Value(_element_count_res)}.transfer_option_description_language_other_lang = @Value(resources_transfer_option_description_language_other_lang)
      SET_TO resources{@Value(_element_count_res)}.xlink_role
    -> AttributeRemover
AttributeRemover
    REMOVE_ATTRS = resources_format_resourceType_fr,resources_format_resourceType_en,resources_protocol,default_key,resources_transfer_option_description_language,resources_name,resources_format,default_value,resources_xlink_role,test_url,resources_transfer_option_description_language_other_lang,resources_url
    -> OUTPUT (output)
Terminator_3
    MESSAGE = Feature Merger error: Translation Terminated

Bookmark: Error code handling
Note: Tests for error code 400
Tester
    BOOL_OP = OR
    COMPOSITE_TEST = 1
    TEST_CLAUSE = TEST @Value(_http_status_code) = 400
    TEST_MODE = TEST
    PASSED -> Logger
    FAILED -> Tester_2
Note: Logs 400 error code
Logger
    LOG_FEATURE = LOG_RECORD
    MAXCOORDS = 20
    MAXFEATS = 20
    MESSAGE = Error Code 400: Bad request by client.  Verify URL syntax.  BC Geoportal Weblink not created.
    SEVERITY = WARN
    LOGGED -> AttributeRemover
Note: Tests for other 4xx error codes. Failed port outputs 5xx error codes by default
Tester_2
    BOOL_OP = AND
    TEST_CLAUSE:
      TEST @Value(_http_status_code) > 400
      TEST @Value(_http_status_code) < 500
    TEST_MODE = TEST
    PASSED -> Logger_2
    FAILED -> Logger_3
Note: Logs 4xx error code
Logger_2
    LOG_FEATURE = LOG_RECORD
    MAXCOORDS = 20
    MAXFEATS = 20
    MESSAGE = Client side error.  Status code @Value(_http_status_code).   BC Geoportal Weblink not created.
    SEVERITY = WARN
    LOGGED -> AttributeRemover
Note: Logs 5xx error code
Logger_3
    LOG_FEATURE = LOG_RECORD
    MAXCOORDS = 20
    MAXFEATS = 20
    MESSAGE = Server side error.  Status code @Value(_http_status_code).   BC Geoportal Weblink not created.
    SEVERITY = WARN
    LOGGED -> AttributeRemover

FME custom transformer ChildViewAttributeTypeExtractor

Parameters:
- DOMAIN =

Input (input)
    -> AttributeExposer_4
AttributeExposer_4
    ATTR_LIST = childViews{}
    -> UUIDGenerator_4
UUIDGenerator_4
    UUID_ATTR = _uuid
    -> Tester_2
    -> FeatureMerger_6 [REQUESTOR]
Tester_2
    BOOL_OP = OR
    COMPOSITE_TEST = 1
    TEST_CLAUSE = TEST childViews{0} ATTRIBUTE_HAS_A_VALUE ""
    TEST_MODE = TEST
    PASSED -> AttributeKeeper_5
AttributeKeeper_5
    KEEP_ATTRS = datatypes_concat,_uuid
    KEEP_LIST = childViews{}
    -> ListExploder_5
ListExploder_5
    ATTR_ACCUM_MODE = Merge List Attributes
    ATTR_CONFLICT_RES = Use List Attribute Values
    INDEX_ATTR = _element_index
    LIST_ATTR = childViews{}
    ELEMENTS -> HTTPCaller_7
    <REJECTED> -> Terminator
HTTPCaller_7
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body2
    TARGET_ATTR_ENCODING = auto-detect
    TARGET_URL = $(DOMAIN)/api/views/@Value(childViews).json
    TRANSFER_TIMEOUT_LENGTH = 90
    USE_COOKIES = No
    VERIFY_SSL_CERTIFICATES = No
    -> JSONFlattener_5
    <REJECTED> -> Cloner
JSONFlattener_5
    ERROR_LIST_ATTR = _json_error
    JSON_DOCUMENT = @Value(_response_body2)
    READ_FROM_FILE = NO
    RECURSIVE = Yes
    -> AttributeExposer_11
    <REJECTED> -> Cloner
AttributeExposer_11
    ATTR_LIST = columns{}.fieldName,columns{}.dataTypeName,name
    -> ListExploder
ListExploder
    ATTR_ACCUM_MODE = Merge List Attributes
    ATTR_CONFLICT_RES = Use List Attribute Values
    INDEX_ATTR = _element_index
    LIST_ATTR = columns{}
    ELEMENTS -> AttributeCreator
AttributeCreator
    ATTR_TABLE = SET_TO layerid = @Value(childViews)
    -> ListBuilder
Note: Création de la liste contenant les noms des attributes, leur type ainsi que la couche à laquelle ils sont reliés
ListBuilder
    GROUP_BY = _uuid
    LIST_ATTRS_TO_INCLUDE = dataTypeName fieldName layerid
    LIST_NAME = AttributeTypeChildView
    -> AttributeKeeper_4
AttributeKeeper_4
    KEEP_ATTRS = _uuid
    KEEP_LIST = AttributeTypeChildView{}
    -> FeatureMerger_6 [SUPPLIER]
FeatureMerger_6
    ATTR_ACCUM_MODE = Merge Supplier
    ATTR_CONFLICT_RES = Use Requestor
    IGNORE_NULLS = No
    JOIN_KEYS = @Value(_uuid) @Value(_uuid) AUTO
    MERGE_TYPE = Attributes Only
    PROCESS_DUPS = NO
    REJECT_NULL_MISSING_KEYS = No
    SUPPLIERS_FIRST = No
    MERGED -> Output (output)
    MERGED -> FeatureMerger_6_Merged
    UNMERGED_REQUESTOR -> Output (output)
    UNUSED_SUPPLIER -> Terminator_2
FeatureMerger_6_Merged: Inspector
Output (output)
Terminator_2
    MESSAGE = Translation Terminated
Cloner
    COPIES = 1
    COPYATT = _copynum
Terminator
    MESSAGE = Translation Terminated

FME custom transformer SPATIAL_TYPE_MAPPER

Parameters:
- FEATURE_LIST_SEARCH = Yes   # Manual feature list search

LOOKUP_TABLE_INPUT (input)
    -> AttributeExposer
DATA_INPUT (input)
    -> AttributeExposer_3
Note: Unmerged Requestor items sent to Excel file
DATA_OUTPUT_FAILED (output)
DATA_OUTPUT_PASSED (output)
Tester_4
    BOOL_OP = OR
    COMPOSITE_TEST = 1
    TEST_CLAUSE = TEST $(FEATURE_LIST_SEARCH) = Yes
    TEST_MODE = TEST
    PASSED -> ListSearcher_2
MANUAL_ITEMS_OUTPUT (output)

Bookmark: Excel file validation
Note: Exposes attributes from lookup table
AttributeExposer
    ATTR_LIST = uuid,spatial_representation_type
    -> Tester
Note: Tests for value in required fields
Tester
    BOOL_OP = AND
    COMPOSITE_TEST = 1 AND 2
    TEST_CLAUSE:
      TEST uuid ATTRIBUTE_HAS_A_VALUE ""
      TEST spatial_representation_type ATTRIBUTE_HAS_A_VALUE ""
    TEST_MODE = TEST
    PASSED -> DuplicateFilter
    FAILED -> Terminator_3
Terminator_3
    MESSAGE = Missing values in spatial_represntation_type or uuid attributes, UUID_Spatial lookup table, GEOSPATIAL_DATA_VALIDATOR transformer.  Translation terminated.
Note: Tests for duplicates of 'uuid' attribute
DuplicateFilter
    INPUT_ORDERED_CHOICE = No
    KEYATTR = uuid
    UNIQUE -> FeatureMerger [SUPPLIER]
    DUPLICATE -> Terminator_2
Terminator_2
    MESSAGE = Duplicate feature @Value(uuid) found in format attribute in UUID_Spatial lookup table, GEOSPATIAL_DATA_VALIDATOR transformer.  Translation terminated.

Bookmark: Spatial Type Mapper
Note: Exposes attributes from incoming data
AttributeExposer_3
    ATTR_LIST = resources{}.spatial_type,id,title,notes,url,global_list_attribute_type{}.spatial_type
    -> ListSearcher
    -> Tester_4
Note: Searches resources{}.spatial_type lists for items with value. These items are extracted from the Geospatial lookup table in the GEOSPATIAL_DATA_VALIDATOR transformer. Possible values are: / a-grid / b-vector / c-textTable
ListSearcher
    INDEX_ATTR = _list_index
    LIST_ATTR = resources{}.spatial_type
    MATCHTYPE = FIRST_NOT_MATCHED_ENCODED
    FOUND -> ListHistogrammer_2
    NOT_FOUND -> FeatureMerger [REQUESTOR]
Note: Data items without value are set by feature merging with UUID_Spatial lookup table
FeatureMerger
    ATTR_ACCUM_MODE = Merge Supplier
    ATTR_CONFLICT_RES = Use Requestor
    IGNORE_NULLS = No
    JOIN_KEYS = @Value(id) @Value(uuid) AUTO
    MERGE_TYPE = Attributes Only
    PROCESS_DUPS = NO
    REJECT_NULL_MISSING_KEYS = No
    SUPPLIERS_FIRST = No
    MERGED -> AttributeRemover
    UNMERGED_REQUESTOR -> Logger
    <REJECTED> -> Terminator
Logger
    LOG_FEATURE = LOG_RECORD
    MAXCOORDS = 20
    MAXFEATS = 20
    MESSAGE = Data record with unique ID @Value(id) missing from UUID_Spatial lookup table in SPATIAL_TYPE_MAPPER transformer and could not be mapped to a value.  See PROCESS_REPORT_MANUAL_TASKS.xls file in XLS directory for details.
    SEVERITY = WARN
    LOGGED -> AttributeKeeper
Note: Unmerged Requestor items retain uuid, title and notes attributes for analysis to add missing items with correct value to the lookup table
AttributeKeeper
    KEEP_ATTRS = url,id,title,notes
    -> DATA_OUTPUT_FAILED (output)
Terminator
    MESSAGE = Process failed at Feature Merger, SPATIAL_TYPE_MAPPER transformer.  Translation terminated.
ListHistogrammer_2
    LIST_NAME = spatialType_histogram_temp
    SRC_LIST = resources{}.spatial_type
    -> ListElementCounter
ListElementCounter
    CNT_ATTR = _element_count
    LIST_NAME = spatialType_histogram_temp{}
    -> PythonCaller
PythonCaller
    NEW_ATTRIBUTES = spatialType_histogram{}.value spatialType_histogram{}.count
    PYTHONSOURCE:
      import fme
      import fmeobjects
      # Template Function interface:
      # When using this function, make sure its name is set as the value of
      # the 'Class or Function to Process Features' transformer parameter
      def processFeature(feature):
          index=0
          for i in range(int(feature.getAttribute('_element_count'))):
              if feature.getAttribute('spatialType_histogram_temp{%d}.value'%(i)):
                  feature.setAttribute('spatialType_histogram{%d}.value'%(index),feature.getAttribute('spatialType_histogram_temp{%d}.value'%(i)))
                  feature.setAttribute('spatialType_histogram{%d}.count'%(index),feature.getAttribute('spatialType_histogram_temp{%d}.count'%(i)))
                  index=index+1
    PYTHONSYMBOL = processFeature
    -> AttributeRemover_3
AttributeRemover_3
    LIST_ATTRS = spatialType_histogram_temp{}
    -> ListSorter_2
Note: spatialType_histogram{}.count list is sorted in descending numeric value; index item 0 becomes the highest count of resources{}.spatial_type items and is set as the spatial_representation_type value
ListSorter_2
    ORDER = Descending
    SRC_LIST = spatialType_histogram{}.count
    TYPE = Numeric
    -> Tester_6
Note: The first three spatialType_histogram{}.count items are tested for equal value
Tester_6
    BOOL_OP = COMPOSITE
    COMPOSITE_TEST = 1 AND 2
    TEST_CLAUSE:
      TEST @Value(spatialType_histogram{0}.count) = @Value(spatialType_histogram{1}.count)
      TEST @Value(spatialType_histogram{1}.count) = @Value(spatialType_histogram{2}.count)
    TEST_MODE = TEST
    PASSED -> ListSorter
    FAILED -> Tester_7
Note: The first two spatialType_histogram{}.count items are tested for equal value
Tester_7
    BOOL_OP = OR
    COMPOSITE_TEST = 1
    TEST_CLAUSE = TEST @Value(spatialType_histogram{0}.count) = @Value(spatialType_histogram{1}.count)
    TEST_MODE = TEST
    PASSED -> AttributeRemover_2
    FAILED -> AttributeSplitter
Note: Removes third item on spatialType_histogram{} list
AttributeRemover_2
    REMOVE_ATTRS = spatialType_histogram{2}.value,spatialType_histogram{2}.count
    -> ListSorter
Note: spatialType_histogram{}.count items that have equal value are sorted by histogram{}.value in ascending order: / a-grid / b-vector / c-textTable / In this event, index item 0 is given priority and set as the spatial_representation_type
ListSorter
    ORDER = Ascending
    SRC_LIST = spatialType_histogram{}.value
    TYPE = Alphabetic
    -> AttributeSplitter
Note: histogram{0}.value is split at the '-' delimiter to remove the prefix from the value ie: 'a-' is removed from 'a-grid'. Output is spatial_trim{} list
AttributeSplitter
    ATTR_NAME = spatialType_histogram{0}.value
    DELIMITER = -
    DROP_EMPTY_PARTS = No
    LIST_NAME = spatial_trim
    TRIM_OPTION = Both
    -> AttributeCreator_4
Note: spatial_representation_type attribute is set to value of spatial_trim{1}
AttributeCreator_4
    ATTR_TABLE = SET_TO spatial_representation_type = @Value(spatial_trim{1})
    -> AttributeRemover
Note: Attribute cleanup
AttributeRemover
    LIST_ATTRS = spatialType_histogram{} spatial_trim{}
    REMOVE_ATTRS = _element_count,uuid,_list_index
    -> DATA_OUTPUT_PASSED (output)

Bookmark: Global_List_Attribute_Type Searcher
ListSearcher_2
    INDEX_ATTR = _list_index
    LIST_ATTR = global_list_attribute_type{}.spatial_type
    MATCHTYPE = FIRST_MATCHED_ENCODED
    FOUND -> ListHistogrammer
ListHistogrammer
    LIST_NAME = spatialType_histogram_temp
    SRC_LIST = global_list_attribute_type{}.spatial_type
    -> ListElementCounter_2
ListElementCounter_2
    CNT_ATTR = _element_count
    LIST_NAME = spatialType_histogram_temp{}
    -> PythonCaller_2
PythonCaller_2
    NEW_ATTRIBUTES = spatialType_histogram{}.value spatialType_histogram{}.count
    PYTHONSOURCE:
      import fme
      import fmeobjects
      # Template Function interface:
      # When using this function, make sure its name is set as the value of
      # the 'Class or Function to Process Features' transformer parameter
      def processFeature(feature):
          index=0
          for i in range(int(feature.getAttribute('_element_count'))):
              if feature.getAttribute('spatialType_histogram_temp{%d}.value'%(i)):
                  feature.setAttribute('spatialType_histogram{%d}.value'%(index),feature.getAttribute('spatialType_histogram_temp{%d}.value'%(i)))
                  feature.setAttribute('spatialType_histogram{%d}.count'%(index),feature.getAttribute('spatialType_histogram_temp{%d}.count'%(i)))
                  index=index+1
    PYTHONSYMBOL = processFeature
    -> AttributeRemover_4
Note: Up to this point is the same logic used for resources{}.spatial_type
AttributeRemover_4
    LIST_ATTRS = spatialType_histogram_temp{}
    -> Tester_2
Tester_2
    BOOL_OP = OR
    COMPOSITE_TEST = 1
    TEST_CLAUSE = TEST spatialType_histogram{} != ""
    TEST_MODE = TEST
    PASSED -> Tester_3
Note: Found those with Spatial representation type
Tester_3
    BOOL_OP = OR
    COMPOSITE_TEST = 1
    TEST_CLAUSE = TEST @Value(spatialType_histogram{0}.count) = 1
    TEST_MODE = TEST
    PASSED -> AttributeSplitter_2
AttributeSplitter_2
    ATTR_NAME = spatialType_histogram{0}.value
    DELIMITER = -
    DROP_EMPTY_PARTS = No
    LIST_NAME = spatialType_splitted
    TRIM_OPTION = Both
    -> AttributeCreator
AttributeCreator
    ATTR_TABLE = SET_TO spatial_representation_type = @Value(spatialType_splitted{1})
    -> AttributeKeeper_2
AttributeKeeper_2
    KEEP_ATTRS = id,spatial_representation_type
    -> MANUAL_ITEMS_OUTPUT (output)

FME custom transformer NS_ATTRIBUTE_MANAGER

Input (input)
    -> AttributeExposer_3
AttributeExposer_3
    ATTR_LIST = id,default_domain_tag,tags{},default_projection_name,default_projection_system_version,default_reference_system,"metadata.custom_fields.Detailed Metadata.Department",description,name,assetType,publicationDate,viewLastModified,createdAt
    -> AttributeCreator_5
AttributeCreator_5
    ATTR_TABLE:
      SET_TO resource.id = @Value(id)
      SET_TO resource.type = @Value(assetType)
    -> UNIQUE_ID_CREATOR
UNIQUE_ID_CREATOR
    UNIQUE_ATT = @Value(resource.id)
    -> Tester_4
Tester
    BOOL_OP = OR
    COMPOSITE_TEST = 1
    TEST_CLAUSE = TEST @Value(description) != ""
    TEST_MODE = TEST
    PASSED -> AttributeCreator_8
    FAILED -> AttributeCreator
AttributeCreator
    ATTR_TABLE = SET_TO description = @Value(name)
    -> AttributeCreator_8
Note: Setting default projection system
AttributeCreator_8
    ATTR_TABLE:
      SET_TO spatialref{0}.projection_name = @Value(default_projection_name)
      SET_TO spatialref{0}.projection_system = @Value(default_reference_system)
      SET_TO spatialref{0}.projection_system_version = @Value(default_projection_system_version)
    -> AttributeCreator_9
Note: Creating inhouse model attribute base on NS format
AttributeCreator_9
    ATTR_TABLE:
      SET_TO sector = @Value(metadata.custom_fields.Detailed Metadata.Department)
      SET_TO notes = @Value(description)
      SET_TO title = @Value(name)
      SET_TO record_publish_date = @Value(publicationDate)
      SET_TO record_last_modified = @Value(viewLastModified)
      SET_TO record_create_date = @Value(createdAt)
    -> DateTimeConverter

Bookmark: Managing tags
Tester_4
    BOOL_OP = OR
    COMPOSITE_TEST = 1
    TEST_CLAUSE = TEST tags{0} ATTRIBUTE_HAS_A_VALUE ""
    TEST_MODE = TEST
    PASSED -> ListCopier
    FAILED -> AttributeCreator_2
AttributeCreator_2
    ATTR_TABLE = SET_TO tags{0} = @Value(default_domain_tag)
    -> ListCopier
ListCopier
    DEST_LIST = tags_copy
    SRC_LIST = tags{}
    -> AttributeRemover
AttributeRemover
    LIST_ATTRS = tags{}
    -> PythonCaller
PythonCaller
    NEW_ATTRIBUTES = tags{}.display_name
    PYTHONSOURCE:
      import fme
      import fmeobjects
      # Template Function interface:
      # When using this function, make sure its name is set as the value of
      # the 'Class or Function to Process Features' transformer parameter
      def processFeature(feature):
          i=0
          for elem in feature.getAttribute('tags_copy{}'):
              feature.setAttribute('tags{%i}.display_name'%(i),elem)
              i+=1



      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> AttributeRemover_2
AttributeRemover_2
    LIST_ATTRS = tags_copy{}
    -> Tester

Bookmark: DateTime Conversion
Note: Formats all date fields to ISO yyyy-mm-dd
DateTimeConverter
    DATETIME_ATTR = record_create_date record_last_modified record_publish_date
    IN_FORMAT = %s$
    OUT_FORMAT = %Y-%m-%d
    PASSTHROUGH = NO
    REPAIR_INPUT = YES
    TEST_INPUT = 1611946240
    -> Output (output)
    -> DateTimeConverter_Output
    <REJECTED> -> error_datetime_output (output)
Output (output)
DateTimeConverter_Output: Inspector
error_datetime_output (output)

FME custom transformer ListSlicer_2
Replaces an existing list with a list containing elements of the slicing range which is determined by the starting index and the number of elements.
If the source list was a structured one like "_list{}.foo", "_list{}.bar", all the members belonging to the same base name will be replaced.
Example
When the source list contains:
_list{0}.foo = '0'
_list{1}.foo = '1'
_list{2}.foo = '2'
_list{3}.foo = '3'
_list{4}.foo = '4'
_list{0}.bar = 'A'
_list{1}.bar = 'B'
_list{2}.bar = 'C'
_list{3}.bar = 'D'
_list{4}.bar = 'E'
After slicing with Starting Element Index = 1 and Number of Elements to Slice = 3, the list will be replaced with:
_list{0}.foo = '1'
_list{1}.foo = '2'
_list{2}.foo = '3'
_list{0}.bar = 'B'
_list{1}.bar = 'C'
_list{2}.bar = 'D'
Note: This transformer contains a Python script which was tested with both Python 2.7 interpreter and Python 3.6 interpreter.
Parameters
    Source List Attribute:
Select a source list attribute to be sliced.
    Starting Element Index:
Specify index of the element to start slicing. The index is always 0-based.
If specified index is less than 0, this transformer considers the starting index as 0.
    Number of Elements to Slice:
Specify the number of elements to be sliced.
If specified number is equal to 0, this transformer removes every element from the source list (i.e. removes the source list).
If specified number is less than 0, this transformer considers the number as 0.
    Null Elements Treatment:
Select how treat <null> elements in the slicing range.
"Replace with Empty String" - Every <null> element will be replaced with an empty string.
"Replace with New Value" - Every <null> element will be replaced with a value specified as New Value for Null parameter.
"Replace with Missing" - Every <null> element will be removed. The element will be missing in the resultant list.
"Leave Null" - Every <null> element will be left in the resultant list as <null>.
    New Value for Null:
Specify a value to be used for replacing <null> elements.
This parameter is used only if you selected "Replace with New Value" to Null Elements Treatment. Otherwise, it'll be just ignored.
    Missing Elements Treatment:
Select how treat <missing> elements in the slicing range.
"Replace with Empty String" - Every <missing> element will be replaced with an empty string.
"Replace with New Value" - Every <missing> element will be replaced with a value specified as New Value for Missing parameter.
"Replace with Null" - Every <missing> element will be replaced with <null>.
"Leave Missing" - Every <missing> element will be still missing in the resultant list.
    New Value for Missing:
Specify a value to be used for replacing <missing> elements.
This parameter is used only if you selected "Replace with New Value" to Missing Elements Treatment. Otherwise, it'll be just ignored.

Parameters:
- SRC_LIST =   # " " Source List Attribute
- START_INDEX = 0   # Starting Element Index
- NUM_ELEMENTS =   # Number of Elements to Slice
- NULL_TREATMENT = empty
- NEWVALUE_FOR_NULL =   # New Value for Null
- MISSING_TREATMENT = empty
- NEWVALUE_FOR_MISSING =   # New Value for Missing

Input (input)
    -> ParameterFetcher
ParameterFetcher
    ATTR_LIST = __listslicer.src_list {$(SRC_LIST)} __listslicer.start_index {$(START_INDEX)} __listslicer.num_elements {$(NUM_ELEMENTS)} __listslicer.null_treat {$(NULL_TREATMENT)} __listslicer.newvalue_for_null {$(NEWVALUE_FOR_NULL)} __listslicer.missing_treat {$(MISSING_TREATMENT)} __listslicer.newvalue_for_missing {$(NEWVALUE_FOR_MISSING)}
    -> PythonCaller
PythonCaller
    HIDE_ATTRIBUTES = __listslicer.src_list __listslicer.start_index __listslicer.num_elements __listslicer.null_treat __listslicer.newvalue_for_null __listslicer.missing_treat __listslicer.newvalue_for_missing
    PYTHONSOURCE:
      # 2014-07-27, Takashi Iijima, Original Implementation
      # 2014-08-02, Takashi Iijima, Resolved encoding issue on list name
      # 2018-06-14, Takashi Iijima, Updated to support both Python 2.7 and Python 3.x
      # 2020-04-30, Takashi Iijima, Changed default Python interpreter version to 3.x, saved with FME 2017.1.2.1

      import fmeobjects, re

      class ListSlicer(object):
          def __init__(self):
              import platform
              if platform.python_version_tuple()[0] == '2':
                  import locale
                  loc = locale.getdefaultlocale()
                  enc = loc[1] if loc else 'utf_8'
                  self.toStr = lambda s: s.encode(enc) if isinstance(s, unicode) else s
              else:
                  self.toStr = lambda s: s

          def input(self, feature):
              listName = self.toStr(feature.getAttribute('__listslicer.src_list'))
              prefix = listName[:-2]
              regexListElement = re.compile(r'^%s\{(\d+)\}(.*)$' % prefix)

              # Find maximum element index and collect suffixes of target list members.
              maxIndex = -1
              suffixes = set([])
              for name in [self.toStr(s) for s in feature.getAllAttributeNames()]:
                  m = regexListElement.match(name)
                  if m:
                      if maxIndex < int(m.group(1)):
                          maxIndex = int(m.group(1))
                      suffixes.add(self.toStr(m.group(2)))

              startIndex = int(feature.getAttribute('__listslicer.start_index'))
              if startIndex < 0:
                  startIndex = 0
              numElements = int(feature.getAttribute('__listslicer.num_elements'))
              if numElements < 0:
                  numElements = 0

              nullTreat = feature.getAttribute('__listslicer.null_treat')
              newValueToNull = feature.getAttribute('__listslicer.newvalue_for_null')

              missingTreat = feature.getAttribute('__listslicer.missing_treat')
              newValueToMissing = feature.getAttribute('__listslicer.newvalue_for_missing')

              for suffix in suffixes:
                  # Move elements from slicing range to head of the list.
                  for i in range(numElements):
                      srcName = '%s{%d}%s' % (prefix, startIndex + i, suffix)
                      destName = '%s{%d}%s' % (prefix, i, suffix)

                      isNull, isMissing, type = feature.getAttributeNullMissingAndType(srcName)
                      if isNull:
                          if nullTreat == 'empty':
                              feature.setAttribute(destName, '')
                          elif nullTreat == 'newvalue':
                              feature.setAttribute(destName, newValueToNull)
                          elif nullTreat == 'missing':
                              feature.removeAttribute(destName)
                          elif nullTreat == 'as_is':
                              feature.setAttributeNullWithType(destName, type)
                          else:
                              raise fmeobjects.FMEException('Debug error: Null Treatment')

                      elif isMissing:
                          if missingTreat == 'empty':
                              feature.setAttribute(destName, '')
                          elif missingTreat == 'newvalue':
                              feature.setAttribute(destName, newValueToMissing)
                          elif missingTreat == 'null':
                              feature.setAttributeNullWithType(destName, type)
                          elif missingTreat == 'as_is':
                              feature.removeAttribute(destName)
                          else:
                              raise fmeobjects.FMEException('Debug error: Missing Treatment')

                      else:
                          feature.setAttribute(destName, feature.getAttribute(srcName))

                  # Remove excess elements.
                  for i in range(numElements, maxIndex + 1):
                      feature.removeAttribute('%s{%d}%s' % (prefix, i, suffix))

              feature.removeAttrsWithPrefix('__listslicer.')
              self.pyoutput(feature)

          def close(self):
              pass
    PYTHONSYMBOL = ListSlicer
    -> Output (output)
Output (output)

FME custom transformer NB_BOUNDING_BOX_EXTRACTOR

Parameters:
- Socrata_Domain =   # Enter the Socrata Domain (without https)
- SocrataAppToken = FL3Cxsebg0Vf6JQ0CnbMujHkQ   # Socrata App Token

feature_input (input)
    -> AttributeExposer_2
AttributeExposer_2
    ATTR_LIST = dataLayers{},dataLayers{}.layerid,dataLayers{}.geomcol,dataLayers{}.name,dataLayers{}.geomtype,assetType
    -> Tester_2
Tester_2
    BOOL_OP = OR
    COMPOSITE_TEST = 1
    TEST_CLAUSE = TEST @Value(assetType) != href
    TEST_MODE = TEST
    PASSED -> UUIDGenerator_2
    FAILED -> Junction_2
Note: cleanup
AttributeRemover_6
    LIST_ATTRS = dataLayers{}.east_bound_longitudes dataLayers{}.north_bound_latitudes dataLayers{}.south_bound_latitudes dataLayers{}.west_bound_longitudes
    REMOVE_ATTRS = coordinatestring,bbox_json,uuidjoinkey
    -> feature_output (output)
Junction_2
    -> Junction
Note: gets the bounding box geojson from the socrata api, enters the json coordinate array into python where list comprehension is used to get the minimum and maximum lat and long
Junction
    -> AttributeExposer
feature_output (output)

Bookmark: Extract Bounding Box
UUIDGenerator_2
    UUID_ATTR = uuidjoinkey
    -> FeatureMerger_2 [REQUESTOR]
    -> AttributeKeeper_2
AttributeKeeper_2
    KEEP_ATTRS = uuidjoinkey
    KEEP_LIST = dataLayers{}
    -> ListExploder_2
ListExploder_2
    ATTR_ACCUM_MODE = Merge List Attributes
    ATTR_CONFLICT_RES = Use List Attribute Values
    INDEX_ATTR = _element_index
    LIST_ATTR = dataLayers{}
    ELEMENTS -> Tester
    <REJECTED> -> Cloner
Tester
    BOOL_OP = OR
    COMPOSITE_TEST = 1
    TEST_CLAUSE = TEST @Value(layerid) != ""
    TEST_MODE = TEST
    PASSED -> StringConcatenator
StringConcatenator
    ACTION = Create New Attribute
    PARM_LINE = fme_basicstring:8%17%10%15%8:https://$(Socrata_Domain)/resource/@Value(layerid).geojson
    VAL_ATTR = GeoAPIEndpoint
    -> HTTPCaller_2
HTTPCaller_2
    CONNECTION_TIMEOUT_LENGTH = 60
    CUSTOM_HEADERS = X-App-Token;$(SocrataAppToken)
    ERROR_ATTR = _error
    FOLLOW_REDIRECTS = Yes
    HTTP_METHOD = GET
    SAVE_FILE = Attribute
    STATUS_CODE_ATTR = _http_status_code
    TARGET_ATTR = bbox_json
    TARGET_ATTR_ENCODING = auto-detect
    TARGET_URL = @Value(GeoAPIEndpoint)?$select=extent(@Value(geomcol))
    TRANSFER_TIMEOUT_LENGTH = 90
    USE_COOKIES = No
    VERIFY_SSL_CERTIFICATES = No
    -> AttributeRemover
    <REJECTED> -> Cloner
AttributeRemover
    REMOVE_ATTRS = _http_status_code
    -> JSONFlattener_2
JSONFlattener_2
    ERROR_LIST_ATTR = _json_error
    JSON_DOCUMENT = @Value(bbox_json)
    NEW_ATTRIBUTES = features
    READ_FROM_FILE = NO
    RECURSIVE = No
    -> JSONExtractor
    <REJECTED> -> Cloner
JSONExtractor
    EXTRACT_QUERY_TABLE = coordinatestring json["features"][0]["geometry"]["coordinates"][0][0]
    JSON_DOCUMENT = @Value(bbox_json)
    READ_FROM_FILE = NO
    EVALUATED -> PythonCaller
    <REJECTED> -> Cloner
Note: extracts the minimum and maximum longitude and latitude values of the bounding box.
PythonCaller
    NEW_ATTRIBUTES = south_bound_latitudes north_bound_latitudes west_bound_longitudes east_bound_longitudes
    PYTHONSOURCE:
      import fme, fmeobjects, json
      # Template Function interface:
      # When using this function, make sure its name is set as the value of
      # the 'Class or Function to Process Features' transformer parameter
      def processFeature(feature):
          list = feature.getAttribute('coordinatestring')
          actualList = json.loads(list)
          longitudes = [float(x[0]) for x in actualList]
          latitudes = [float(x[1]) for x in actualList]
          feature.setAttribute('south_bound_latitudes',min(latitudes))
          feature.setAttribute('north_bound_latitudes',max(latitudes))
          feature.setAttribute('west_bound_longitudes',min(longitudes))
          feature.setAttribute('east_bound_longitudes',max(longitudes))
    PYTHONSYMBOL = processFeature
    -> FeatureMerger_2 [SUPPLIER]
FeatureMerger_2
    ATTR_ACCUM_MODE = Merge Supplier
    ATTR_CONFLICT_RES = Use Requestor
    IGNORE_NULLS = No
    JOIN_KEYS = @Value(uuidjoinkey) @Value(uuidjoinkey) AUTO
    LIST_ATTRS_TO_INCLUDE = east_bound_longitudes geomcol geomtype name north_bound_latitudes south_bound_latitudes west_bound_longitudes layerid
    LIST_NAME = dataLayers
    MERGE_TYPE = Attributes Only
    PROCESS_DUPS = NO
    REJECT_NULL_MISSING_KEYS = No
    SUPPLIERS_FIRST = No
    MERGED -> ListRangeExtractor
    UNMERGED_REQUESTOR -> AttributeExposer
Cloner
    COPIES = 1
    COPYATT = _copynum
AttributeExposer
    ATTR_LIST = default_west,default_east,default_north,default_south
    -> AttributeCreator
AttributeCreator
    ATTR_TABLE:
      SET_TO north_bound_latitude = @Value(default_north)
      SET_TO south_bound_latitude = @Value(default_south)
      SET_TO west_bound_longitude = @Value(default_west)
      SET_TO east_bound_longitude = @Value(default_east)
    -> feature_output (output)

Bookmark: Consolidates longitude and latitude lists for if a dataset has multiple layers
ListRangeExtractor
    MAX = north_bound_latitude
    MIN = minnorth
    SRC_LIST = dataLayers{}.north_bound_latitudes
    -> ListRangeExtractor_2
ListRangeExtractor_2
    MAX = maxsouth
    MIN = south_bound_latitude
    SRC_LIST = dataLayers{}.south_bound_latitudes
    -> ListRangeExtractor_3
ListRangeExtractor_3
    MAX = maxwest
    MIN = west_bound_longitude
    SRC_LIST = dataLayers{}.west_bound_longitudes
    -> ListRangeExtractor_4
ListRangeExtractor_4
    MAX = east_bound_longitude
    MIN = mineast
    SRC_LIST = dataLayers{}.east_bound_longitudes
    -> AttributeRemover_6

Bookmark: COMMENTS
Note: Please add terminator to rejected ports when needed
