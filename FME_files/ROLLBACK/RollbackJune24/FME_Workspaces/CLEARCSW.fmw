FME workspace CLEARCSW.fmw

Parameters:
- ENTITY_SEARCH_LITERAL = %%   # Select string with p-t name fragment
- CSW_URL = http://127.0.0.1:8080/pycsw   # "%https://pycsw-bc.ddr-dev.cgp-pgc.ca/pycsw?%http://127.0.0.1:8080/pycsw CSW URL

Note: This section extracts the unique ID's from all data records currently loaded to the CSW.
Creator
    GEOMTYPE = Geometry Object
    NUM = 1
    CREATED -> AttributeCreator_255
Note: Loads the Delete Records XML template for each CSW Data Record not found in the current data search
XMLTemplater_2
    QUERY_EXPR:
      <csw:Transaction xmlns:csw="http://www.opengis.net/cat/csw/2.0.2" xmlns:ogc="http://www.opengis.net/ogc" xmlns:apiso="http://www.opengis.net/cat/csw/apiso/1.0" xmlns:xsi="http://www.w3.org/2001/XMLSchema-instance" service="CSW" version="2.0.2" xsi:schemaLocation="http://www.opengis.net/cat/csw/2.0.2 http://schemas.opengis.net/csw/2.0.2/CSW-publication.xsd">
          <csw:Delete>
              <csw:Constraint version="1.1.0">
                  <ogc:Filter>
                      <ogc:PropertyIsLike escapeChar="\" singleChar="?" wildCard="*">
                          <ogc:PropertyName>dc:identifier</ogc:PropertyName>
                          <ogc:Literal>{fme:get-attribute("csw_id")}</ogc:Literal>
                      </ogc:PropertyIsLike>
                  </ogc:Filter>
              </csw:Constraint>
          </csw:Delete>
      </csw:Transaction>
    RESULT_ATTRIBUTE = CSWRequest
    XQUERY_TYPE = Expression
    -> XMLFormatter_4
Note: Formats Delete Records XML's
XMLFormatter_4
    COLLAPSE_EMPTY_ELEMENT = No
    FORMATTING_CHOICE = Pretty-Print XML
    LIST_NAME = _xml_error
    NAMESPACE_CLEANUP = Yes
    SCHEMALOC_CLEANUP = Yes
    XML_ATTR_TEXT = CSWRequest
    XML_INPUT_TYPE = Attribute Specifying XML Text
    XML_OUTPUT_ATTR = _xml_output
    XML_OUTPUT_TYPE = Attribute
    PASSED -> XMLValidator_4
Note: Validates Delete Records XML's
XMLValidator_4
    LIMIT_ERRORS = No
    LIST_NAME = _xml_error
    VAL_MODE_1 = Syntax Only
    XML_ATTR_TEXT = CSWRequest
    XML_INPUT_TYPE = Attribute Specifying XML Text
    PASSED -> PyCSW_POST_4
Note: Posts Delete Records XML for each UUID in the CSW not found in the current data search, removing the obsolete record
PyCSW_POST_4: PythonCaller
    NEW_ATTRIBUTES = insert_response
    PYTHONSOURCE:
      import fme
      import fmeobjects
      import urllib3
      import requests

      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):

          def __init__(self):
              pass

              self.csw_url = fme.macroValues['CSW_URL']

          def input(self,feature):
              self.xml_str = feature.getAttribute('_xml_output')
              self.xml_str = self.xml_str.encode('utf-8')

              request_str = self.post_xml()

              feature.setAttribute('insert_response', request_str)

              self.pyoutput(feature)

          def post_xml(self):
              headers = {'Content-Type': 'text/xml; charset=utf-8'} # set what your server accepts

              return requests.post(self.csw_url, data=self.xml_str, headers=headers).text

          def close(self):
              pass
    PYTHONSYMBOL = FeatureProcessor
    -> Logger
Logger
    LOG_FEATURE = LOG_ONLY
    MAXCOORDS = 20
    MAXFEATS = 20
    MESSAGE = @Value(insert_response)
    SEVERITY = INFO

Bookmark: CSW UUID Reader
Note: Attribute required to perform CSW search
AttributeCreator_255
    ATTR_TABLE = SET_TO entity_search_literal = $(ENTITY_SEARCH_LITERAL)
    -> XMLTemplater
Note: Loads the Get Records XML template
XMLTemplater
    QUERY_EXPR:
      <csw:GetRecords
          service="CSW"
          version="2.0.2"
          resultType="results"
          outputFormat="application/xml"
          outputSchema="http://www.opengis.net/cat/csw/2.0.2"
          xsi:schemaLocation="http://www.opengis.net/cat/csw/2.0.2 http://schemas.opengis.net/csw/2.0.2/CSW-discovery.xsd"
          xmlns:csw="http://www.opengis.net/cat/csw/2.0.2"
          xmlns:dc="http://purl.org/dc/elements/1.1/"
          xmlns:dct="http://purl.org/dc/terms/"
          xmlns:gmd="http://www.isotc211.org/2005/gmd"
          xmlns:gml="http://www.opengis.net/gml"
          xmlns:ows="http://www.opengis.net/ows"
          xmlns:xs="http://www.w3.org/2001/XMLSchema"
          xmlns:xsi="http://www.w3.org/2001/XMLSchema-instance">
          <csw:Query typeNames="csw:Record">
              <csw:ElementSetName typeNames="gmd:MD_Metadata">summary</csw:ElementSetName>
              <csw:Constraint version="1.1.0">
                  <Filter
                      xmlns="http://www.opengis.net/ogc"
                      xmlns:gml="http://www.opengis.net/gml">
                      <PropertyIsEqualTo>
                          <PropertyName>csw:AnyText</PropertyName>
                          <Literal>{fme:get-attribute("entity_search_literal")}</Literal>
                      </PropertyIsEqualTo>
                  </Filter>
              </csw:Constraint>
          </csw:Query>
      </csw:GetRecords>
    RESULT_ATTRIBUTE = CSWRequest
    XQUERY_TYPE = Expression
    -> XMLFormatter
Note: Formats Get Records XML
XMLFormatter
    COLLAPSE_EMPTY_ELEMENT = No
    FORMATTING_CHOICE = Pretty-Print XML
    LIST_NAME = _xml_error
    NAMESPACE_CLEANUP = Yes
    SCHEMALOC_CLEANUP = Yes
    XML_ATTR_TEXT = CSWRequest
    XML_INPUT_TYPE = Attribute Specifying XML Text
    XML_OUTPUT_ATTR = _xml_output
    XML_OUTPUT_TYPE = Attribute
    PASSED -> XMLValidator
Note: Validates XML File
XMLValidator
    LIMIT_ERRORS = No
    LIST_NAME = _xml_error
    VAL_MODE_1 = Syntax Only
    XML_ATTR_TEXT = CSWRequest
    XML_INPUT_TYPE = Attribute Specifying XML Text
    PASSED -> PyCSW_POST_1
Note: Posts XML to PyCSW using Python script and returns XML with dataset summary
PyCSW_POST_1: PythonCaller
    NEW_ATTRIBUTES = insert_response
    PYTHONSOURCE:
      import fme
      import fmeobjects
      import urllib3
      import requests

      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):

          def __init__(self):
              pass

              self.csw_url = fme.macroValues['CSW_URL']

          def input(self,feature):
              self.xml_str = feature.getAttribute('_xml_output')
              self.xml_str = self.xml_str.encode('utf-8')

              request_str = self.post_xml()

              feature.setAttribute('insert_response', request_str)

              self.pyoutput(feature)

          def post_xml(self):
              headers = {'Content-Type': 'text/xml; charset=utf-8'} # set what your server accepts

              return requests.post(self.csw_url, data=self.xml_str, headers=headers).text

          def close(self):
              pass
    PYTHONSYMBOL = FeatureProcessor
    -> XMLFragmenter
Note: Exposes the unique ID elements from the returned XML file
XMLFragmenter
    ATTRIBUTE_XML = insert_response
    EMBEDDED_EXPRESSIONS = identifier
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    XML_SOURCE_TYPE = Attribute with XML document
    FRAGMENTS -> StringSearcher_8
Note: Extracts string snippet from the unique ID element
StringSearcher_8
    CASE = no
    MATCHED_RESULT_ATTR = csw_id
    REGEXP = (?<=<dc:identifier xmlns:dc="http://purl.org/dc/elements/1.1/">).*(?=</dc:identifier>)
    STRING_TO_SEARCH = @Value(xml_fragment)
    MATCHED -> Junction_13
Note: AttributeKeeper : Input
Junction_13
    -> XMLTemplater_2
