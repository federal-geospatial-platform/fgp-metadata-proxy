FME workspace metrique_qc_attribute_mapper.fmw

Parameters:
- IN_FFS_FILE_1 =   # Source FME Feature Store (FFS) File(s)
- LOG_FILE =
- OUT_FFS_FILE_1 =

Readers:
- FFS_1: FFS from $(IN_FFS_FILE_1)

Writers:
- FFS_2: FFS to $(OUT_FFS_FILE_1)

Source1 (reader FFS_1)
    attributes: _creation_instance varchar(200), result.file_id varchar(200), MD_Metadata.fileIdentifier.CharacterString varchar(200), MD_Metadata.MD_Metadata varchar(200), _OpenMapsFilter varchar(200), result.results varchar(200), debut varchar(200), NbRecords varchar(200), root_url varchar(200), _response_body varchar(200), _http_status_code varchar(200), MD_Metadata{} varchar(200)
    -> QC_ATTRIBUTE_MAPPER
QC_ATTRIBUTE_MAPPER
    -> resultat1 (writer FFS_2)
resultat1 (writer FFS_2)
    attributes: progress_code varchar(200), tags{}.display_name varchar(200), contacts{0}.name varchar(200), contacts{0}.email varchar(200), sector varchar(200), location varchar(200), _creation_instance varchar(200), result.file_id varchar(200), MD_Metadata.fileIdentifier.CharacterString varchar(200), MD_Metadata.MD_Metadata varchar(200), _OpenMapsFilter varchar(200), result.results varchar(200), debut varchar(200), NbRecords varchar(200), root_url varchar(200), _response_body varchar(200), _http_status_code varchar(200), MD_Metadata{} varchar(200), temporal varchar(200), metadata_created varchar(200), resources{}.created varchar(200), metadata_modified varchar(200), resources{}.last_modified varchar(200), notes varchar(200), resources{}.name varchar(200), resources{}.format varchar(200), resources{}.url varchar(200), title varchar(200), update_frequency varchar(200), id varchar(200),
      contacts{0}.position varchar(200), contacts{0}.position_other_lang varchar(200), contacts{0}.address varchar(200), contacts{0}.administrative_area varchar(200), contacts{0}.city varchar(200), contacts{0}.country varchar(200), contacts{0}.facsimile varchar(200), contacts{0}.phone varchar(200), contacts{0}.postal_code varchar(200), license_id varchar(200), tags_element_count varchar(200)
