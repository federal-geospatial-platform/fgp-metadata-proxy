FME workspace ATTRIBUTE_MAPPING_ERRORS_EXCEL_CREATOR.fmw

Parameters:
- SourceDataset_FFS = C:\Data\ATTRIBUTE_MAPPING_ERRORS\AttributeMappingErrors.ffs   # Source FME Feature Store (FFS) File(s)
- DestDataset_XLSXW = C:\Data\ATTRIBUTE_MAPPING_ERRORS\LookupTableAddOns.xlsx   # Destination Microsoft Excel File

Readers:
- FFS_1: FFS from $(SourceDataset_FFS)

Writers:
- XLSXW_1: XLSXW to $(DestDataset_XLSXW)

ATTRIBUTE_MAPPING_ERRORS (reader FFS_1)
    attributes: error varchar(200)
    -> StringSearcher
StringSearcher
    CASE = no
    MATCHED_RESULT_ATTR = format_error
    REGEXP = (?<=Unable to map value )(.*)(?= for attribute)
    STRING_TO_SEARCH = @Value(error)
    MATCHED -> DuplicateFilter
DuplicateFilter
    INPUT_ORDERED_CHOICE = No
    KEYATTR = format_error
    UNIQUE -> Sheet1 (writer XLSXW_1)
Sheet1 (writer XLSXW_1)
    attributes: error string(200), format_error auto(20)
