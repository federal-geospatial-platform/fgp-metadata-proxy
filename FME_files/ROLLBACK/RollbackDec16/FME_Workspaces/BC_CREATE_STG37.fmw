FME workspace BC_CREATE_STG37.fmw

Parameters:
- CSW_URL = http://ec2-35-182-113-175.ca-central-1.compute.amazonaws.com:80/csw   # CSW URL
- CSW_URL_AWS_SELECT_AB = http://ec2-35-183-211-115.ca-central-1.compute.amazonaws.com:80/csw   # CSW URL AWS_SELECT_AB
- CSW_URL_AWS_SELECT_BC = http://ec2-35-182-113-175.ca-central-1.compute.amazonaws.com:80/csw   # CSW URL AWS
- DELIMITER = ,   # Set iso_topic delimiter
- DestDataset_FFS = C:\Data\ATTRIBUTE_MAPPING_ERRORS\AttributeMappingErrors.ffs   # Destination FME Feature Store (FFS) File
- DestDataset_FFS_4 = C:\Data\FFS\BC_AllRecords_Translated.ffs   # Destination FME Feature Store (FFS) File
- DestDataset_TEXTLINE = C:\Data\bc_xml_result_local   # Destination Text File
- EMAIL_ADMIN = robert.bennett@canada.ca   # Enter Admin eMail
- EMAIL_ENCRYPTION = SSL
- EMAIL_HOST = smtp.mail.yahoo.com
- EMAIL_PORT = 465
- EMAIL_SENDER = robbennett@rocketmail.com
- EMAIL_SENDER_PASSWORD =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
- FANOUT_DIRECTORY_FAILED = C:\Data\bc_xml_failed   # Fanout Directory
- FANOUT_DIRECTORY_PASSED = C:\Data\bc_xml_result   # Fanout Directory
- IN_XLS_DEFAULTVALUE_FILE = C:\Data\LOOKUP_TABLES\BC_DefaultAttributeMapper.xlsx
- IN_XLS_LOOKUPTABLE_ROLE_FILE = C:\Data\LOOKUP_TABLES\RoleAttributeMapper.xlsx
- IN_XLS_LOOKUPTABLE_UPDATECYCLE_FILE = C:\Data\LOOKUP_TABLES\UpdateCycleAttributeMapper.xlsx
- IN_XLS_LOOKUPTABLE_SPATIALREP_FILE = C:\Data\LOOKUP_TABLES\SpatialRepresentationAttributeMapper.xlsx
- IN_XLS_LOOKUPTABLE_PROGSTATUS_FILE = C:\Data\LOOKUP_TABLES\ProgressStatusAttributeMapper.xlsx
- IN_XLS_LOOKUPTABLE_SPATIALREF_FILE = C:\Data\LOOKUP_TABLES\SpatialReferenceMapper.xlsx
- LOG_FILE = C:\Data\BC_Create.log   # Log File
- LOOP_ITERATIONS = 10   # Enter number of loops to query source data
- P-T_ABBR = BC   # Province-Territory Abbreviation
- QUERY_ITERATIONS = 1000   # Enter number of rows per iteration to query source data
- SELECT_METHOD = Local   # Select XML Creation Method
- TEMPLATE_GMD_CITEDRESPONSIBLEPARTY = C:\Data\XML_TEMPLATE\GMD_CITEDRESPONSIBLEPARTY.xml   # GMD_CITEDRESPONSIBLEPARTY Template File
- TEMPLATE_GMD_CONTACT = C:\Data\XML_TEMPLATE\GMD_CONTACT.xml
- TEMPLATE_GMD_DISTRIBUTIONFORMAT = C:\Data\XML_TEMPLATE\GMD_DISTRIBUTIONFORMAT.xml
- TEMPLATE_GMD_DISTRIBUTOR = C:\Data\XML_TEMPLATE\GMD_DISTRIBUTOR.xml
- TEMPLATE_GMD_KEYWORDS = C:\Data\XML_TEMPLATE\GMD_KEYWORDS.xml
- TEMPLATE_GMD_MDMETADATA = C:\Data\XML_TEMPLATE\GMD_MDMETADATA.xml
- TEMPLATE_GMD_ONLINERESOURCE = C:\Data\XML_TEMPLATE\GMD_ONLINERESOURCE.xml
- TEMPLATE_GMD_REFERENCESYSTEMINFO = C:\Data\XML_TEMPLATE\GMD_REFERENCESYSTEMINFO.xml
- TEMPLATE_GMD_RESOURCEMAINTENANCE = C:\Data\XML_TEMPLATE\GMD_RESOURCEMAINTENANCE.xml
- TEMPALTE_GMD_TOPICCATEGORY = C:\Data\XML_TEMPLATE\GMD_TOPICCATEGORY.xml
- TEMPLATE_GMD_TRANSFEROPTIONS = C:\Data\XML_TEMPLATE\GMD_TRANSFEROPTIONS.xml
- TIME_FILTER_DAYS = 0   # Enter preceding number of days to filter
- TIME_FILTER_MONTHS = 0   # Enter preceding number of months to filter
- SourceDataset_XLSXR_11 = C:\Data\LOOKUP_TABLES\Config_BC_XML_Publisher.xlsx   # Source Microsoft Excel File(s)
- SourceDataset_XLSXR_12 = C:\Data\LOOKUP_TABLES\FormatAttributeMapper.xlsx   # Source Microsoft Excel File(s)
- SourceDataset_XLSXR = C:\Data\LOOKUP_TABLES\Keyword.xlsx   # Source Microsoft Excel File(s)

Readers:
- XLSXR_1: XLSXR from $(IN_XLS_DEFAULTVALUE_FILE)
- XLSXR_2: XLSXR from $(SourceDataset_XLSXR_11)
- XLSXR_3: XLSXR from $(IN_XLS_LOOKUPTABLE_PROGSTATUS_FILE)
- XLSXR_4: XLSXR from $(IN_XLS_LOOKUPTABLE_ROLE_FILE)
- XLSXR_5: XLSXR from $(IN_XLS_LOOKUPTABLE_SPATIALREF_FILE)
- XLSXR_6: XLSXR from $(IN_XLS_LOOKUPTABLE_SPATIALREP_FILE)
- XLSXR_7: XLSXR from $(IN_XLS_LOOKUPTABLE_UPDATECYCLE_FILE)
- XLSXR_8: XLSXR from $(SourceDataset_XLSXR_12)
- XLSXR_9: XLSXR from $(SourceDataset_XLSXR)

Writers:
- TEXTLINE_1: TEXTLINE to $(FANOUT_DIRECTORY_PASSED)
- TEXTLINE_2: TEXTLINE to $(FANOUT_DIRECTORY_FAILED)
- FFS_1: FFS to $(DestDataset_FFS)
- FFS_2: FFS to $(DestDataset_FFS_4)
- TEXTLINE_3: TEXTLINE to $(DestDataset_TEXTLINE)

Note: Writes XML to a local folder without publishing to PyCSW, and without the PyCSW transaction headers and footers
text_line (writer TEXTLINE_3)
    attributes: text_line_data buffer
Note: Creates eMail notification of data translation results
NOTIFY_CREATE
    EMAIL_ADMIN = $(EMAIL_ADMIN)
    EMAIL_ENCRYPTION = $(EMAIL_ENCRYPTION)
    EMAIL_HOST = $(EMAIL_HOST)
    EMAIL_PORT = $(EMAIL_PORT)
    EMAIL_SENDER = $(EMAIL_SENDER)
    EMAIL_SENDER_PASSWORD = $(EMAIL_SENDER_PASSWORD)
    ID = @Value(id)
    P-T_ABBR = $(P-T_ABBR)
Note: Writes XML published to the PyCSW to a local folder
text_line (writer TEXTLINE_1)
    attributes: text_line_data buffer
Note: Writes XML that failed to publish to the PyCSW to a local folder
text_line (writer TEXTLINE_2)
    attributes: text_line_data buffer

Bookmark: Data extraction and french translation
Creator
    GEOMTYPE = Geometry Object
    NUM = 1
    CREATED -> BC_CREATE_PRETRANSLATE
Note: Custom transformer queries the British Columbia open government portal API, exposes returned attributes and filters data by open, geospatial data. It also contains a date filter for debugging purposes only.
BC_CREATE_PRETRANSLATE
    EMAIL_ADMIN = $(EMAIL_ADMIN)
    EMAIL_ENCRYPTION = $(EMAIL_ENCRYPTION)
    EMAIL_HOST = $(EMAIL_HOST)
    EMAIL_PORT = $(EMAIL_PORT)
    EMAIL_SENDER = $(EMAIL_SENDER)
    EMAIL_SENDER_PASSWORD = $(EMAIL_SENDER_PASSWORD)
    LOOP_ITERATIONS = $(LOOP_ITERATIONS)
    QUERY_ITERATIONS = $(QUERY_ITERATIONS)
    TIME_FILTER_DAYS = $(TIME_FILTER_DAYS)
    TIME_FILTER_MONTHS = $(TIME_FILTER_MONTHS)
    -> BC_GEOWAREHOUSE_URL_BUILDER
Note: Custom transformer sends specific extracted attributes to the Amazon translation service to be translated to French.
AWS_TRANSLATE
    -> DEFAULT_ATTRIBUTE_MAPPER
    -> BC_AllRecords_Translated (writer FFS_2)
BC_AllRecords_Translated (writer FFS_2)

Bookmark: BC resource formatter
Note: Concatenates URL for BC Geowarehouse download links
BC_GEOWAREHOUSE_URL_BUILDER
    -> BC_WMS_FORMATTER
Note: Concatenates WMS URL's to required WMS format
BC_WMS_FORMATTER
    -> BC_RESOURCE_NAME_CORRECTION
Note: Substitutes resource name with dataset title when resource name is missing
BC_RESOURCE_NAME_CORRECTION
    -> AWS_TRANSLATE

Bookmark: Default value and date management
BC_DEFAULT_ATTRIBUTES (reader XLSXR_1)
    attributes: default_key char(28), default_value char(134)
    -> DEFAULT_ATTRIBUTE_MAPPER [LOOKUP_TABLE_INPUT]
Note: Sets default attirbute values
DEFAULT_ATTRIBUTE_MAPPER
    -> TEMPORAL_EXTENTS_MAPPER
Note: Maps data collection start and end dates
TEMPORAL_EXTENTS_MAPPER
    -> TOPIC_PARSER

Bookmark: Topic extraction
Note: Parses topics into individual attributes when multiple topics appear as comma separated values
TOPIC_PARSER
    DELIMITER = $(DELIMITER)
    -> METADATA_VALUE_MAPPER_7 [DATA_INPUT]

Bookmark: Attribute value mapper
Keyword (reader XLSXR_9)
    attributes: original_value char(33), real_value_english char(33)
    -> METADATA_VALUE_MAPPER_7 [LOOKUP_TABLE_INPUT]
Note: Maps iso_topic to HNAP standards
METADATA_VALUE_MAPPER_7
    Att_To_map = iso_topic{}.topic_value
    CODE_REFRESH = NO
    ENGLISH_REFRESH = YES
    ERROR_NOT_MAPPED = YES
    FRENCH_REFRESH = NO
    -> METADATA_VALUE_MAPPER [DATA_INPUT]
    -> MAPPING_ERROR_LIST_CREATOR
Note: This section utilizes mulitple instances of the METADATA_VALUE_MAPPER to correct values to valid English values and to add the valid French equivalents and RI_CODES where applicable. It can be utilized for mulitple metadata items by accessing custom look up tables applicable to specific items. / Turn the error mapping options and the data items to be mapped on or off by clicking on the transformer and selecting yes/no. / - ERROR_NOT_MAPPED: enables mapping of data item values that cannot be found in the lookup tables. / - ENGLISH_REFRESH: enables updating of English attribute values. / - FRENCH_REFRESH: enables updating of French attribute values. / - CODE_REFRESH: enables updating of RI_CODE values. / Enter the attribute key name by clicking on the transformer and selecting the drop down menu next to the 'att_to_map' text box and selecting the 'Open text editor...' option. Explicitly enter the attribute key name in the text editor (ie: contacts{}.role). / IMPORTANT: Do not select the 'Attribute Value' option from the drop down menu to select the attribute key name.
Role (reader XLSXR_4)
    attributes: original_value char(22), real_value_english char(22), real_value_french char(21), code_value char(7)
    -> METADATA_VALUE_MAPPER [LOOKUP_TABLE_INPUT]
Note: Maps role to HNAP standards
METADATA_VALUE_MAPPER
    Att_To_map = contacts{}.role
    CODE_REFRESH = YES
    ENGLISH_REFRESH = YES
    ERROR_NOT_MAPPED = YES
    FRENCH_REFRESH = YES
    -> METADATA_VALUE_MAPPER_2 [DATA_INPUT]
    -> MAPPING_ERROR_LIST_CREATOR
Update (reader XLSXR_7)
    attributes: original_value char(12), real_value_english char(12), real_value_french char(14), code_value char(7)
    -> METADATA_VALUE_MAPPER_2 [LOOKUP_TABLE_INPUT]
Note: Maps update cycle to HNAP standards
METADATA_VALUE_MAPPER_2
    Att_To_map = resources{}.resource_update_cycle
    CODE_REFRESH = YES
    ENGLISH_REFRESH = YES
    ERROR_NOT_MAPPED = YES
    FRENCH_REFRESH = YES
    -> METADATA_VALUE_MAPPER_5 [DATA_INPUT]
    -> MAPPING_ERROR_LIST_CREATOR
Progress (reader XLSXR_3)
    attributes: original_value char(18), real_value_english char(18), real_value_french char(18), code_value char(7)
    -> METADATA_VALUE_MAPPER_5 [LOOKUP_TABLE_INPUT]
Note: Maps progress codes to HNAP standards
METADATA_VALUE_MAPPER_5
    Att_To_map = progress_code
    CODE_REFRESH = YES
    ENGLISH_REFRESH = YES
    ERROR_NOT_MAPPED = YES
    FRENCH_REFRESH = YES
    -> METADATA_VALUE_MAPPER_6 [DATA_INPUT]
    -> MAPPING_ERROR_LIST_CREATOR
SpatialRepresentation (reader XLSXR_6)
    attributes: original_value char(12), real_value_english char(12), real_value_french char(13), code_value char(7)
    -> METADATA_VALUE_MAPPER_6 [LOOKUP_TABLE_INPUT]
Note: Maps spatial representation types to HNAP standards
METADATA_VALUE_MAPPER_6
    Att_To_map = spatial_representation_type
    CODE_REFRESH = YES
    ENGLISH_REFRESH = YES
    ERROR_NOT_MAPPED = YES
    FRENCH_REFRESH = YES
    -> METADATA_VALUE_MAPPER_4 [DATA_INPUT]
    -> MAPPING_ERROR_LIST_CREATOR
SpatialRef (reader XLSXR_5)
    attributes: original_value char(47), real_value_english char(12)
    -> METADATA_VALUE_MAPPER_4 [LOOKUP_TABLE_INPUT]
Note: Maps spatial reference values to HNAP standards
METADATA_VALUE_MAPPER_4
    Att_To_map = resources{}.projection_name
    CODE_REFRESH = NO
    ENGLISH_REFRESH = YES
    ERROR_NOT_MAPPED = YES
    FRENCH_REFRESH = NO
    -> METADATA_FORMAT_MAPPER [DATA_INPUT]
    -> MAPPING_ERROR_LIST_CREATOR

Bookmark: Format value mapper
Note: This section utilizes the METADATA_FORMAT_MAPPER to correct data format values to valid data format values and to associate and add the French and English 'Resource Type' attribute to each data format type. It accesses a custom look up table applicable to data formats. / Turn the error mapping options and the data items to be mapped on or off by clicking on the transformer and selecting yes/no. / - ERROR_NOT_MAPPED: enables mapping of data item values that cannot be found in the lookup tables. / - REAL_VALUE_REFRESH: enables updating of data format attribute values. / - RES_TYPE_FR_REFRESH: enables mapping of French resource types. / - RES_TYPE_EN_REFRESH: enables mapping of English resource types. / Enter the attribute key name by clicking on the transformer and selecting the drop down menu next to the 'att_to_map' text box and selecting the 'Open text editor...' option. Explicitly enter the attribute key name in the text editor (ie: resources{}.format). / IMPORTANT: Do not select the 'Attribute Value' option from the drop down menu to select the attribute key name.
Format (reader XLSXR_8)
    attributes: original_value char(24), real_value char(10), resource_type_fr char(20), resource_type_en char(20)
    -> METADATA_FORMAT_MAPPER [LOOKUP_TABLE_INPUT]
Note: Maps data formats and resource types to HNAP standards
METADATA_FORMAT_MAPPER
    Att_To_map = resources{}.format
    ERROR_NOT_MAPPED = YES
    REAL_VALUE_REFRESH = YES
    RES_TYPE_EN_REFRESH = YES
    RES_TYPE_FR_REFRESH = YES
    -> RESOURCE_NAME_UNDERSCORE_REMOVER
    -> MAPPING_ERROR_LIST_CREATOR

Bookmark: Mapping error list creator
Note: Creates list of errors found and corrected in mapping
MAPPING_ERROR_LIST_CREATOR
    LIST_ATTR = mapping_errors{}
    LIST_NAME = mapping_errors{}
    -> ATTRIBUTE_MAPPING_ERRORS (writer FFS_1)
ATTRIBUTE_MAPPING_ERRORS (writer FFS_1)
    attributes: error varchar(200), _element_index varchar(200)

Bookmark: Data preparation for metadata section
Note: Removes all underscores from resources{}.name attributes. Long compounded names joined by underscores in this field can cause display formatting issues when published to the FGP.
RESOURCE_NAME_UNDERSCORE_REMOVER
    -> GMD_SECTION_DATA_EXTRACTION
Note: Creates lists and removes duplicates for GMD_Section
GMD_SECTION_DATA_EXTRACTION
    -> MORE_INFO_MANAGER
Note: Tests the more_info{}.link list for valid attribute values and filters them out where missing
MORE_INFO_MANAGER
    -> REMOVE_BROKEN_URL_WMS_ESRI_REST

Bookmark: Data cleanup. Dropping broken web services
Note: Tests WMS/ESRI_REST resource URL's and removes them where broken
REMOVE_BROKEN_URL_WMS_ESRI_REST
    -> WMS_REST_LANGUAGE_FORMATTER

Bookmark: HNAP Rules- 1 web service per language.
Note: Formats WMS and ESRI REST resources to add French versions and formats French and English versions with valid supporting attributes
WMS_REST_LANGUAGE_FORMATTER
    ADMIN_EMAIL = robert.bennett@canada.ca
    EMAIL_ENCRYPTION = SSL
    EMAIL_HOST = smtp.mail.yahoo.com
    EMAIL_PORT = 465
    EMAIL_SENDER = robbennett@rocketmail.com
    EMAIL_SENDER_PASSWORD =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
    -> DUPLICATE_SERVICE_REMOVER
Note: Removes duplicate WMS or ESRI REST resources where they exist, that would otherwise invalidate the dataset
DUPLICATE_SERVICE_REMOVER
    -> XML_PUBLISHER

Bookmark: XML CREATION AND WRITING
Note: Excel config file to map BC attributes to those required by XML templates
CONFIG_FILE (reader XLSXR_2)
    attributes: HNAP_ATTRIBUTES char(55), FEATURE_ATTRIBUTES char(61), METADATA_SECTION char(210)
    -> XML_PUBLISHER [CONFIG_FILE]
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
XML_PUBLISHER
    CSW_URL = $(CSW_URL_AWS_SELECT_AB)
    CSW_URL_AWS_SELECT_AB = $(CSW_URL_AWS_SELECT_AB)
    CSW_URL_AWS_SELECT_BC = $(CSW_URL_AWS_SELECT_BC)
    SELECT_METHOD = $(SELECT_METHOD)
    TEMPALTE_GMD_TOPICCATEGORY = $(TEMPALTE_GMD_TOPICCATEGORY)
    TEMPLATE_GMD_CITEDRESPONSIBLEPARTY = $(TEMPLATE_GMD_CITEDRESPONSIBLEPARTY)
    TEMPLATE_GMD_CONTACT = $(TEMPLATE_GMD_CONTACT)
    TEMPLATE_GMD_DISTRIBUTIONFORMAT = $(TEMPLATE_GMD_DISTRIBUTIONFORMAT)
    TEMPLATE_GMD_DISTRIBUTOR = $(TEMPLATE_GMD_DISTRIBUTOR)
    TEMPLATE_GMD_KEYWORDS = $(TEMPLATE_GMD_KEYWORDS)
    TEMPLATE_GMD_MDMETADATA = $(TEMPLATE_GMD_MDMETADATA)
    TEMPLATE_GMD_ONLINERESOURCE = $(TEMPLATE_GMD_ONLINERESOURCE)
    TEMPLATE_GMD_REFERENCESYSTEMINFO = $(TEMPLATE_GMD_REFERENCESYSTEMINFO)
    TEMPLATE_GMD_RESOURCEMAINTENANCE = $(TEMPLATE_GMD_RESOURCEMAINTENANCE)
    TEMPLATE_GMD_TRANSFEROPTIONS = $(TEMPLATE_GMD_TRANSFEROPTIONS)
    LOCAL -> text_line (writer TEXTLINE_3)
    INSERT_PASSED -> NOTIFY_CREATE [INSERTED]
    INSERT_PASSED -> text_line (writer TEXTLINE_1)
    INSERT_FAILED -> NOTIFY_CREATE [INSERT_FAILED]
    INSERT_FAILED -> text_line (writer TEXTLINE_2)
