FME workspace metrique_ab_create_pretranslate.fmw

Parameters:
- LOG_FILE =
- IN_FFS_FILE_1 =
- IN_FFS_FILE_2 =
- IN_FFS_FILE_3 =
- OUT_FFS_FILE_1 =
- OUT_FFS_FILE_2 =
- OUT_FFS_FILE_3 =
- CSW_QUERY_1 =
- CSW_QUERY_2 =
- CSW_QUERY_3 =
- EMAIL_ADMIN = robert.bennett@canada.ca
- EMAIL_ENCRYPTION = SSL
- EMAIL_HOST = smtp.mail.yahoo.com
- EMAIL_PORT = 465
- EMAIL_SENDER = robbennett@rocketmail.com
- EMAIL_SENDER_PASSWORD =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
- SAMPLE_SELECT = No
- SAMPLE_SIZE = 100
- TIME_FILTER_DAYS = 0
- TIME_FILTER_MONTHS = 0
- UNIT_TEST_HTTP_BYPASS = No

Readers:
- FFS_1: FFS from $(IN_FFS_FILE_1)
- FFS_2: FFS from $(IN_FFS_FILE_2)
- FFS_3: FFS from $(IN_FFS_FILE_3)

Writers:
- FFS_4: FFS to $(OUT_FFS_FILE_1)
- FFS_5: FFS to $(OUT_FFS_FILE_2)
- FFS_6: FFS to $(OUT_FFS_FILE_3)

source1 (reader FFS_1)
    attributes: _creation_instance varchar(200), _response_body varchar(200), _http_status_code varchar(200)
    -> AB_CREATE_PRETRANSLATE [UNIT_TEST_FFS_INPUT_1]
source2 (reader FFS_2)
    attributes: csw_query_2 varchar(200), _response_body varchar(200), _http_status_code varchar(200)
    -> AB_CREATE_PRETRANSLATE [UNIT_TEST_FFS_INPUT_2]
source3 (reader FFS_3)
    attributes: geodiscover_url varchar(200), id varchar(200), csw_query_2 varchar(200), _response_body varchar(200), _http_status_code varchar(200), SummaryRecord varchar(200), _element_index varchar(200), identifier{}.scheme varchar(200), identifier{} varchar(200), identifier varchar(200), _file_idscheme varchar(200), _file_ididentifier varchar(200), _list_index varchar(200)
    -> AB_CREATE_PRETRANSLATE [UNIT_TEST_FFS_INPUT_3]
Creator
    GEOMTYPE = Geometry Object
    NUM = 1
    CREATED -> AB_CREATE_PRETRANSLATE
AB_CREATE_PRETRANSLATE
    CSW_QUERY_1 = $(CSW_QUERY_1)
    CSW_QUERY_2 = $(CSW_QUERY_2)
    CSW_QUERY_3 = $(CSW_QUERY_3)
    EMAIL_ADMIN = $(EMAIL_ADMIN)
    EMAIL_ENCRYPTION = $(EMAIL_ENCRYPTION)
    EMAIL_HOST = $(EMAIL_HOST)
    EMAIL_PORT = $(EMAIL_PORT)
    EMAIL_SENDER = $(EMAIL_SENDER)
    EMAIL_SENDER_PASSWORD = $(EMAIL_SENDER_PASSWORD)
    SAMPLE_SELECT = $(SAMPLE_SELECT)
    SAMPLE_SIZE = $(SAMPLE_SIZE)
    TIME_FILTER_DAYS = $(TIME_FILTER_DAYS)
    TIME_FILTER_MONTHS = $(TIME_FILTER_MONTHS)
    UNIT_TEST_HTTP_BYPASS = $(UNIT_TEST_HTTP_BYPASS)
    UNIT_TEST_FFS_OUTPUT_1 -> resultat1 (writer FFS_4)
    UNIT_TEST_FFS_OUTPUT_2 -> resultat_2 (writer FFS_5)
    -> resultat_3 (writer FFS_6)
resultat1 (writer FFS_4)
    attributes: csw_query_2 varchar(200), start_number varchar(200), nb_query varchar(200), _creation_instance varchar(200), _response_body varchar(200), _http_status_code_1 varchar(200), _http_status_code varchar(200), SearchResults.numberOfRecordsMatched varchar(200), _copynum varchar(200)
resultat_2 (writer FFS_5)
    attributes: id varchar(200), csw_query_2 varchar(200), _response_body varchar(200), _http_status_code_2 varchar(200), _http_status_code varchar(200), SummaryRecord varchar(200), _element_index varchar(200), identifier{}.scheme varchar(200), identifier{} varchar(200), identifier varchar(200), _file_idscheme varchar(200), _file_ididentifier varchar(200), _list_index varchar(200)
resultat_3 (writer FFS_6)
    attributes: method varchar(200), test_url varchar(200), data_collection_start_date varchar(200), data_collection_end_date varchar(200), geodiscover_url varchar(200), id varchar(200), contacts{} varchar(200), record_last_modified varchar(200), metadata_standard varchar(200), metadata_standard_version varchar(200), title varchar(200), notes varchar(200), progress_code varchar(200), spatial_representation_type varchar(200), east_bound_longitude varchar(200), north_bound_latitude varchar(200), west_bound_longitude varchar(200), south_bound_latitude varchar(200), distributionList{} varchar(200), tags{} varchar(200), resource_update_cycle varchar(200), resources{} varchar(200), record_create_date varchar(200), record_publish_date varchar(200), iso_topic{} varchar(200), spatialref{} varchar(200), sector varchar(200)
