FME workspace BC_FGP_XML_BUILDER_STG03.fmw

Parameters:
- API_QUERY_1 = @Value(api_query_1)
- API_QUERY_2 = @Value(api_query_2)
- AWS_TRANSLATE_ON = Yes
- CREATE_NEW_DATABASE = No
- CSW_URL = http://ec2amaz-2hiajuv/pycsw?   # "%https://pycsw-bc.ddr-dev.cgp-pgc.ca/pycsw?%http://127.0.0.1:8080/pycsw CSW URL
- DELIMITER = ,
- EMAIL_ADMIN = robert.bennett@canada.ca
- EMAIL_ENCRYPTION = SSL
- EMAIL_HOST = smtp.mail.yahoo.com
- EMAIL_PORT = 465
- EMAIL_SENDER = robbennett@rocketmail.com
- EMAIL_SENDER_PASSWORD =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
- ENTITY_SEARCH_LITERAL = Columbia
- FANOUT_DIRECTORY_FAILED = $(FME_SHAREDRESOURCE_DATA)\PT_Harvester\BC\XML_FAILED
- FANOUT_DIRECTORY_PASSED = $(FME_SHAREDRESOURCE_DATA)\PT_Harvester\BC\XML_PASSED
- IN_XLS_LOOKUP = $(FME_SHAREDRESOURCE_DATA)\PT_Harvester\P-T_ETL_LOOKUP_TABLES.xlsx
- LOG_FILE = $(FME_SHAREDRESOURCE_DATA)\PT_Harvester\BC\LOG\BC_Create.log
- METHOD_SELECT = Auto
- OUT_FFS_MAPPING_ERROR = $(FME_SHAREDRESOURCE_DATA)\PT_Harvester\BC\FFS\AttributeMappingErrors.ffs
- OUT_FFS_TRANSLATED = $(FME_SHAREDRESOURCE_DATA)\PT_Harvester\BC\FFS\BC_AllRecords_Translated.ffs
- OUT_FFS_WEBSERVICE_ERROR = $(FME_SHAREDRESOURCE_DATA)\PT_Harvester\BC\FFS\web_service_error.ffs
- OUT_RESULT_FOLDER = $(FME_SHAREDRESOURCE_DATA)\PT_Harvester\BC\XML_LOCAL
- P-T_ABBR = BC
- SAMPLE_SELECT = No
- SAMPLE_SIZE = 250
- TEMPLATE_GMD_CITEDRESPONSIBLEPARTY = $(FME_SHAREDRESOURCE_DATA)\PT_Harvester\GMD_CITEDRESPONSIBLEPARTY.xml
- TEMPLATE_GMD_CONTACT = $(FME_SHAREDRESOURCE_DATA)\PT_Harvester\GMD_CONTACT.xml
- TEMPLATE_GMD_DISTRIBUTIONFORMAT = $(FME_SHAREDRESOURCE_DATA)\PT_Harvester\GMD_DISTRIBUTIONFORMAT.xml
- TEMPLATE_GMD_DISTRIBUTOR = $(FME_SHAREDRESOURCE_DATA)\PT_Harvester\GMD_DISTRIBUTOR.xml
- TEMPLATE_GMD_KEYWORDS = $(FME_SHAREDRESOURCE_DATA)\PT_Harvester\GMD_KEYWORDS.xml
- TEMPLATE_GMD_MDMETADATA = $(FME_SHAREDRESOURCE_DATA)\PT_Harvester\GMD_MDMETADATA.xml
- TEMPLATE_GMD_REFERENCESYSTEMINFO = $(FME_SHAREDRESOURCE_DATA)\PT_Harvester\GMD_REFERENCESYSTEMINFO.xml
- TEMPLATE_GMD_RESOURCEMAINTENANCE = $(FME_SHAREDRESOURCE_DATA)\PT_Harvester\GMD_RESOURCEMAINTENANCE.xml
- TEMPLATE_GMD_TOPICCATEGORY = $(FME_SHAREDRESOURCE_DATA)\PT_Harvester\GMD_TOPICCATEGORY.xml
- TEMPLATE_GMD_TRANSFEROPTIONS = $(FME_SHAREDRESOURCE_DATA)\PT_Harvester\GMD_TRANSFEROPTIONS.xml
- TIME_FILTER_DAYS = 7
- TIME_FILTER_MONTHS = 0
- TIME_STAMP = @Value(_timestamp)   # "{}" TIME_STAMP
- UNIT_TEST_HTTP_BYPASS = No
- UNIT_TEST_PYCSW_BYPASS = No
- TEST_URL = @Value(test_url)   # test url
- FME_SHAREDRESOURCE_DATA = C:\Data   # FME Server Resource Data

Readers:
- XLSXR_1: XLSXR from $(IN_XLS_LOOKUP)

Writers:
- TEXTLINE_1: TEXTLINE to $(FANOUT_DIRECTORY_PASSED)
- TEXTLINE_2: TEXTLINE to $(FANOUT_DIRECTORY_FAILED)
- FFS_1: FFS to $(OUT_FFS_MAPPING_ERROR)
- FFS_2: FFS to $(OUT_FFS_TRANSLATED)
- TEXTLINE_3: TEXTLINE to $(OUT_RESULT_FOLDER)
- FFS_3: FFS to $(OUT_FFS_WEBSERVICE_ERROR)

Creator
    GEOMTYPE = Geometry Object
    NUM = 1
    CREATED -> BC_DATA_EXTRACTION [CSW_QUERY]
    CREATED -> BC_DATA_EXTRACTION [API_QUERY]
web_service_error (writer FFS_3)
    attributes: id varchar(200), description varchar(200), format varchar(200), name varchar(200), projection_name varchar(200), resource_update_cycle varchar(200), url varchar(200), resources varchar(200), name_fr varchar(200), protocol varchar(200), _uuid varchar(200), _element_index varchar(200), resource_update_cycle_code varchar(200), resource_update_cycle_fr varchar(200), _error varchar(200), fme_rejection_code varchar(200), _response_body varchar(200), _http_status_code varchar(200), _url_failure_message varchar(200)
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer
RESULTS_NOTIFICATION
    CSW_ID = @Value(csw_id)
    EMAIL_ADMIN = robert.bennett@canada.ca
    EMAIL_ENCRYPTION = SSL
    EMAIL_HOST = smtp.mail.yahoo.com
    EMAIL_PORT = 465
    EMAIL_RESULTS = No
    EMAIL_SENDER = robbennett@rocketmail.com
    EMAIL_SENDER_PASSWORD =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
    ID = @Value(id)

Bookmark: Extracting data from BC Portal
BC_DATA_EXTRACTION
    API_QUERY_1 = $(API_QUERY_1)
    API_QUERY_2 = $(API_QUERY_2)
    CREATE_NEW_DATABASE = $(CREATE_NEW_DATABASE)
    EMAIL_ADMIN = $(EMAIL_ADMIN)
    EMAIL_ENCRYPTION = $(EMAIL_ENCRYPTION)
    EMAIL_HOST = $(EMAIL_HOST)
    EMAIL_PORT = $(EMAIL_PORT)
    EMAIL_SENDER = $(EMAIL_SENDER)
    EMAIL_SENDER_PASSWORD = $(EMAIL_SENDER_PASSWORD)
    ENTITY_SEARCH_LITERAL = $(ENTITY_SEARCH_LITERAL)
    SAMPLE_SELECT = $(SAMPLE_SELECT)
    SAMPLE_SIZE = $(SAMPLE_SIZE)
    TIME_FILTER_DAYS = $(TIME_FILTER_DAYS)
    TIME_FILTER_MONTHS = $(TIME_FILTER_MONTHS)
    TIME_STAMP = $(TIME_STAMP)
    UNIT_TEST_HTTP_BYPASS = $(UNIT_TEST_HTTP_BYPASS)
    UNIT_TEST_PYCSW_BYPASS = $(UNIT_TEST_PYCSW_BYPASS)
    NO_DELETED_RECORDS_COUNT -> RESULTS_NOTIFICATION [NO_RECORDS_DELETED_COUNT]
    DELETED_RECORDS_COUNT -> RESULTS_NOTIFICATION [RECORDS_DELETED_COUNT]
    NEW_RECORDS_COUNT -> RESULTS_NOTIFICATION [NEW_RECORDS_COUNT]
    TOTAL_RECORDS_COUNT -> RESULTS_NOTIFICATION [TOTAL_RECORDS_COUNT]
    -> FORMAT_VALIDATOR [PythonCaller_Input]
    UPDATED_RECORDS_COUNT -> RESULTS_NOTIFICATION [UPDATED_RECORDS_COUNT]

Bookmark: Attribute Validation
Note: Verfication if URL is valid WMS call for WMS formats
FORMAT_VALIDATOR
    PythonCaller_Output -> EMAIL_FORMAT_TESTER
Note: Tests for '@' in email addresses
EMAIL_FORMAT_TESTER
    -> BC_GEOWAREHOUSE_URL_BUILDER

Bookmark: BC resource formatter
Note: Concatenates URL for BC Geowarehouse download links
BC_GEOWAREHOUSE_URL_BUILDER
    -> BC_WMS_FORMATTER
Note: Concatenates WMS URL's to required WMS format
BC_WMS_FORMATTER
    -> BC_RESOURCE_NAME_CORRECTION
Note: Substitutes resource name with dataset title when resource name is missing
BC_RESOURCE_NAME_CORRECTION
    -> SELECT

Bookmark: Language Translation
Note: NOTE: AWS_TRANSLATE tools only function in the AWS Server environment. Published parameter AWS_TRANSLATE_ON switches between translate tool or proxy. Using proxy saves on translation fees when developing/testing, or allows user to run tool outside of AWS Server.
SELECT: Tester
    BOOL_OP = OR
    TEST_CLAUSE = TEST $(AWS_TRANSLATE_ON) = Yes
    TEST_MODE = TEST
    PASSED -> AWS_TRANSLATE_ENGLISH_TO_FRENCH
    FAILED -> FRENCH_TRANSLATION_PROXY_BUILDER
Note: Proxy transformer used for development testing in place of AWS Translate.
FRENCH_TRANSLATION_PROXY_BUILDER
    -> DEFAULT_ATTRIBUTE_MAPPER
Note: Custom transformer sends specific extracted attributes to the Amazon translation service to be translated to French.
AWS_TRANSLATE_ENGLISH_TO_FRENCH
    UNIT_TEST_AWS_BYPASS = No
    -> BC_AllRecords_Translated (writer FFS_2)
    -> DEFAULT_ATTRIBUTE_MAPPER
Note: FFS File for post translation data to save costs in the event tool has to be rerun after this point
BC_AllRecords_Translated (writer FFS_2)
    attributes: id varchar(200), test_url varchar(200), method varchar(200), _creation_instance varchar(200), east_bound_longitude varchar(200), iso_topic_string varchar(200), license_title varchar(200), metadata_standard_version varchar(200), more_info{}.link varchar(200), name varchar(200), north_bound_latitude varchar(200), notes varchar(200), projection varchar(200), record_create_date varchar(200), record_last_modified varchar(200), record_publish_date varchar(200), resources{}.data_collection_end_date varchar(200), resources{}.data_collection_start_date varchar(200), resources{}.description varchar(200), resources{}.format varchar(200), resources{}.id varchar(200), resources{}.name varchar(200), resources{}.projection_name varchar(200), resources{}.resource_update_cycle varchar(200), resources{}.url varchar(200), sector varchar(200), south_bound_latitude varchar(200), spatial varchar(200), spatial_datatypes varchar(200), tags{}.display_name varchar(200),
      title varchar(200), west_bound_longitude varchar(200), email varchar(200), role varchar(200), role_code varchar(200), role_fr varchar(200), position varchar(200), position_fr varchar(200), contacts{}.email varchar(200), contacts{}.name varchar(200), contacts{}.role varchar(200), contacts{}.role_code varchar(200), contacts{}.role_fr varchar(200), contacts{}.position varchar(200), contacts{}.position_fr varchar(200), resources{} varchar(200), data_collection_end_date varchar(200), data_collection_start_date varchar(200), description varchar(200), format varchar(200), projection_name varchar(200), resource_update_cycle varchar(200), url varchar(200), resources varchar(200), title_fr varchar(200), sector_fr varchar(200), notes_fr varchar(200), tags{}.display_name_fr varchar(200), resources{}.name_fr varchar(200)

Bookmark: Default value and date management
Default_BC (reader XLSXR_1)
    attributes: default_key char(46), default_value char(236)
    -> DEFAULT_ATTRIBUTE_MAPPER [LOOKUP_TABLE_INPUT]
Note: Sets default attirbute values
DEFAULT_ATTRIBUTE_MAPPER
    -> TEMPORAL_EXTENTS_MAPPER
Note: Maps data collection start and end dates
TEMPORAL_EXTENTS_MAPPER
    -> TOPIC_PARSER

Bookmark: Topic extraction
Note: Parses topics into individual attributes when multiple topics appear as comma separated values
TOPIC_PARSER
    DELIMITER = $(DELIMITER)
    -> METADATA_VALUE_MAPPER_7 [DATA_INPUT]

Bookmark: Attribute value mapper
Keyword (reader XLSXR_1)
    attributes: original_value char(33), real_value_english char(33)
    -> METADATA_VALUE_MAPPER_7 [LOOKUP_TABLE_INPUT]
Note: Maps iso_topic to HNAP standards
METADATA_VALUE_MAPPER_7
    ATT_TO_MAP = iso_topic{}.topic_value
    CODE_REFRESH = NO
    ENGLISH_REFRESH = YES
    ERROR_NOT_MAPPED = YES
    FRENCH_REFRESH = NO
    -> METADATA_VALUE_MAPPER [DATA_INPUT]
    -> MAPPING_ERROR_LIST_CREATOR
Role (reader XLSXR_1)
    attributes: original_value char(22), real_value_english char(22), real_value_french char(21), code_value char(7)
    -> METADATA_VALUE_MAPPER [LOOKUP_TABLE_INPUT]
Note: Maps role to HNAP standards
METADATA_VALUE_MAPPER
    ATT_TO_MAP = contacts{}.role
    CODE_REFRESH = YES
    ENGLISH_REFRESH = YES
    ERROR_NOT_MAPPED = YES
    FRENCH_REFRESH = YES
    -> METADATA_VALUE_MAPPER_2 [DATA_INPUT]
    -> MAPPING_ERROR_LIST_CREATOR
Note: This section utilizes mulitple instances of the METADATA_VALUE_MAPPER to correct values to valid English values and to add the valid French equivalents and RI_CODES where applicable. It can be utilized for mulitple metadata items by accessing custom look up tables applicable to specific items. / Turn the error mapping options and the data items to be mapped on or off by clicking on the transformer and selecting yes/no. / - ERROR_NOT_MAPPED: enables mapping of data item values that cannot be found in the lookup tables. / - ENGLISH_REFRESH: enables updating of English attribute values. / - FRENCH_REFRESH: enables updating of French attribute values. / - CODE_REFRESH: enables updating of RI_CODE values. / Enter the attribute key name by clicking on the transformer and selecting the drop down menu next to the 'att_to_map' text box and selecting the 'Open text editor...' option. Explicitly enter the attribute key name in the text editor (ie: contacts{}.role). / IMPORTANT: Do not select the 'Attribute Value' option from the drop down menu to select the attribute key name.
Update (reader XLSXR_1)
    attributes: original_value char(13), real_value_english char(12), real_value_french char(14), code_value char(7)
    -> METADATA_VALUE_MAPPER_2 [LOOKUP_TABLE_INPUT]
Note: Maps update cycle to HNAP standards
METADATA_VALUE_MAPPER_2
    ATT_TO_MAP = resource_update_cycle
    CODE_REFRESH = YES
    ENGLISH_REFRESH = YES
    ERROR_NOT_MAPPED = YES
    FRENCH_REFRESH = YES
    -> METADATA_VALUE_MAPPER_5 [DATA_INPUT]
    -> MAPPING_ERROR_LIST_CREATOR
Progress (reader XLSXR_1)
    attributes: original_value char(18), real_value_english char(18), real_value_french char(18), code_value char(7)
    -> METADATA_VALUE_MAPPER_5 [LOOKUP_TABLE_INPUT]
Note: Maps progress codes to HNAP standards
METADATA_VALUE_MAPPER_5
    ATT_TO_MAP = progress_code
    CODE_REFRESH = YES
    ENGLISH_REFRESH = YES
    ERROR_NOT_MAPPED = YES
    FRENCH_REFRESH = YES
    -> METADATA_VALUE_MAPPER_6 [DATA_INPUT]
    -> MAPPING_ERROR_LIST_CREATOR
SpatialRepresentation (reader XLSXR_1)
    attributes: original_value char(12), real_value_english char(12), real_value_french char(13), code_value char(7)
    -> METADATA_VALUE_MAPPER_6 [LOOKUP_TABLE_INPUT]
Note: Maps spatial representation types to HNAP standards
METADATA_VALUE_MAPPER_6
    ATT_TO_MAP = spatial_representation_type
    CODE_REFRESH = YES
    ENGLISH_REFRESH = YES
    ERROR_NOT_MAPPED = YES
    FRENCH_REFRESH = YES
    -> METADATA_VALUE_MAPPER_4 [DATA_INPUT]
    -> MAPPING_ERROR_LIST_CREATOR
SpatialRef (reader XLSXR_1)
    attributes: original_value char(47), real_value_english char(12)
    -> METADATA_VALUE_MAPPER_4 [LOOKUP_TABLE_INPUT]
Note: Maps spatial reference values to HNAP standards
METADATA_VALUE_MAPPER_4
    ATT_TO_MAP = resources{}.projection_name
    CODE_REFRESH = NO
    ENGLISH_REFRESH = YES
    ERROR_NOT_MAPPED = YES
    FRENCH_REFRESH = NO
    -> METADATA_FORMAT_MAPPER [DATA_INPUT]
    -> MAPPING_ERROR_LIST_CREATOR

Bookmark: Format value mapper
Format (reader XLSXR_1)
    attributes: original_value char(160), real_value char(10), resource_type_fr char(20), resource_type_en char(20)
    -> METADATA_FORMAT_MAPPER [LOOKUP_TABLE_INPUT]
Note: This section utilizes the METADATA_FORMAT_MAPPER to correct data format values to valid data format values and to associate and add the French and English 'Resource Type' attribute to each data format type. It accesses a custom look up table applicable to data formats. / Turn the error mapping options and the data items to be mapped on or off by clicking on the transformer and selecting yes/no. / - ERROR_NOT_MAPPED: enables mapping of data item values that cannot be found in the lookup tables. / - REAL_VALUE_REFRESH: enables updating of data format attribute values. / - RES_TYPE_FR_REFRESH: enables mapping of French resource types. / - RES_TYPE_EN_REFRESH: enables mapping of English resource types. / Enter the attribute key name by clicking on the transformer and selecting the drop down menu next to the 'att_to_map' text box and selecting the 'Open text editor...' option. Explicitly enter the attribute key name in the text editor (ie: resources{}.format). / IMPORTANT: Do not select the 'Attribute Value' option from the drop down menu to select the attribute key name.
METADATA_FORMAT_MAPPER
    ATT_TO_MAP = resources{}.format
    ERROR_NOT_MAPPED = YES
    REAL_VALUE_REFRESH = YES
    RES_TYPE_EN_REFRESH = YES
    RES_TYPE_FR_REFRESH = YES
    -> MAPPING_ERROR_LIST_CREATOR
    -> RESOURCE_NAME_UNDERSCORE_REMOVER

Bookmark: Mapping error list creator
Note: Creates list of errors found and corrected in mapping
MAPPING_ERROR_LIST_CREATOR
    LIST_ATTR = mapping_errors{}
    LIST_NAME = mapping_errors{}
    -> ATTRIBUTE_MAPPING_ERRORS (writer FFS_1)
ATTRIBUTE_MAPPING_ERRORS (writer FFS_1)
    attributes: error varchar(200), _element_index varchar(200)

Bookmark: Data preparation for metadata section
Note: Removes all underscores from resources{}.name attributes. Long compounded names joined by underscores in this field can cause display formatting issues when published to the FGP.
RESOURCE_NAME_UNDERSCORE_REMOVER
    -> GMD_SECTION_DATA_EXTRACTION
Note: Creates lists and removes duplicates for GMD_Section
GMD_SECTION_DATA_EXTRACTION
    -> MORE_INFO_MANAGER
Note: Tests the more_info{}.link list for valid attribute values and filters them out where missing
MORE_INFO_MANAGER
    -> REMOVE_BROKEN_URL_WMS_ESRI_REST

Bookmark: Data cleanup. Dropping broken web services
Note: Tests WMS/ESRI_REST resource URL's and removes them where broken
REMOVE_BROKEN_URL_WMS_ESRI_REST
    -> WMS_REST_LANGUAGE_FORMATTER
    FAULTY_URL_OUTPUT -> web_service_error (writer FFS_3)

Bookmark: HNAP Rules- 1 web service per language.
Note: Formats WMS and ESRI REST resources to add French versions and formats French and English versions with valid supporting attributes
WMS_REST_LANGUAGE_FORMATTER
    ADMIN_EMAIL = $(EMAIL_ADMIN)
    EMAIL_ENCRYPTION = $(EMAIL_ENCRYPTION)
    EMAIL_HOST = $(EMAIL_HOST)
    EMAIL_PORT = $(EMAIL_PORT)
    EMAIL_SENDER = $(EMAIL_SENDER)
    EMAIL_SENDER_PASSWORD = $(EMAIL_SENDER_PASSWORD)
    -> DUPLICATE_SERVICE_REMOVER
Note: Removes duplicate WMS or ESRI REST resources where they exist, that would otherwise invalidate the dataset
DUPLICATE_SERVICE_REMOVER
    -> BC_GEOPORTAL_WEBLINK_ADDER

Bookmark: Add geoportal weblink
Note: Creates additional entry in resources{} list based upon element count and adds required elements. Concatenate URL to BC Geoportal Weblink
BC_GEOPORTAL_WEBLINK_ADDER
    EMAIL_ADMIN = $(EMAIL_ADMIN)
    EMAIL_ENCRYPTION = $(EMAIL_ENCRYPTION)
    EMAIL_HOST = $(EMAIL_HOST)
    EMAIL_PORT = $(EMAIL_PORT)
    EMAIL_SENDER = $(EMAIL_SENDER)
    EMAIL_SENDER_PASSWORD = $(EMAIL_SENDER_PASSWORD)
    TEST_URL = $(TEST_URL)
    -> XML_PUBLISHER

Bookmark: XML CREATION AND WRITING
Note: Excel config file to map BC attributes to those required by XML templates
Config_BC (reader XLSXR_1)
    attributes: HNAP_ATTRIBUTES char(54), FEATURE_ATTRIBUTES char(60), METADATA_SECTION char(191)
    -> XML_PUBLISHER [CONFIG_FILE]
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
XML_PUBLISHER
    CSW_URL = http://pycsw-6ee5e20/pycsw?
    METHOD_SELECT = $(METHOD_SELECT)
    TEMPLATE_GMD_CITEDRESPONSIBLEPARTY = $(TEMPLATE_GMD_CITEDRESPONSIBLEPARTY)
    TEMPLATE_GMD_CONTACT = $(TEMPLATE_GMD_CONTACT)
    TEMPLATE_GMD_DISTRIBUTIONFORMAT = $(TEMPLATE_GMD_DISTRIBUTIONFORMAT)
    TEMPLATE_GMD_DISTRIBUTOR = $(TEMPLATE_GMD_DISTRIBUTOR)
    TEMPLATE_GMD_KEYWORDS = $(TEMPLATE_GMD_KEYWORDS)
    TEMPLATE_GMD_MDMETADATA = $(TEMPLATE_GMD_MDMETADATA)
    TEMPLATE_GMD_REFERENCESYSTEMINFO = $(TEMPLATE_GMD_REFERENCESYSTEMINFO)
    TEMPLATE_GMD_RESOURCEMAINTENANCE = $(TEMPLATE_GMD_RESOURCEMAINTENANCE)
    TEMPLATE_GMD_TOPICCATEGORY = $(TEMPLATE_GMD_TOPICCATEGORY)
    TEMPLATE_GMD_TRANSFEROPTIONS = $(TEMPLATE_GMD_TRANSFEROPTIONS)
    LOCAL -> text_line (writer TEXTLINE_3)
    INSERT_PASSED -> text_line (writer TEXTLINE_1)
    INSERT_PASSED -> RESULTS_NOTIFICATION [INSERTED]
    INSERT_FAILED -> text_line (writer TEXTLINE_2)
    INSERT_FAILED -> RESULTS_NOTIFICATION [INSERT_REJECTED]
    UPDATE_PASSED -> text_line (writer TEXTLINE_1)
    UPDATE_PASSED -> RESULTS_NOTIFICATION [UPDATED]
    UPDATE_FAILED -> text_line (writer TEXTLINE_2)
    UPDATE_FAILED -> RESULTS_NOTIFICATION [UPDATE_REJECTED]

Bookmark: Data extraction and french translation
Note: Custom transformer queries the British Columbia open government portal API and exposes returned attributes and filters data by open, geospatial data and date. It also validates the currency of PyCSW metadata records and removes those that no longer exist in the BC open government portal.
