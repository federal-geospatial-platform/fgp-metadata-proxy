FME workspace metrique_bc_attribute_formatter.fmw

Parameters:
- LOG_FILE = a.log
- OUT_FFS_FILE = resultat1.ffs

Writers:
- FFS_1: FFS to $(OUT_FFS_FILE)

Creator
    GEOMTYPE = Geometry Object
    NUM = 1
    CREATED -> AttributeCreator
    CREATED -> AttributeCreator_2
    CREATED -> AttributeCreator_3
    CREATED -> AttributeCreator_4
    CREATED -> AttributeCreator_5
Note: All fields have a valid content
AttributeCreator
    ATTR_TABLE:
      SET_TO record_create_date = 2020-05-25
      SET_TO record_publish_date = 2021-01-21
      SET_TO resources{0}.name = Name of the resources
      SET_TO contacts = [("name":"Annika Livingston","email":"annika.livingston@gov.bc.ca","org":"d2e433a1-b785-4d03-8a2b-392069175eb4","role":"pointOfContact","displayed":""),("name":"DataBC Operations","email":"data@gov.bc.ca","org":"d2e433a1-b785-4d03-8a2b-392069175eb4","role":"pointOfContact","displayed":true)]
      SET_TO record_last_modified = 2020-07-07
    -> BC_ATTRIBUTE_FORMATTER
Note: record_create_date is missing
AttributeCreator_2
    ATTR_TABLE:
      SET_TO record_create_date = 2020-05-25
      SET_TO record_publish_date = 2021-01-21
      SET_TO resources{0}.name = Name of the resources
      SET_TO contacts = [("name":"Annika Livingston","email":"annika.livingston@gov.bc.ca","org":"d2e433a1-b785-4d03-8a2b-392069175eb4","role":"pointOfContact","displayed":""),("name":"DataBC Operations","email":"data@gov.bc.ca","org":"d2e433a1-b785-4d03-8a2b-392069175eb4","role":"pointOfContact","displayed":true)]
      SET_TO record_last_modified = 2020-07-07
    -> BC_ATTRIBUTE_FORMATTER
Note: No resources
AttributeCreator_3
    ATTR_TABLE:
      SET_TO record_create_date = 2020-05-25
      SET_TO record_publish_date = 2021-01-21
      SET_TO contacts = [("name":"Annika Livingston","email":"annika.livingston@gov.bc.ca","org":"d2e433a1-b785-4d03-8a2b-392069175eb4","role":"pointOfContact","displayed":""),("name":"DataBC Operations","email":"data@gov.bc.ca","org":"d2e433a1-b785-4d03-8a2b-392069175eb4","role":"pointOfContact","displayed":true)]
      SET_TO record_last_modified = 2020-07-07
    -> BC_ATTRIBUTE_FORMATTER
Note: Date is invalid
AttributeCreator_4
    ATTR_TABLE:
      SET_TO record_create_date = 2020-05-25
      SET_TO record_publish_date = 2021-01-21
      SET_TO resources{0}.name = Name of the resources
      SET_TO contacts = [("name":"Annika Livingston","email":"annika.livingston@gov.bc.ca","org":"d2e433a1-b785-4d03-8a2b-392069175eb4","role":"pointOfContact","displayed":""),("name":"DataBC Operations","email":"data@gov.bc.ca","org":"d2e433a1-b785-4d03-8a2b-392069175eb4","role":"pointOfContact","displayed":true)]
      SET_TO record_last_modified = 2020a-07-07
    -> BC_ATTRIBUTE_FORMATTER
Note: contacts JSON document is not well formed
AttributeCreator_5
    ATTR_TABLE:
      SET_TO record_create_date = 2020-05-25
      SET_TO record_publish_date = 2021-01-21
      SET_TO resources{0}.name = Name of the resources
      SET_TO contacts = [("name"::"Annika Livingston","email":"annika.livingston@gov.bc.ca","org":"d2e433a1-b785-4d03-8a2b-392069175eb4","role":"pointOfContact","displayed":""),("name":"DataBC Operations","email":"data@gov.bc.ca","org":"d2e433a1-b785-4d03-8a2b-392069175eb4","role":"pointOfContact","displayed":true)]
      SET_TO record_last_modified = 2020-07-07
    -> BC_ATTRIBUTE_FORMATTER
BC_ATTRIBUTE_FORMATTER
    NO_RESOURCES -> out_ffs (writer FFS_1)
    INVALID_DATE -> out_ffs (writer FFS_1)
    INVALID_CONTACTS -> out_ffs (writer FFS_1)
    -> out_ffs (writer FFS_1)
out_ffs (writer FFS_1)
