FME workspace metrique_on_api_geohub_resources_keywords_manager.fmw

Parameters:
- IN_FFS_FILE_1 =
- IN_FFS_FILE_2 =
- LOG_FILE =
- OUT_FFS_FILE =
- TEST_URL = @Value(test_url)   # test url

Readers:
- FFS_1: FFS from $(IN_FFS_FILE_1)
- FFS_3: FFS from $(IN_FFS_FILE_2)

Writers:
- FFS_2: FFS to $(OUT_FFS_FILE)

OTOTO (reader FFS_1)
    -> ON_API_GEOHUB_RESOURCES_KEYWORDS_MERGER [API_DATA_INPUT]
source2 (reader FFS_3)
    attributes: resources{}.format varchar(200), resources{}.url varchar(200), title varchar(200), resources{}.name varchar(200), notes varchar(200), links.esriRest varchar(200), id varchar(200), licenseInfo varchar(200), item varchar(200), itemType varchar(200), extent{}.array{} varchar(200), spatialReference varchar(200), last_modified varchar(200), publish_date varchar(200), sector varchar(51), email varchar(19), name varchar(51), tags{}.display_name varchar(200), uuid_spatial varchar(200), spatial_representation_type varchar(5)
    -> ON_API_GEOHUB_RESOURCES_KEYWORDS_MERGER [GEOHUB_DATA_INPUT]
ON_API_GEOHUB_RESOURCES_KEYWORDS_MERGER
    -> out_ffs (writer FFS_2)
out_ffs (writer FFS_2)
