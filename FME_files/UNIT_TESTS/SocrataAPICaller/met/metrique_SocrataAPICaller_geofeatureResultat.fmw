FME workspace metrique_SocrataAPICaller_geofeatureResultat.fmw

Parameters:
- IN_FFS_FILE =
- LOG_FILE =
- OUT_FFS_FILE =
- LOOKUP_TABLE_GEODATATYPES =
- LOOKUP_TABLE_REMOVE =
- UNIT_TEST = No   # Unit Test Mode
- SocrataAppToken = FL3Cxsebg0Vf6JQ0CnbMujHkQ   # Socrata App Token
- Socrata_Domain = gnb.socrata.com   # Enter the Socrata Domain (without https)

Readers:
- FFS_1: FFS from $(IN_FFS_FILE)
- CSV2_2: CSV2 from $(LOOKUP_TABLE_GEODATATYPES)
- CSV2_1: CSV2 from $(LOOKUP_TABLE_REMOVE)

Writers:
- FFS_2: FFS to $(OUT_FFS_FILE)

Note: source
OTOTO (reader FFS_1)
    -> SocrataAPICaller [feature_input]
Note: Removelookup
CSV (reader CSV2_1)
    attributes: dataid string, keep string
    -> SocrataAPICaller [Dataset_Removal_Table]
Note: geotypes_lookup
CSV (reader CSV2_2)
    attributes: datatype string
    -> SocrataAPICaller [Geospatial_Datatypes_Lookup_Table]
SocrataAPICaller
    SocrataAppToken = $(SocrataAppToken)
    Socrata_Domain = $(Socrata_Domain)
    UNIT_TEST = $(UNIT_TEST)
    feature_output -> out_ffs (writer FFS_2)
out_ffs (writer FFS_2)
    attributes: True_Ids{}.geomcol varchar(200), True_Ids{}.geomtype varchar(200), True_Ids{}.trueid varchar(200), _creation_instance varchar(200), _toto varchar(200), currentDatasetCount varchar(200), iteration varchar(200), resource.type varchar(200), resource.id varchar(200), permalink varchar(200), resource.columns_datatype{} varchar(200), resource.columns_field_name{} varchar(200), geomidx varchar(200), fme_rejection_code varchar(200)
