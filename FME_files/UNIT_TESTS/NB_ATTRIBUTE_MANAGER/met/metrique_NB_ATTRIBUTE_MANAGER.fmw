FME workspace metrique_NB_ATTRIBUTE_MANAGER.fmw

Parameters:
- IN_FFS_FILE = $(FME_MF_DIR)source_8.ffs
- LOG_FILE =
- OUT_FFS_FILE = $(FME_MF_DIR)resultat_8.ffs

Readers:
- FFS_1: FFS from $(IN_FFS_FILE)

Writers:
- FFS_2: FFS to $(OUT_FFS_FILE)

Note: source
OTOTO (reader FFS_1)
    -> NB_ATTRIBUTE_MANAGER
NB_ATTRIBUTE_MANAGER
    -> AttributeCreator
    error_datetime_output -> AttributeCreator_2
AttributeCreator
    ATTR_TABLE = SET_TO output_port = Feature_Output
    -> out_ffs (writer FFS_2)
AttributeCreator_2
    ATTR_TABLE = SET_TO output_port = error_datetime_output
    -> out_ffs (writer FFS_2)
out_ffs (writer FFS_2)
    attributes: output_port varchar(200), nom_organisation_fr varchar(200), nom_organisation_en varchar(200), sector varchar(200), sector_fr varchar(200), org_name_temp varchar(200), spatialref{}.projection_name varchar(200), spatialref{}.projection_system varchar(200), spatialref{}.projection_system_version varchar(200), id varchar(200), UNIQUE_ATT varchar(200), resource.id varchar(200), resource.type varchar(200), assetType varchar(200), default_domain_tag varchar(200), tags{} varchar(200), metadata.custom_fields.Department / Ministère.Department / Ministère varchar(200), attribution varchar(200), default_sector_en varchar(200), default_sector_fr varchar(200), default_projection_name varchar(200), default_projection_system_version varchar(200), default_reference_system varchar(200), category varchar(200), default_category varchar(200), p-t_entity varchar(200), p-t_entity_fr varchar(200), _list{} varchar(200), _element_count uint64, publicationDate varchar(200),
      createdAt varchar(200), viewLastModified varchar(200), fme_rejection_code buffer
