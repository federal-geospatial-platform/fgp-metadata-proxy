FME workspace metrique_geo_none_geo_selector_2.fmw

Parameters:
- CSV_FILE_NAME = GeospatialValidation_1
- CSV_PATH = .
- CSV_PT =
- LOG_FILE =
- OUT_FFS_FILE = resul3.ffs

Writers:
- FFS_1: FFS to $(OUT_FFS_FILE)

Creator
    GEOMTYPE = Geometry Object
    NUM = 1
    CREATED -> AttributeCreator
Note: resources 1
AttributeCreator
    ATTR_TABLE = SET_TO description = dgn
    -> GEO_NONE_GEO_SELECTOR_2
GEO_NONE_GEO_SELECTOR_2
    CSV_FILE_NAME = $(CSV_FILE_NAME)
    CSV_PATH = $(CSV_PATH)
    CSV_PROVINCE = $(CSV_PT)
    YAML_DIRECTIVES:
      #resources{}.format:
      #  domain: lookup_table_format, [a,b]
      #  spatial_type: overwrite, no_overwite, if_null_overwite
      #  not_found: log, no_log
      #  search_type: equals, contains
      #
      description:
        domain: lookup_table_format
        spatial_type: overwrite
        not_found: no_log
        search_type: equals
    GEOSPATIAL -> out_ffs (writer FFS_1)
    NONE_GEOSPATIAL -> out_ffs (writer FFS_1)
    LOG_ERROR -> out_ffs (writer FFS_1)
out_ffs (writer FFS_1)
    attributes: description varchar(200), _geo_none_geo_status varchar(200), id varchar(200), _not_found_err_msg varchar(200), format varchar(200), _timestamp varchar(200)
