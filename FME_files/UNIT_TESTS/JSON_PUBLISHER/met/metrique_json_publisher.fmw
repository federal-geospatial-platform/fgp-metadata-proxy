FME workspace metrique_json_publisher.fmw

Parameters:
- IN_FFS_FILE =
- LOG_FILE =
- LOOKUP_TABLE =
- OUT_FFS_FILE =
- JSON_ROOT_TEMPLATE =   # *.json JSON_ROOT_TEMPLATE
- JSON_RESOURCE_TEMPLATE =   # *.json JSON_ROOT_TEMPLATE

Readers:
- FFS_1: FFS from $(IN_FFS_FILE)
- CSV2_1: CSV2 from $(LOOKUP_TABLE)

Writers:
- FFS_2: FFS to $(OUT_FFS_FILE)

CSV (reader CSV2_1)
    attributes: default_key string, default_value string
    -> JSON_PUBLISHER [CONFIG_FILE]
OTOTO (reader FFS_1)
    -> JSON_PUBLISHER
JSON_PUBLISHER
    JSON_RESOURCE_TEMPLATE = $(JSON_RESOURCE_TEMPLATE)
    JSON_ROOT_TEMPLATE = $(JSON_ROOT_TEMPLATE)
    OUTPUT_LOCAL -> resultat1 (writer FFS_2)
resultat1 (writer FFS_2)
    attributes: _local varchar(200), _order varchar(200), SECTION varchar(200), _list{}.list_name varchar(200), _list{}.FEATURE_ATTRIBUTES varchar(200), _list{}.TBS_ATTRIBUTES varchar(200), _element_count varchar(200), _list_index varchar(200), _RANDOM_list_name varchar(200), _RANDOM_FEATURE_ATTRIBUTES varchar(200), _RANDOM_TBS_ATTRIBUTES varchar(200), keywords_fr varchar(200), keywords_en varchar(200), CKAN_Transaction varchar(200), TBS_subject varchar(200), TBS_topic varchar(200), data_collection_end_date varchar(200), data_collection_start_date varchar(200), date_published varchar(200), description_en varchar(200), description_fr varchar(200), email varchar(200), id varchar(200), jurisdiction varchar(200), locale varchar(200), metadata_modified varchar(200), nom_organisation_en varchar(200), nom_organisation_fr varchar(200), org_name varchar(200), p-t_entity_en varchar(200),
      p-t_entity_fr varchar(200), position_name_en varchar(200), position_name_fr varchar(200), prov_portal_last_modified varchar(200), source_metadata_date_created varchar(200), tbs_att_name_date_modified_prov varchar(200), tbs_collection varchar(200), tbs_hierarchy_level varchar(200), tbs_imso_approval varchar(200), tbs_license_id varchar(200), tbs_locale varchar(200), tbs_owner_org_id varchar(200), tbs_ready_to_publish varchar(200), tbs_responsible_role varchar(200), tbs_restriction varchar(200), tbs_state varchar(200), tbs_type varchar(200), title_en varchar(200), title_fr varchar(200), update_frequency_tbs varchar(200), tags{}.display_name_fr varchar(200), tags{}.display_name_en varchar(200), resources{} varchar(200), format_tbs varchar(200), name_en varchar(200), name varchar(200), name_fr varchar(200), res_type_tbs varchar(200), tbs_resource_language varchar(200), url varchar(200),
      date_runtime varchar(200), _concatenated_fr varchar(200), _concatenated_en varchar(200), _nb_res varchar(200), _res_lang_list varchar(200), json_file varchar(200), metadata_contact_fr varchar(200), metadata_contact_en varchar(200)
