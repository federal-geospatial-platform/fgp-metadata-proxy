FME workspace metrique_DCAT_Reader_1.fmw

Parameters:
- LOG_FILE =
- OUT_FFS_FILE = result_1.ffs
- GEO_HUB_SERVICE = Custom GeoHub
- CUSTOM_PRIMARY = http://localhost:5000/primary/catalogue/data.json
- CUSTOM_SECONDARY = http://localhost:5000/secondary/catalogue?filter[owner]=Manitoba_Government&page[number]=1&page[size]=25

Writers:
- FFS_1: FFS to $(OUT_FFS_FILE)

Creator
    GEOMTYPE = Geometry Object
    NUM = 1
    CREATED -> DCAT_Reader
DCAT_Reader
    CUSTOM_PRIMARY = $(CUSTOM_PRIMARY)
    CUSTOM_SECONDARY = $(CUSTOM_SECONDARY)
    GEO_HUB_SERVICE = $(GEO_HUB_SERVICE)
    Résultats -> Sampler
Note: Sample first features
Sampler
    RATE = 5
    SAMPLE_MODE = No
    SAMPLE_TYPE_LONG = First N Features
    SAMPLED -> out_ffs (writer FFS_1)
    NOT_SAMPLED -> Sampler_2
Note: Sample last features
Sampler_2
    RATE = 5
    SAMPLE_MODE = No
    SAMPLE_TYPE_LONG = Last N Features
    SAMPLED -> out_ffs (writer FFS_1)
out_ffs (writer FFS_1)
    attributes: _creation_instance uint64
