FME workspace Comparateur.fmw

Parameters:
- LOG_FILE =
- IN_FFS_ETALON_FILE =
- IN_FFS_RESULTAT_FILE =

ChangeDetector
    BLANK_AND_MISSING_DIFFER = Yes
    LENIENT_MATCH = No
    MATCH = NONE
    MATCH_STRATEGY = Match All Attributes
    ADDED -> Terminator
    DELETED -> Terminator
Terminator
    MESSAGE = Translation Terminated

Bookmark: RESULTAT
Note: Lecture générique.
Player_2
    FEAT_TYPE_ATTR = fme_feature_type
    RECFILE = $(IN_FFS_RESULTAT_FILE)
    PLAYED_BACK -> PythonCaller
Note: Bulk remover for fme_ "private" attribute and other
PythonCaller
    PYTHONSOURCE:
      import fme
      import fmeobjects

      def removeFMEAttributes(feature):
          # Remove the attributes that starts with a predetermined prefix
          feature.removeAttrsWithPrefix('fme_')
          feature.removeAttrsWithPrefix('multi')
    PYTHONSYMBOL = removeFMEAttributes
    -> AttributeRemover
AttributeRemover
    REMOVE_ATTRS = fme_feature_type
    -> ChangeDetector [REVISED]

Bookmark: ETALON
Note: Lecture générique.
Player
    FEAT_TYPE_ATTR = fme_feature_type
    RECFILE = $(IN_FFS_ETALON_FILE)
    PLAYED_BACK -> PythonCaller_2
Note: Bulk remover for fme_ "private" attribute and other
PythonCaller_2
    PYTHONSOURCE:
      import fme
      import fmeobjects

      def removeFMEAttributes(feature):
          # Remove the attributes that starts with a predetermined prefix
          feature.removeAttrsWithPrefix('fme_')
          feature.removeAttrsWithPrefix('multi')
    PYTHONSYMBOL = removeFMEAttributes
    -> AttributeRemover_2
AttributeRemover_2
    REMOVE_ATTRS = fme_feature_type
    -> ChangeDetector [ORIGINAL]
