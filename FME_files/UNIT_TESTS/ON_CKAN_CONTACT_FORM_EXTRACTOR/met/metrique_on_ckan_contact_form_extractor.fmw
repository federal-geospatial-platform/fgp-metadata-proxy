FME workspace metrique_on_ckan_contact_form_extractor.fmw

Parameters:
- IN_FFS_FILE = $(FME_MF_DIR)source1.ffs
- LOG_FILE =
- OUT_FFS_FILE = $(FME_MF_DIR)resultat1.ffs

Readers:
- FFS_1: FFS from $(IN_FFS_FILE)

Writers:
- FFS_2: FFS to $(OUT_FFS_FILE)

OTOTO (reader FFS_1)
    -> ON_CKAN_CONTACT_FORM_EXTRACTOR
ON_CKAN_CONTACT_FORM_EXTRACTOR
    CKAN_ROOT = https://data.ontario.ca
    -> out_ffs (writer FFS_2)
out_ffs (writer FFS_2)
    attributes: organization.id varchar(200), id varchar(200), org_contact.en varchar(200), org_contact.fr varchar(200)
