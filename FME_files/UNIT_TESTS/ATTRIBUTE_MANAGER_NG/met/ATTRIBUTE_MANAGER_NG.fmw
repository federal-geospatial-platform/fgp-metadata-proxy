FME workspace ATTRIBUTE_MANAGER_NG.fmw

Parameters:
- IN_FFS_SOURCE = $(FME_MF_DIR)source_1.ffs
- OUT_FFS_FILE = $(FME_MF_DIR)etalon_1.ffs
- LOG_FILE =

Creator
    GEOMTYPE = Geometry Object
    NUM = 1
    CREATED -> FeatureReader [INITIATOR]
FeatureReader
    ATTR_ACCUM_MODE = Only Use Result
    COMBINE_GEOM = Use Result
    DATASET = $(IN_FFS_SOURCE)
    FFS_USE_SEARCH_ENVELOPE = NO
    FORMAT = FFS
    INTERACT = <No Spatial Filter>
    OUTPUT_FEATURES_DISPLAY = Schema and Data Features
    <OTHER> -> ATTRIBUTE_MANAGER_NG
ATTRIBUTE_MANAGER_NG
    IN_YAML_TEXT:
      benoit{}.:
          action: text_overwrite
          attr2set: WADDUP

      notes:
          action: attribute_not_null
          attr2set: title

      iso_topic{}.:
          action: attribute_not_null
          attr2set: default_iso_topic

      publisher:
          action:text_overwrite
          attr2set: NRCan

      description:
          action: text_not_null
          attr2set: Description FGP

      maintainer:
          action: attribute_overwrite
          attr2set: description

      tags{}.name:
          action: attribute_not_null
          attr2set: default_tags_display_name

      richard{}.:
          action: attribute_overwrite
          attr2set: default_iso_topic
    -> Recorder
Recorder
    COMPRESSION_LEVEL = 6
    CREATE_SPATIAL_INDEX = No
    MODE = RECORD_PASS_THROUGH
    RECFILE = $(OUT_FFS_FILE)
    STORE_SCANNED_METADATA = No
    STORE_SCANNED_SCHEMA = No
