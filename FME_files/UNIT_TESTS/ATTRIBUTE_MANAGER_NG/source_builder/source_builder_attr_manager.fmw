FME workspace source_builder_attr_manager.fmw

Creator
    GEOMTYPE = Geometry Object
    NUM = 1
    CREATED -> FeatureReader [INITIATOR]
FeatureReader
    ATTRIBUTES = Output,tags{}.name
    ATTR_ACCUM_MODE = Only Use Result
    COMBINE_GEOM = Use Result
    DATASET = $(FME_MF_DIR_ENCODED)source_1.ffs
    FFS_USE_SEARCH_ENVELOPE = NO
    FORMAT = FFS
    INTERACT = <No Spatial Filter>
    OUTPUT_FEATURES_DISPLAY = Schema and Data Features
    -> AttributeExposer
AttributeExposer
    ATTR_LIST = url
    -> Tester
Tester
    BOOL_OP = OR
    COMPOSITE_TEST = 1
    TEST_CLAUSE = TEST @Value(url) = https://open.yukon.ca/data/datasets/religion-national-household-survey-2011
    TEST_MODE = TEST
    PASSED -> PythonCaller_4
    FAILED -> PythonCaller
PythonCaller_4
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              feature.setAttribute('benoit{2}.richard', '0')
              self.pyoutput(feature)
          def close(self):
              pass
    PYTHONSYMBOL = FeatureProcessor
    -> PythonCaller
PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              feature.setAttribute('benoit{0}.numero', '0')
              feature.setAttribute('benoit{1}.numero', '1')
              feature.setAttribute('benoit{2}.numero', '2')
              feature.setAttribute('benoit{8}.numero', '10')
              feature.setAttribute('iso_topic{5}.topic_value', '')
              self.pyoutput(feature)
          def close(self):
              pass
    PYTHONSYMBOL = FeatureProcessor
    -> ATTRIBUTE_MANAGER_NG
Creator_2
    GEOMTYPE = Geometry Object
    NUM = 1
    CREATED -> ATTRIBUTE_MANAGER_NG
ATTRIBUTE_MANAGER_NG
    IN_YAML_TEXT:
      benoit{}.:
          action: text_overwrite
          attr2set: WADDUP

      notes:
          action: attribute_not_null
          attr2set: title

      iso_topic{}.:
          action: attribute_not_null
          attr2set: default_iso_topic

      publisher:
          action: text_overwrite
          attr2set: NRCan

      description:
          action: text_not_null
          attr2set: Description FGP

      maintainer:
          action: attribute_overwrite
          attr2set: description

      tags{}.name:
          action: attribute_not_null
          attr2set: default_tags_display_name

      richard{}.:
          action: attribute_overwrite
          attr2set: default_iso_topic
