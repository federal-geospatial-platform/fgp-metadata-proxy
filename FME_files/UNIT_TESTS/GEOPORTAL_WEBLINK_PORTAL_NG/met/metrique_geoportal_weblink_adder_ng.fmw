FME workspace metrique_geoportal_weblink_adder_ng.fmw

Parameters:
- WEBLINK_WILDCARD = id
- URL_VALIDATION = NO
- FEATURE_TYPE = GeoportalWeblink_QC
- IN_CSV_LOOKUP_TABLES_DIR = .
- P-T_ABBR = QC
- LOG_FILE = log.log
- OUT_RESULT = resultat2.ffs

Writers:
- FFS_1: FFS to $(OUT_RESULT)

GEOPORTAL_WEBLINK_ADDER_NG
    FEATURE_TYPE = $(FEATURE_TYPE)
    IN_CSV_LOOKUP_TABLES_DIR = $(IN_CSV_LOOKUP_TABLES_DIR)
    P-T_ABBR = $(P-T_ABBR)
    URL_VALIDATION = $(URL_VALIDATION)
    WEBLINK_WILDCARD = @Value(id)
    -> NewFeatureType (writer FFS_1)
NewFeatureType (writer FFS_1)

Bookmark: Valid entry
Creator
    GEOMTYPE = Geometry Object
    NUM = 1
    CREATED -> AttributeCreator
AttributeCreator
    ATTR_TABLE = SET_TO id = valid_name
    -> GEOPORTAL_WEBLINK_ADDER_NG

Bookmark: Invalid entry
Creator_2
    GEOMTYPE = Geometry Object
    NUM = 1
    CREATED -> AttributeCreator_2
AttributeCreator_2
    ATTR_TABLE = SET_TO id = invalid_name
    -> GEOPORTAL_WEBLINK_ADDER_NG
