FME workspace metrique_email_format_tester.fmw

Parameters:
- IN_FFS_FILE =
- LOG_FILE =
- OUT_FFS_FILE =
- TEST_URL = @Value(test_url)   # test url
- DEFAULT_CONTACT_EMAIL =

Readers:
- FFS_1: FFS from $(IN_FFS_FILE)

Writers:
- FFS_2: FFS to $(OUT_FFS_FILE)

OTOTO (reader FFS_1)
    -> EMAIL_FORMAT_TESTER
EMAIL_FORMAT_TESTER
    DEFAULT_CONTACT_EMAIL = $(DEFAULT_CONTACT_EMAIL)
    -> out_ffs (writer FFS_2)
out_ffs (writer FFS_2)
