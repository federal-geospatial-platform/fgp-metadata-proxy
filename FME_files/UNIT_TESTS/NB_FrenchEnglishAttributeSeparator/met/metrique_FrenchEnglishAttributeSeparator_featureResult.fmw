FME workspace metrique_FrenchEnglishAttributeSeparator_featureResult.fmw

Parameters:
- IN_FFS_FILE = $(FME_MF_DIR)source_1.ffs
- LOG_FILE =
- LOOKUP_TABLE = $(FME_MF_DIR)lookuptables\NB_SlashCountSeparator.csv
- OUT_FFS_FILE = $(FME_MF_DIR)resultat_1.ffs
- ATTRIBUTE_TO_SPLIT = attribute_to_split

Readers:
- FFS_1: FFS from $(IN_FFS_FILE)
- CSV2_1: CSV2 from $(LOOKUP_TABLE)

Writers:
- FFS_2: FFS to $(OUT_FFS_FILE)

Note: source
OTOTO (reader FFS_1)
    -> NB_FrenchEnglishAttributeSeparator [Feature_Input]
Note: Slashcount
CSV (reader CSV2_1)
    attributes: dataid string, lang_sep_pos string
    -> NB_FrenchEnglishAttributeSeparator [SlashLocationSheet]
NB_FrenchEnglishAttributeSeparator
    ATTRIBUTE_TO_SPLIT = $(ATTRIBUTE_TO_SPLIT)
    Feature_Output -> out_ffs (writer FFS_2)
out_ffs (writer FFS_2)
