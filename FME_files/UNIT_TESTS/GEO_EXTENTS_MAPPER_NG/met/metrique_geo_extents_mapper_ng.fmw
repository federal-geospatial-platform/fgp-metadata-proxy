FME workspace metrique_geo_extents_mapper_ng.fmw

Parameters:
- LATITUDE_MIN = 44
- LATITUDE_MAX = 64
- LONGITUDE_MIN = -80
- LONGITUDE_MAX = 56
- FEATURE_TYPE = Coord_QC
- IN_CSV_LOOKUP_TABLES_DIR = .
- P-T_ABBR = QC
- LOG_FILE = log.log
- OUT_RESULT = resultat1.ffs

Writers:
- FFS_1: FFS to $(OUT_RESULT)

GEO_EXTENTS_MAPPER_NG
    FEATURE_TYPE = $(FEATURE_TYPE)
    IN_CSV_LOOKUP_TABLES_DIR = $(IN_CSV_LOOKUP_TABLES_DIR)
    LATITUDE_MAX = $(LATITUDE_MAX)
    LATITUDE_MIN = $(LATITUDE_MIN)
    LONGITUDE_MAX = $(LONGITUDE_MAX)
    LONGITUDE_MIN = $(LONGITUDE_MIN)
    P-T_ABBR = $(P-T_ABBR)
    EXTENT_DEFINED -> NewFeatureType (writer FFS_1)
    UNKNOWN_EXTENT -> NewFeatureType (writer FFS_1)
NewFeatureType (writer FFS_1)
    attributes: location varchar(200), id varchar(200)

Bookmark: Filter pass
Note: Different combination of Resources are tested with and without vlues
Creator
    GEOMTYPE = Geometry Object
    NUM = 1
    CREATED -> AttributeCreator
Note: Location in the CSV file
AttributeCreator
    ATTR_TABLE = SET_TO location = ville-quebec
    -> GEO_EXTENTS_MAPPER_NG
Creator_2
    GEOMTYPE = Geometry Object
    NUM = 1
    CREATED -> AttributeCreator_2
Note: Unknown location
AttributeCreator_2
    ATTR_TABLE = SET_TO location = Inconnu
    -> GEO_EXTENTS_MAPPER_NG
Creator_3
    GEOMTYPE = Geometry Object
    NUM = 1
    CREATED -> AttributeCreator_3
Note: User defined lat-lon
AttributeCreator_3
    ATTR_TABLE:
      SET_TO location = Inconnu
      SET_TO east_bound_longitude = 90
      SET_TO west_boud_longitude = -90
      SET_TO south_bound_latitude = -90
      SET_TO north_bound_longitude
    -> GEO_EXTENTS_MAPPER_NG

FME custom transformer GEO_EXTENTS_MAPPER_NG
Description 
This custom transformer will add spatial extents to metadata records that do not have spatial extents.  For the matadata records without a spatial extent, the spatial extents are extracted from a lookup table based on the location attribute of the metadata record.  If the spatial extent is not set and the location is not present in the lookup table the spatial extent cannot be set and a description is added in the log file.
Input Ports 
INPUT: The input metadata records to process.
Output Ports 
EXTENT_DEFINED: The output metdata records for which the spatial extent is defined (already present and/or added).
UNKNOWN_EXTENT: The output metdata records for which the spatial extent is unknown (not defined).
Parameters
LATITUDE_MIN: Minimum latitude for all the entries of the lookup table;
LATITUDE_MAX: Maximum latitude for all the entries of the lookup table;
LONGITUDE_MIN: Minimum longitude for all the entries of the lookup table;
LONGITUDE_MAX: Maximum longitude for all the entries of the lookup table;
FEATURE_TYPE: Name of the CSV file to read (without .csv extension);
IN_CSV_LOOKUP_TABLES_DIR: Name of the directory path containing the CSV file to read;
P-T_ABBR: Two letters abbreviation of the province or the territory.

Parameters:
- LATITUDE_MIN =
- LATITUDE_MAX =
- LONGITUDE_MIN =
- LONGITUDE_MAX =
- FEATURE_TYPE =
- IN_CSV_LOOKUP_TABLES_DIR =
- P-T_ABBR =

INPUT (input)
    -> AttributeExposer_2
EXTENT_DEFINED (output)
UNKNOWN_EXTENT (output)

Bookmark: GEO_EXTENTS_MAPPER
Note: Exposes attributes from incoming data
AttributeExposer_2
    ATTR_LIST = location,east_bound_longitude,id
    -> Tester
Note: Tests for bounding box coordinates
Tester
    BOOL_OP = OR
    COMPOSITE_TEST = 1
    TEST_CLAUSE = TEST east_bound_longitude ATTRIBUTE_HAS_A_VALUE ""
    TEST_MODE = TEST
    PASSED -> ATTRIBUTE_UNEXPOSER
    FAILED -> FeatureMerger_2 [REQUESTOR]
Note: Items without bounding box coordinates receive values joined from Coord lookup table, joined on 'location' attribute
FeatureMerger_2
    ATTR_ACCUM_MODE = Merge Supplier
    ATTR_CONFLICT_RES = Use Requestor
    IGNORE_NULLS = No
    JOIN_KEYS = @Value(location) @Value(location) AUTO
    MERGE_TYPE = Attributes Only
    PROCESS_DUPS = NO
    REJECT_NULL_MISSING_KEYS = No
    SUPPLIERS_FIRST = No
    MERGED -> AttributeRemover
    UNMERGED_REQUESTOR -> Logger
    <REJECTED> -> Terminator_4
Note: Attribute cleanup
AttributeRemover
    REMOVE_ATTRS = location,$(LOCATION_ATT)
    -> ATTRIBUTE_UNEXPOSER
Note: Unexpose all attributes
ATTRIBUTE_UNEXPOSER
    -> EXTENT_DEFINED (output)
Logger
    LOG_FEATURE = LOG_ONLY
    MAXCOORDS = 20
    MAXFEATS = 20
    MESSAGE = lAttribute value @Value(location) missing from Coord lookup table in GEO_EXTENTS_MAPPER transformer.  Bounding box coordinates could not be mapped See PROCESS_REPORT_MANUAL_TASKS.xls file for details in XLS directory for details.
    SEVERITY = WARN
    LOGGED -> AttributeKeeper
AttributeKeeper
    KEEP_ATTRS = location,id
    -> UNKNOWN_EXTENT (output)
Terminator_4
    MESSAGE = Process failed at Feature Merger, GEO_EXTENTS_MAPPER transformer.  Translation terminated.

Bookmark: Reading of the CSV file
LOOKUP_TABLES_READER_NG
    CSV_ENCODING = utf-8
    CSV_PATH = $(IN_CSV_LOOKUP_TABLES_DIR)
    FEATURE_TYPE = $(FEATURE_TYPE)
    PT = $(P-T_ABBR)
    -> AttributeExposer_4
Note: Exposes attributes from lookup table
AttributeExposer_4
    ATTR_LIST = location,east_bound_longitude,north_bound_latitude,south_bound_latitude,west_bound_longitude
    -> Tester_4
Note: Tests accuracy of bounding box coordinates. MIN and MAX, LONGITUDE and LATITUDE set in published parameters for the provincial/territorial geographic extents
Tester_4
    BOOL_OP = COMPOSITE
    COMPOSITE_TEST = 1 AND 2 AND 3 AND 4 AND 5 AND 6 AND 7 AND 8 AND 9 AND 10
    TEST_CLAUSE:
      TEST @Value(east_bound_longitude) < $(LONGITUDE_MAX)
      TEST @Value(east_bound_longitude) > $(LONGITUDE_MIN)
      TEST @Value(north_bound_latitude) < $(LATITUDE_MAX)
      TEST @Value(north_bound_latitude) > $(LATITUDE_MIN)
      TEST @Value(south_bound_latitude) < $(LATITUDE_MAX)
      TEST @Value(south_bound_latitude) > $(LATITUDE_MIN)
      TEST @Value(west_bound_longitude) < $(LONGITUDE_MAX)
      TEST @Value(west_bound_longitude) > $(LONGITUDE_MIN)
      TEST @Value(north_bound_latitude) > @Value(south_bound_latitude)
      TEST @Value(east_bound_longitude) > @Value(west_bound_longitude)
    TEST_MODE = TEST
    PASSED -> FeatureMerger_2 [SUPPLIER]
