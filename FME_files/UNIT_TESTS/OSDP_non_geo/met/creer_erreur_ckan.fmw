FME workspace creer_erreur_ckan.fmw

Parameters:
- IN_WORKING_DIR =
- LOG_FILE =   # Log File
- OLD_RECORD =

Creator
    GEOMTYPE = Geometry Object
    NUM = 1
    CREATED -> FeatureReader [INITIATOR]
FeatureReader
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = $(IN_WORKING_DIR)
    FORMAT = PATH
    OUTPUT_FEATURES_DISPLAY = Schema and Data Features
    PATH_GLOB_PATTERN = *
    PATH_NO_EMPTY_PROPERTIES = YES
    PATH_RECURSE_DIRECTORIES = YES
    PATH_RETRIEVE_FILE_PROPERTIES = NO
    PATH_TYPE = ANY
    PATH -> Tester
Tester
    BOOL_OP = OR
    COMPOSITE_TEST = 1
    TEST_CLAUSE = TEST @Value(path_filename) = SOURCE_SYNCH_ERRORS.xlsx
    TEST_MODE = TEST
    PASSED -> SystemCaller_2
SystemCaller_2
    CMD = DEL /Q @Value(path_directory_windows)XLS\*.*
    -> FeatureHolder
FeatureHolder
    -> Tester_2
Tester_2
    BOOL_OP = OR
    COMPOSITE_TEST = 1
    TEST_CLAUSE = CASE_INSENSITIVE_TEST $(OLD_RECORD) = yes
    TEST_MODE = CASE_INSENSITIVE_TEST
    PASSED -> AttributeCreator
    FAILED -> DateTimeStamper
AttributeCreator
    ATTR_TABLE = SET_TO _timestamp = 00010101
    -> SystemCaller
DateTimeStamper
    DATETIME_ATTR = _timestamp
    STAMP_TYPE = date
    TIMEZONE = utc
    -> SystemCaller
SystemCaller
    CMD = COPY /Y @Value(path_windows) @Value(path_directory_windows)\XLS\CKAN_SYNCH_ERRORS_@Value(_timestamp).@Value(path_extension)
