FME workspace comparateur_sqllite.fmw

Parameters:
- IN_SQLLITE_RES_FILE =
- IN_SQLLITE_ETALON_FILE =
- LOG_FILE =

Readers:
- SQLITE3_1: SQLITE3 from $(IN_SQLLITE_RES_FILE)
- SQLITE3_2: SQLITE3 from $(IN_SQLLITE_ETALON_FILE)

bd_reference (reader SQLITE3_1)
    attributes: provider text, uuid_pt text, uuid_osdp text
    -> ChangeDetector [ORIGINAL]
bd_reference (reader SQLITE3_2)
    attributes: provider text, uuid_pt text, uuid_osdp text
    -> ChangeDetector [REVISED]
ChangeDetector
    BLANK_AND_MISSING_DIFFER = No
    BLANK_AND_MISSING_NAMES_TRAITS_DIFFER = No
    CHECK_COORDINATE_SYSTEMS = No
    CHECK_TYPES_AND_ENCODINGS = No
    LENIENT_MATCH = No
    MATCH = FULL
    MATCHATTRS = provider uuid_osdp uuid_pt
    MATCH_STRATEGY = Match Selected Attributes
    UNCHANGED_OUTPUT = Output Original
    UPDATED -> Terminator
    INSERTED -> Terminator
    DELETED -> Terminator
Terminator
    MESSAGE = Translation Terminated
