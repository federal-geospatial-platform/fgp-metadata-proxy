FME workspace metrique_bc_data_reader.fmw

Parameters:
- IN_FFS_FILE =
- LOG_FILE =
- OUT_FFS_FILE =
- GEODISCOVER_URL =

Readers:
- FFS_1: FFS from $(IN_FFS_FILE)

Writers:
- FFS_2: FFS to $(OUT_FFS_FILE)

OTOTO (reader FFS_1)
    -> BC_DATA_READER
BC_DATA_READER
    -> out_ffs (writer FFS_2)
out_ffs (writer FFS_2)
    attributes: method varchar(200), test_url varchar(200), contacts{}.email varchar(200), contacts{}.name varchar(200), contacts{}.role varchar(200), east_bound_longitude varchar(200), id varchar(200), iso_topic_string varchar(200), license_title varchar(200), metadata_standard_version varchar(200), more_info{}.link varchar(200), name varchar(200), north_bound_latitude varchar(200), notes varchar(200), object_name varchar(200), projection varchar(200), record_create_date varchar(200), record_last_modified varchar(200), record_publish_date varchar(200), resources{}.data_collection_end_date varchar(200), resources{}.data_collection_start_date varchar(200), resources{}.description varchar(200), resources{}.format varchar(200), resources{}.id varchar(200), resources{}.name varchar(200), resources{}.projection_name varchar(200), resources{}.resource_update_cycle varchar(200), resources{}.url varchar(200), sector varchar(200), south_bound_latitude varchar(200),
      spatial varchar(200), spatial_datatypes varchar(200), tags{}.display_name varchar(200), title varchar(200), west_bound_longitude varchar(200)
