FME workspace metrique_aws_translate_ng.fmw

Parameters:
- LOG_FILE =
- OUT_FFS_FILE = $(FME_MF_DIR)resultat1.ffs
- ACTIVATE_TRANSLATION =
- MODE =
- ATTR_2_TRANSLATE =
- ATTR_LIST_2_TRANSLATE =

Writers:
- FFS_1: FFS to $(OUT_FFS_FILE)

Creator
    GEOMTYPE = Geometry Object
    NUM = 1
    CREATED -> AttributeCreator
AttributeCreator
    ATTR_TABLE:
      SET_TO notes = This is the a note
      SET_TO title = This is a title
      SET_TO title_fr = Ceci est un titre
      SET_TO sector
      SET_TO tags{0}.display_name = Display name: 0
      SET_TO tags{1}.display_name = Display name: 1
      SET_TO resources{0}.name = Resource name: 0
      SET_TO resources{1}.name = Resource name: 1
      SET_TO resources{1}.name_fr = Nom de la ressource:1
      SET_TO resources{3}.name = Resource name: 3
      SET_TO resources{3}.name_fr = Resource name: 3
    -> AWS_TRANSLATE_NG
AWS_TRANSLATE_NG
    ACTIVATE_TRANSLATION = $(ACTIVATE_TRANSLATION)
    ATTR_2_TRANSLATE = $(ATTR_2_TRANSLATE)
    ATTR_LIST_2_TRANSLATE = $(ATTR_LIST_2_TRANSLATE)
    MODE = $(MODE)
    -> out_ffs (writer FFS_1)
    TRANSLATION_PROBLEM -> out_ffs (writer FFS_1)
out_ffs (writer FFS_1)
