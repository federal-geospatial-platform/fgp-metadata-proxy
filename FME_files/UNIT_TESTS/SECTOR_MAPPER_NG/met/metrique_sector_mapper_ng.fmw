FME workspace metrique_sector_mapper_ng.fmw

Parameters:
- IN_FFS_FILE = $(FME_MF_DIR)source1.ffs
- LOG_FILE =
- OUT_FFS_FILE = $(FME_MF_DIR)resultat1.ffs
- FEATURE_TYPE = Sector_NB
- IN_CSV_LOOKUP_TABLES_DIR = .
- P-T_ABBR = NB

Readers:
- FFS_1: FFS from $(IN_FFS_FILE)

Writers:
- FFS_2: FFS to $(OUT_FFS_FILE)

OTOTO (reader FFS_1)
    -> SECTOR_MAPPER_NG
SECTOR_MAPPER_NG
    FEATURE_TYPE = $(FEATURE_TYPE)
    IN_CSV_LOOKUP_TABLES_DIR = $(IN_CSV_LOOKUP_TABLES_DIR)
    P-T_ABBR = $(P-T_ABBR)
    UNMAPPED_OUTPUT -> out_ffs (writer FFS_2)
    PUBLISHED_OUTPUT -> out_ffs (writer FFS_2)
    UNPUBLISHED_OUTPUT -> out_ffs (writer FFS_2)
out_ffs (writer FFS_2)
    attributes: sector varchar(200), id varchar(200), original_sector_value varchar(200), hnap_sector_value varchar(200), graphic_link varchar(200), fgp_publish varchar(200)

FME custom transformer SECTOR_MAPPER_NG
Description 
This custom transformer sorts the record (feature) to be published based on the sector name.  The valid sector name is contained in a CSV file.
Input Ports 
INPUT: The input metadata records (features) to process.
Output Ports 
PUBLISHED_OUTPUT: The records (features) to be publihed in the FGP based on the sector name.
UNPUBLISHED_OUTPUT: The records (features) not to be publihed in the FGP based on the sector name.
UNMAPPED_OUTPUT: The records (features) for which the sector is not present (unmapped)  in the CSV file.
Parameters 
FEATURE_TYPE: Name of the CSV file to read (without .csv extension);
IN_CSV_LOOKUP_TABLES_DIR: Name of the directory path containing the CSV file to read;
P-T_ABBR: Two letters abbreviation of the province or the territory.

Parameters:
- FEATURE_TYPE =
- IN_CSV_LOOKUP_TABLES_DIR =
- P-T_ABBR =

INPUT (input)
    -> AttributeExposer
PUBLISHED_OUTPUT (output)
UNPUBLISHED_OUTPUT (output)
UNMAPPED_OUTPUT (output)

Bookmark: Sector Mapper
Note: Expose needed attributes
AttributeExposer
    ATTR_LIST = sector,id
    -> FeatureMerger [REQUESTOR]
Note: Read the CSV sectors
LOOKUP_TABLES_READER_NG
    CSV_ENCODING = utf-8
    CSV_PATH = $(IN_CSV_LOOKUP_TABLES_DIR)
    FEATURE_TYPE = $(FEATURE_TYPE)
    PT = $(P-T_ABBR)
    -> AttributeExposer_2
Note: Expose needed attributes
AttributeExposer_2
    ATTR_LIST = original_sector_value,hnap_sector_value,graphic_link,fgp_publish
    -> FeatureMerger [SUPPLIER]
FeatureMerger
    ATTR_ACCUM_MODE = Merge Supplier
    ATTR_CONFLICT_RES = Use Requestor
    IGNORE_NULLS = No
    JOIN_KEYS = @Value(sector) @Value(original_sector_value) AUTO
    MERGE_TYPE = Attributes Only
    PROCESS_DUPS = NO
    REJECT_NULL_MISSING_KEYS = No
    SUPPLIERS_FIRST = No
    MERGED -> Tester
    UNMERGED_REQUESTOR -> AttributeKeeper
Note: Test if published in the FGP
Tester
    BOOL_OP = OR
    COMPOSITE_TEST = 1
    TEST_CLAUSE = TEST @LowerCase(@Value(fgp_publish)) = @LowerCase(oui)
    TEST_MODE = TEST
    PASSED -> AttributeRenamer
    FAILED -> UNPUBLISHED_OUTPUT (output)
AttributeRenamer
    ATTR_TABLE = RENAME_SET_DEFAULT hnap_sector_value > sector
    -> AttributeRemover_2
AttributeRemover_2
    REMOVE_ATTRS = original_sector_value,fgp_publish,hnap_sector_value
    -> ATTRIBUTE_UNEXPOSER
Note: Unexpose all attributes
ATTRIBUTE_UNEXPOSER
    -> PUBLISHED_OUTPUT (output)
AttributeKeeper
    KEEP_ATTRS = sector,id
    -> UNMAPPED_OUTPUT (output)
