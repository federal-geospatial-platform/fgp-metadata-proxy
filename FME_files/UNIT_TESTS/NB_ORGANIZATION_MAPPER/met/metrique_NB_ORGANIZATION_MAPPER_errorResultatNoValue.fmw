FME workspace metrique_NB_ORGANIZATION_MAPPER_errorResultatNoValue.fmw

Parameters:
- IN_FFS_FILE =
- LOG_FILE =
- LOOKUP_TABLE =
- OUT_FFS_FILE =

Readers:
- FFS_1: FFS from $(IN_FFS_FILE)
- CSV2_2: CSV2 from $(LOOKUP_TABLE)

Writers:
- FFS_2: FFS to $(OUT_FFS_FILE)

OTOTO (reader FFS_1)
    -> NB_ORGANIZATION_MAPPER [feature_input]
CSV (reader CSV2_2)
    attributes: api_value string, organization_name string, organization_name_fr string
    -> NB_ORGANIZATION_MAPPER [Sector_Lookup_table]
NB_ORGANIZATION_MAPPER
    No_Organization_Value -> out_ffs (writer FFS_2)
out_ffs (writer FFS_2)
    attributes: resource.attribution varchar(200), classification.domain_metadata{0}.value varchar(200)
