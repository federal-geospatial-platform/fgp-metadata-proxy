FME workspace Comparateur.fmw

Parameters:
- LOG_FILE =
- IN_ETALON_FILE = $(FME_MF_DIR)etalon1.ffs
- IN_RESULTAT_FILE = $(FME_MF_DIR)resultat.ffs

Readers:
- FFS_1: FFS from $(IN_ETALON_FILE)
- FFS_2: FFS from $(IN_RESULTAT_FILE)

AttributeRemover
    REMOVE_ATTRS = fme_feature_type,multi_reader_full_id,TYPE_LAC,SNRC,multi_reader_type,multi_reader_id,CODE,SHAPE_GEOMETRY,CODE_CLASS,PRECISION,multi_reader_keyword,_hash_abstract,_hash_datestamp,_hash_format,_hash_id,_hash_name,_hash_title,_hash_url
    -> ChangeDetector [ORIGINAL]
AttributeRemover_2
    REMOVE_ATTRS = fme_feature_type,multi_reader_full_id,Id,TYPE_LAC,SNRC,multi_reader_type,multi_reader_id,CODE,SHAPE_GEOMETRY,CODE_CLASS,PRECISION,multi_reader_keyword
    -> ChangeDetector [REVISED]
ChangeDetector
    BLANK_AND_MISSING_DIFFER = Yes
    LENIENT_MATCH = No
    MATCH = NONE
    MATCH_STRATEGY = Match All Attributes
    ADDED -> Terminator
    DELETED -> Terminator
Terminator
    MESSAGE = Translation Terminated

Bookmark: ETALON
Note: Lecture générique.
ETALON (reader FFS_1)
    attributes: CODE number(8,0), CODE_CLASS number(8,0), PRECISION number(3,0), SHAPE_GEOMETRY char(15), SNRC number(31,15), TYPE_LAC number(2,0)
    -> AttributeRemover

Bookmark: RESULTAT
Note: Lecture générique.
RESULTAT (reader FFS_2)
    attributes: CODE number(8,0), CODE_CLASS number(8,0), PRECISION number(3,0), SHAPE_GEOMETRY char(15), SNRC number(31,15), TYPE_LAC number(2,0), Id number(2,0)
    -> AttributeRemover_2
