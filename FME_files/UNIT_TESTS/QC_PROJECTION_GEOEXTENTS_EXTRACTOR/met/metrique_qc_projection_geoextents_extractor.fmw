FME workspace metrique_qc_projection_geoextents_extractor.fmw

Parameters:
- IN_FFS_FILE =
- LOG_FILE =
- OUT_FFS_FILE =
- GEODISCOVER_URL =

Readers:
- FFS_1: FFS from $(IN_FFS_FILE)

Writers:
- FFS_2: FFS to $(OUT_FFS_FILE)

OTOTO (reader FFS_1)
    -> QC_PROJECTION_GEOEXTENTS_EXTRACTOR
QC_PROJECTION_GEOEXTENTS_EXTRACTOR
    DATA_OUTPUT -> out_ffs (writer FFS_2)
out_ffs (writer FFS_2)
    attributes: resources{}.url varchar(200), resources{}.format varchar(200), spatialref{}.projection_name varchar(200), spatialref{}.projection_system varchar(200), spatialref{}.projection_system_version varchar(200), east_bound_longitude varchar(200), north_bound_latitude varchar(200), south_bound_latitude varchar(200), west_bound_longitude varchar(200)
