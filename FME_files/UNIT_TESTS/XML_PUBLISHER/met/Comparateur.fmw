FME workspace Comparateur.fmw

Parameters:
- IN_XML_RESULTAT =
- IN_XML_ETALON =
- LOG_FILE =

Creator
    GEOMTYPE = Geometry Object
    NUM = 1
    CREATED -> XMLFlattener
    CREATED -> XMLFlattener_2
Note: Lecture du fichier résultat
XMLFlattener
    EMBEDDED_EXPRESSIONS = MD_Metadata
    FEATURE_TYPES_FORMAT_NAME = XML
    FILE_XML = $(IN_XML_RESULTAT)
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    XML_SOURCE_TYPE = XML file
    -> TerminatorMinMax_2
TerminatorMinMax_2
    Message = ERREUR : Aucune entité traitée
    NombreEntitesMaximal = *
    NombreEntitesMinimal = 1
    -> BulkAttributeRemover_2
BulkAttributeRemover_2
    ATTR_EXP = ^_
    -> ChangeDetector [ORIGINAL]
XMLFlattener_2
    EMBEDDED_EXPRESSIONS = MD_Metadata
    FEATURE_TYPES_FORMAT_NAME = XML
    FILE_XML = $(IN_XML_ETALON)
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    XML_SOURCE_TYPE = XML file
    -> TerminatorMinMax
TerminatorMinMax
    Message = ERREUR : Aucune entité traitée
    NombreEntitesMaximal = *
    NombreEntitesMinimal = 1
    -> BulkAttributeRemover
BulkAttributeRemover
    ATTR_EXP = ^_
    -> ChangeDetector [REVISED]
ChangeDetector
    BLANK_AND_MISSING_DIFFER = No
    LENIENT_MATCH = No
    MATCH = NONE
    MATCH_STRATEGY = Match All Attributes
    ADDED -> Terminator
    DELETED -> Terminator
Terminator
    MESSAGE = Translation Terminated
