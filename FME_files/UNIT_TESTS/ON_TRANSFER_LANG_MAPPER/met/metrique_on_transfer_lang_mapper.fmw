FME workspace metrique_on_transfer_lang_mapper.fmw

Parameters:
- IN_FFS_FILE =
- LOG_FILE =
- LOOKUP_TABLE =
- OUT_FFS_FILE =

Readers:
- FFS_1: FFS from $(IN_FFS_FILE)
- XLSXR_1: XLSXR from $(LOOKUP_TABLE)

Writers:
- FFS_2: FFS to $(OUT_FFS_FILE)

Sheet1 (reader XLSXR_1)
    attributes: language_value char(19), transfer_option_description_language char(8), transfer_option_description_language_other_lang char(8)
    -> ON_TRANSFER_LANG_MAPPER [LOOKUP_TABLE_INPUT]
OTOTO (reader FFS_1)
    -> ON_TRANSFER_LANG_MAPPER [DATA_INPUT]
ON_TRANSFER_LANG_MAPPER
    -> resultat1 (writer FFS_2)
resultat1 (writer FFS_2)
    attributes: transfer_option_description_language varchar(200), transfer_option_description_language_other_lang varchar(200), resources{}.transfer_option_description_language varchar(200), resources{}.transfer_option_description_language_other_lang varchar(200)
