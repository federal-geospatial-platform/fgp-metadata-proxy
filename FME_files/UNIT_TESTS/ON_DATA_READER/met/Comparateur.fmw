FME workspace Comparateur.fmw

Parameters:
- LOG_FILE =
- IN_ETALON_FILE = $(FME_MF_DIR)etalon1.ffs
- IN_RESULTAT_FILE = $(FME_MF_DIR)resultat.ffs

Readers:
- FFS_1: FFS from $(IN_ETALON_FILE)
- FFS_2: FFS from $(IN_RESULTAT_FILE)

AttributeRemover
    REMOVE_ATTRS = fme_feature_type,multi_reader_full_id,TYPE_LAC,SNRC,multi_reader_type,multi_reader_id,CODE,SHAPE_GEOMETRY,CODE_CLASS,PRECISION,multi_reader_keyword
    -> AttributeRemover_3
AttributeRemover_3
    REMOVE_ATTRS = _element_count
    -> ChangeDetector [ORIGINAL]
AttributeRemover_2
    REMOVE_ATTRS = fme_feature_type,multi_reader_full_id,Id,TYPE_LAC,SNRC,multi_reader_type,multi_reader_id,CODE,SHAPE_GEOMETRY,CODE_CLASS,PRECISION,multi_reader_keyword
    -> AttributeRemover_4
AttributeRemover_4
    REMOVE_ATTRS = metadata_created,metadata_modified,notes_translated_fr,organization.title,title_translated.fr,notes_translated.fr
    -> ChangeDetector [REVISED]
ChangeDetector
    BLANK_AND_MISSING_DIFFER = Yes
    LENIENT_MATCH = No
    MATCH = NONE
    MATCH_STRATEGY = Match All Attributes
    ADDED -> Terminator
    DELETED -> Terminator
Terminator
    MESSAGE = Translation Terminated

Bookmark: ETALON
Note: Lecture générique.
ETALON (reader FFS_1)
    attributes: CODE number(8,0), CODE_CLASS number(8,0), PRECISION number(3,0), SHAPE_GEOMETRY char(15), SNRC number(31,15), TYPE_LAC number(2,0)
    -> AttributeRemover

Bookmark: RESULTAT
Note: Lecture générique.
RESULTAT (reader FFS_2)
    attributes: CODE number(8,0), CODE_CLASS number(8,0), PRECISION number(3,0), SHAPE_GEOMETRY char(15), SNRC number(31,15), TYPE_LAC number(2,0), Id number(2,0)
    -> AttributeRemover_2
