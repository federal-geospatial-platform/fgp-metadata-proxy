FME workspace metrique_nl_attribute_extractor.fmw

Parameters:
- LOG_FILE = coco
- IN_FFS_FILE = $(FME_MF_DIR)source_1.ffs
- OUT_FFS_FILE = $(FME_MF_DIR)resultat_1.ffs

Readers:
- FFS_1: FFS from $(IN_FFS_FILE)

Writers:
- FFS_2: FFS to $(OUT_FFS_FILE)

Creator (reader FFS_1)
    attributes: _creation_instance number(2,0), _url_dataset_geo char(74), _url_dataset_non_geo char(74), _url_root char(27), contributor char(156), data_collection_start_date char(59), geographical_coverage char(112), license_id char(24), note char(904), org_contact.en char(25), publisher char(72), record_create_date char(11), record_published_date char(11), resources{}.format char(23), resources{}.name char(94), resources{}.url char(71), sector char(123), tags{}.display_name char(27), title char(96), type char(8), xml_type char(12)
    -> NL_ATTRIBUTE_EXTRACTOR
NL_ATTRIBUTE_EXTRACTOR
    -> Creator (writer FFS_2)
Creator (writer FFS_2)
    attributes: _creation_instance number(2,0), _url_dataset_geo char(74), _url_dataset_non_geo char(74), _url_root char(27), contributor char(156), data_collection_start_date char(59), geographical_coverage char(112), license_id char(24), note char(904), org_contact.en char(25), publisher char(72), record_create_date char(11), record_published_date char(11), resources{}.format char(23), resources{}.name char(94), resources{}.url char(71), sector char(123), tags{}.display_name char(27), title char(96), type char(8), xml_type char(12)
