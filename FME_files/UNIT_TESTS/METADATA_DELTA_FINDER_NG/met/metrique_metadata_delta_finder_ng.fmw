FME workspace metrique_metadata_delta_finder_ng.fmw

Parameters:
- IN_FFS_CAT_READ_TEST_FILE = $(FME_MF_DIR)source2.ffs
- IN_FFS_FILE = $(FME_MF_DIR)source1.ffs
- LOG_FILE =
- OUT_FFS_FILE = cocoout

Readers:
- FFS_1: FFS from $(IN_FFS_FILE)

Writers:
- FFS_2: FFS to $(OUT_FFS_FILE)

OTOTO (reader FFS_1)
    -> METADATA_DELTA_FINDER_NG
METADATA_DELTA_FINDER_NG
    ABSTRACT_ATT_NEW = notes
    ABSTRACT_ATT_REF = MD_Metadata.identificationInfo.MD_DataIdentification.abstract.CharacterString
    CUSTOM_CSW_CKAN_URL = TOTO
    DATESTAMP_ATT_NEW = record_last_modified
    DATESTAMP_ATT_REF = MD_Metadata.dateStamp.Date
    ID_ATT_NEW = id
    ID_ATT_REF = MD_Metadata.fileIdentifier.CharacterString
    LOCAL_SOURCE = Yes
    LOCAL_SOURCE_DIR = " "
    LOCAL_SOURCE_FORMAT = XML
    PYCSW_CKAN_OVERWRITE = YES
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    Statistics -> out_ffs (writer FFS_2)
    No_Change -> out_ffs (writer FFS_2)
    Update -> out_ffs (writer FFS_2)
    Insert -> out_ffs (writer FFS_2)
    Delete -> out_ffs (writer FFS_2)
out_ffs (writer FFS_2)
    attributes: _real_count varchar(200), _count uint64, _hash_prov varchar(200), _type varchar(200), RESOURCES_FORMAT_ATT varchar(200), _global_hashkey varchar(200), id varchar(200), _hash_pycsw varchar(200), MD_Metadata.fileIdentifier.CharacterString varchar(200), MD_Metadata.path_windows varchar(200), MD_Metadata.path_extension varchar(200), path_windows varchar(200), path_extension varchar(200), PyCSW_Transaction varchar(200)
