FME workspace metrique_geoportal_weblink_adder.fmw

Parameters:
- IN_FFS_FILE =
- LOG_FILE =
- OUT_FFS_FILE =
- WEBLINK_WILDCARD =
- LOOKUP_TABLE =

Readers:
- FFS_1: FFS from $(IN_FFS_FILE)
- CSV2_1: CSV2 from $(LOOKUP_TABLE)

Writers:
- FFS_2: FFS to $(OUT_FFS_FILE)

CSV (reader CSV2_1)
    attributes: default_key string, default_value string
    -> GEOPORTAL_WEBLINK_ADDER [LOOKUP_TABLE_INPUT]
OTOTO (reader FFS_1)
    -> GEOPORTAL_WEBLINK_ADDER
GEOPORTAL_WEBLINK_ADDER
    WEBLINK_WILDCARD = $(WEBLINK_WILDCARD)
    -> resultat1 (writer FFS_2)
resultat1 (writer FFS_2)
    attributes: contacts{}.email varchar(200), contacts{}.name varchar(200), contacts{}.role varchar(200), iso_topic{} varchar(200), iso_topic{}.topic_value varchar(200), projectionList{}.codespace varchar(200), projectionList{}.projection_name varchar(200), projectionList{}.version varchar(200), resources{}.data_collection_end_date varchar(200), resources{}.data_collection_start_date varchar(200), resources{}.format varchar(200), resources{}.name varchar(200), resources{}.resource_update_cycle varchar(200), resources{}.url varchar(200), tags{}.display_name varchar(200), resources{} varchar(200), name varchar(200), id varchar(200)
