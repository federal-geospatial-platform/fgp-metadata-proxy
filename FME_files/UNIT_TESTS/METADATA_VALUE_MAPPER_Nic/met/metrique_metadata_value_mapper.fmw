FME workspace metrique_metadata_value_mapper.fmw

Parameters:
- ATT_TO_MAP =
- CODE_REFRESH =
- ENGLISH_REFRESH =
- ERROR_NOT_MAPPED =
- FRENCH_REFRESH =
- LOG_FILE =
- LOOKUP_TABLE =
- OUT_FFS_FILE =
- IN_FFS_MANUAL_SOURCE =

Readers:
- CSV2_1: CSV2 from $(LOOKUP_TABLE)

Writers:
- FFS_1: FFS to $(OUT_FFS_FILE)

Creator
    GEOMTYPE = Geometry Object
    NUM = 1
    CREATED -> Tester
Tester
    BOOL_OP = OR
    COMPOSITE_TEST = 1
    TEST_CLAUSE = TEST $(IN_FFS_MANUAL_SOURCE) != ""
    TEST_MODE = TEST
    PASSED -> FeatureReader [INITIATOR]
    FAILED -> AttributeRemover
FeatureReader
    ATTR_ACCUM_MODE = Only Use Result
    COMBINE_GEOM = Use Result
    DATASET = $(IN_FFS_MANUAL_SOURCE)
    FFS_USE_SEARCH_ENVELOPE = NO
    FORMAT = FFS
    INTERACT = <No Spatial Filter>
    OUTPUT_FEATURES_DISPLAY = Schema and Data Features
    <OTHER> -> METADATA_VALUE_MAPPER [DATA_INPUT]
AttributeRemover
    REMOVE_ATTRS = _creation_instance
    -> AttributeCreator
AttributeCreator
    ATTR_TABLE:
      SET_TO progress_code = COMPLETED
      SET_TO contact{0}.role = OWNER
      SET_TO contact{1}.role = USER
    -> METADATA_VALUE_MAPPER [DATA_INPUT]
CSV (reader CSV2_1)
    -> METADATA_VALUE_MAPPER [LOOKUP_TABLE_INPUT]
METADATA_VALUE_MAPPER
    ATT_TO_MAP = $(ATT_TO_MAP)
    CODE_REFRESH = $(CODE_REFRESH)
    ENGLISH_REFRESH = $(ENGLISH_REFRESH)
    ERROR_NOT_MAPPED = $(ERROR_NOT_MAPPED)
    FRENCH_REFRESH = $(FRENCH_REFRESH)
    -> out_ffs (writer FFS_1)
out_ffs (writer FFS_1)
