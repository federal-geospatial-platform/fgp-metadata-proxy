FME workspace metrique_nb_esrimapper.fmw

Parameters:
- ATT_TO_MAP =
- CODE_REFRESH =
- ENGLISH_REFRESH =
- ERROR_NOT_MAPPED =
- FRENCH_REFRESH =
- IN_FFS_FILE =
- LOG_FILE =
- LOOKUP_TABLE =
- OUT_FFS_FILE =

Readers:
- FFS_1: FFS from $(IN_FFS_FILE)
- CSV2_1: CSV2 from $(LOOKUP_TABLE)

Writers:
- FFS_2: FFS to $(OUT_FFS_FILE)

OTOTO (reader FFS_1)
    -> NB_ESRIMAPPER
CSV (reader CSV2_1)
    attributes: original_value string, real_value_english string, real_value_french string, code_value string
    -> NB_ESRIMAPPER [ESRI_LOOKUP]
NB_ESRIMAPPER
    -> out_ffs (writer FFS_2)
out_ffs (writer FFS_2)
    attributes: resources{} varchar(200), resource.id varchar(200), title varchar(200), title_fr varchar(200), original_value buffer, real_value_english buffer, real_value_french buffer, code_value buffer, EsriLink varchar(200), idval varchar(200), Layertype varchar(200), joinuuidkey varchar(200), name_fr varchar(200), format varchar(200), url varchar(200), name varchar(200), projection_name varchar(200), projection_system varchar(200), projection_system_version varchar(200), resources{}.name varchar(200), resources{}.url varchar(200), resources{}.format varchar(200), resources{}.name_fr varchar(200), spatialref{}.projection_name varchar(200), spatialref{}.projection_system varchar(200), spatialref{}.projection_system_version varchar(200)
