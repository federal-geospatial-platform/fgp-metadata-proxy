FME workspace Comparateur.fmw

Parameters:
- LOG_FILE =
- IN_ETALON_FILE = $(FME_MF_DIR)etalon1.ffs
- IN_RESULTAT_FILE = $(FME_MF_DIR)resultat.ffs

Readers:
- FFS_1: FFS from $(IN_ETALON_FILE)
- FFS_2: FFS from $(IN_RESULTAT_FILE)

AttributeExposer [off]
    ATTR_LIST = multi_writer_id,multi_reader_keyword,multi_reader_full_id,multi_reader_id,fme_feature_type
    -> AttributeRemover_2
AttributeRemover_2 [off]
    REMOVE_ATTRS = multi_reader_id,multi_reader_keyword,fme_feature_type,multi_writer_id,multi_reader_full_id
    -> ChangeDetector [REVISED]
AttributeExposer_3 [off]
    ATTR_LIST = multi_writer_id,multi_reader_keyword,multi_reader_full_id,multi_reader_id,fme_feature_type
    -> AttributeRemover_3
AttributeRemover_3 [off]
    REMOVE_ATTRS = multi_reader_id,multi_reader_keyword,fme_feature_type,multi_writer_id,multi_reader_full_id
    -> ChangeDetector [ORIGINAL]
ChangeDetector
    BLANK_AND_MISSING_DIFFER = Yes
    LENIENT_MATCH = No
    MATCH = NONE
    MATCH_STRATEGY = Match All Attributes
    ADDED -> Terminator
    DELETED -> Terminator
Terminator [off]
    MESSAGE = Translation Terminated

Bookmark: ETALON
Note: Lecture générique.
ETALON (reader FFS_1)
    attributes: CODE number(8,0), CODE_CLASS number(8,0), PRECISION number(3,0), SHAPE_GEOMETRY char(15), SNRC number(31,15), TYPE_LAC number(2,0)
    -> ChangeDetector [ORIGINAL]

Bookmark: RESULTAT
Note: Lecture générique.
RESULTAT (reader FFS_2)
    attributes: CODE number(8,0), CODE_CLASS number(8,0), PRECISION number(3,0), SHAPE_GEOMETRY char(15), SNRC number(31,15), TYPE_LAC number(2,0), Id number(2,0)
    -> ChangeDetector [REVISED]
