FME workspace metrique_qc_date_formatter.fmw

Parameters:
- IN_FFS_FILE_1 =   # Source FME Feature Store (FFS) File(s)
- LOG_FILE =
- OUT_FFS_FILE_1 =

Readers:
- FFS_1: FFS from $(IN_FFS_FILE_1)

Writers:
- FFS_2: FFS to $(OUT_FFS_FILE_1)

Source1 (reader FFS_1)
    attributes: _creation_instance varchar(200), result.file_id varchar(200), MD_Metadata.fileIdentifier.CharacterString varchar(200), MD_Metadata.MD_Metadata varchar(200), _OpenMapsFilter varchar(200), result.results varchar(200), debut varchar(200), NbRecords varchar(200), root_url varchar(200), _response_body varchar(200), _http_status_code varchar(200), MD_Metadata{} varchar(200)
    -> QC_DATE_FORMATTER
QC_DATE_FORMATTER
    -> resultat1 (writer FFS_2)
resultat1 (writer FFS_2)
    attributes: record_create_date varchar(200), data_collection_start_date varchar(200), record_publish_date varchar(200), record_last_modified varchar(200), data_collection_end_date varchar(200), _creation_instance varchar(200), result.file_id varchar(200), MD_Metadata.fileIdentifier.CharacterString varchar(200), MD_Metadata.MD_Metadata varchar(200), _OpenMapsFilter varchar(200), result.results varchar(200), debut varchar(200), NbRecords varchar(200), root_url varchar(200), _response_body varchar(200), _http_status_code varchar(200), MD_Metadata{} varchar(200)
