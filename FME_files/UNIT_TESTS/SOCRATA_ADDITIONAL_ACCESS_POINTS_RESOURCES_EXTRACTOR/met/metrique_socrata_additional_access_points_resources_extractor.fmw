FME workspace metrique_socrata_additional_access_points_resources_extractor.fmw

Parameters:
- IN_FFS_FILE = $(FME_MF_DIR)source1.ffs
- LOG_FILE =
- OUT_FFS_FILE = $(FME_MF_DIR)resultat1.ffs

Readers:
- FFS_1: FFS from $(IN_FFS_FILE)

Writers:
- FFS_2: FFS to $(OUT_FFS_FILE)

OTOTO (reader FFS_1)
    -> SOCRATA_ADDITIONAL_ACCESS_POINTS_RESOURCES_EXTRACTOR
SOCRATA_ADDITIONAL_ACCESS_POINTS_RESOURCES_EXTRACTOR
    -> out_ffs (writer FFS_2)
out_ffs (writer FFS_2)
