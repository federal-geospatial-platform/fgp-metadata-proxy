FME workspace metrique_bc_geoportal_weblink_adder.fmw

Parameters:
- IN_FFS_FILE =
- LOG_FILE =
- OUT_FFS_FILE =
- TEST_URL = @Value(test_url)   # test url

Readers:
- FFS_1: FFS from $(IN_FFS_FILE)

Writers:
- FFS_2: FFS to $(OUT_FFS_FILE)

OTOTO (reader FFS_1)
    -> BC_GEOPORTAL_WEBLINK_ADDER
BC_GEOPORTAL_WEBLINK_ADDER
    EMAIL_ADMIN = robert.bennett@canada.ca
    EMAIL_ENCRYPTION = SSL
    EMAIL_HOST = smtp.mail.yahoo.com
    EMAIL_PORT = 465
    EMAIL_SENDER = robbennett@rocketmail.com
    EMAIL_SENDER_PASSWORD =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
    TEST_URL = $(TEST_URL)
    -> out_ffs (writer FFS_2)
out_ffs (writer FFS_2)
