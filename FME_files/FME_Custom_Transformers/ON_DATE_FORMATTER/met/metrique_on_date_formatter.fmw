FME workspace metrique_on_date_formatter.fmw

Parameters:
- IN_FFS_FILE =
- LOG_FILE =
- OUT_FFS_FILE =
- GEODISCOVER_URL =

Readers:
- FFS_1: FFS from $(IN_FFS_FILE)

Writers:
- FFS_2: FFS to $(OUT_FFS_FILE)

OTOTO (reader FFS_1)
    -> ON_DATE_FORMATTER
ON_DATE_FORMATTER
    -> out_ffs (writer FFS_2)
out_ffs (writer FFS_2)
    attributes: record_create_date varchar(200), record_last_modified varchar(200), record_publish_date varchar(200), data_collection_end_date varchar(200), data_collection_start_date varchar(200)
