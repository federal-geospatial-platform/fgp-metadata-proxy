FME workspace metrique_metadata_format_mapper.fmw

Parameters:
- ATT_TO_MAP =
- ERROR_NOT_MAPPED =
- IN_FFS_FILE =
- LOG_FILE =
- LOOKUP_TABLE =
- OUT_FFS_FILE =
- OUT_FFS_FILE_2 =
- REAL_VALUE_REFRESH =
- RES_TYPE_EN_REFRESH =
- RES_TYPE_FR_REFRESH =

Readers:
- FFS_1: FFS from $(IN_FFS_FILE)
- CSV2_1: CSV2 from $(LOOKUP_TABLE)

Writers:
- FFS_2: FFS to $(OUT_FFS_FILE)
- FFS_3: FFS to $(OUT_FFS_FILE_2)

CSV (reader CSV2_1)
    attributes: original_value string, real_value string, resource_type_fr string, resource_type_en string
    -> METADATA_FORMAT_MAPPER [LOOKUP_TABLE_INPUT]
OTOTO (reader FFS_1)
    -> METADATA_FORMAT_MAPPER [DATA_INPUT]
METADATA_FORMAT_MAPPER
    ATT_TO_MAP = $(ATT_TO_MAP)
    ERROR_NOT_MAPPED = $(ERROR_NOT_MAPPED)
    REAL_VALUE_REFRESH = $(REAL_VALUE_REFRESH)
    RES_TYPE_EN_REFRESH = $(RES_TYPE_EN_REFRESH)
    RES_TYPE_FR_REFRESH = $(RES_TYPE_FR_REFRESH)
    -> out_ffs (writer FFS_2)
    -> MAPPING_ERROR_LIST_CREATOR
out_ffs (writer FFS_2)
    attributes: mapping_errors{}.error varchar(200)
MAPPING_ERROR_LIST_CREATOR
    LIST_ATTR = mapping_errors{}
    LIST_NAME = mapping_errors{}
    -> out_ffs_2 (writer FFS_3)
out_ffs_2 (writer FFS_3)
    attributes: error varchar(200), _element_index varchar(200)
