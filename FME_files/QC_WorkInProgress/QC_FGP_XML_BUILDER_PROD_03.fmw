FME workspace QC_FGP_XML_BUILDER_PROD_03.fmw

Parameters:
- ACTIVATE_TRANSLATION = No
- CATALOGUE_READER_SELECT = Yes
- CSW_URL = http://127.0.0.1:8080/pycsw?   # "%http://127.0.0.1:8080/pycsw? CSW URL
- CUSTOM_URL = https://www.donneesquebec.ca/recherche/api/action   # https://www.donneesquebec.ca/recherche/api/action CUSTOM_URL
- DELETE_LIST = $(FME_SHAREDRESOURCE_DATA)\PT_Harvester\QC\XLS\DELETE_LIST.xlsx
- FANOUT_DIRECTORY_FAILED = $(FME_SHAREDRESOURCE_DATA)\PT_Harvester\QC\XML_FAILED
- FANOUT_DIRECTORY_PASSED = $(FME_SHAREDRESOURCE_DATA)\PT_Harvester\QC\XML_PASSED
- IN_FFS_TESTING_FILE = $(FME_SHAREDRESOURCE_DATA)\PT_Harvester\QC\FFS\QC_UNIT_TEST_CAT_READER_RESULTS_APR_28.ffs
- LOCAL_WRITER = Yes
- LOG_FILE = $(FME_SHAREDRESOURCE_DATA)\PT_Harvester\QC\LOG\QC.log
- OUT_FFS_MAPPING_ERROR = $(FME_SHAREDRESOURCE_DATA)\PT_Harvester\QC\FFS\AttributeMappingErrors.ffs
- OUT_FFS_WEBSERVICE_ERROR = $(FME_SHAREDRESOURCE_DATA)\PT_Harvester\QC\FFS\web_service_error.ffs
- OUT_RESULT_FOLDER = $(FME_SHAREDRESOURCE_DATA)\PT_Harvester\QC\XML_LOCAL
- P-T_ABBR = QC
- PYCSW_OVERWRITE = YES
- SAMPLE_SELECT = Yes
- SAMPLE_SIZE = 60
- SECTORS_NOT_MAPPED = $(FME_SHAREDRESOURCE_DATA)\PT_Harvester\QC\XLS\SECTORS_NOT_MAPPED.xlsx
- SPATIALTYPE_NOT_MAPPED = $(FME_SHAREDRESOURCE_DATA)\PT_Harvester\QC\XLS\SPATIALTYPE_NOT_MAPPED.xlsx
- TEMPLATE_GMD_CITEDRESPONSIBLEPARTY = $(FME_SHAREDRESOURCE_DATA)\PT_Harvester\GMD_CITEDRESPONSIBLEPARTY.xml
- TEMPLATE_GMD_CONTACT = $(FME_SHAREDRESOURCE_DATA)\PT_Harvester\GMD_CONTACT.xml
- TEMPLATE_GMD_DISTRIBUTIONFORMAT = $(FME_SHAREDRESOURCE_DATA)\PT_Harvester\GMD_DISTRIBUTIONFORMAT.xml
- TEMPLATE_GMD_DISTRIBUTOR = $(FME_SHAREDRESOURCE_DATA)\PT_Harvester\GMD_DISTRIBUTOR.xml
- TEMPLATE_GMD_KEYWORDS = $(FME_SHAREDRESOURCE_DATA)\PT_Harvester\GMD_KEYWORDS.xml
- TEMPLATE_GMD_MDMETADATA = $(FME_SHAREDRESOURCE_DATA)\PT_Harvester\GMD_MDMETADATA.xml
- TEMPLATE_GMD_REFERENCESYSTEMINFO = $(FME_SHAREDRESOURCE_DATA)\PT_Harvester\GMD_REFERENCESYSTEMINFO.xml
- TEMPLATE_GMD_RESOURCEMAINTENANCE = $(FME_SHAREDRESOURCE_DATA)\PT_Harvester\GMD_RESOURCEMAINTENANCE.xml
- TEMPLATE_GMD_TOPICCATEGORY = $(FME_SHAREDRESOURCE_DATA)\PT_Harvester\GMD_TOPICCATEGORY.xml
- TEMPLATE_GMD_TRANSFEROPTIONS = $(FME_SHAREDRESOURCE_DATA)\PT_Harvester\GMD_TRANSFEROPTIONS.xml
- SourceDataset_XLSXR = C:\Data\PT_Harvester\P-T_ETL_LOOKUP_TABLES.xlsx   # Source Microsoft Excel File(s)
- FME_SHAREDRESOURCE_DATA = C:\Data   # FME Server Resource Data

Readers:
- XLSXR_1: XLSXR from $(SourceDataset_XLSXR)

Writers:
- TEXTLINE_1: TEXTLINE to $(FANOUT_DIRECTORY_PASSED)
- TEXTLINE_2: TEXTLINE to $(FANOUT_DIRECTORY_FAILED)
- FFS_1: FFS to $(OUT_FFS_MAPPING_ERROR)
- TEXTLINE_3: TEXTLINE to $(OUT_RESULT_FOLDER)
- FFS_2: FFS to $(OUT_FFS_WEBSERVICE_ERROR)
- XLSXW_1: XLSXW to $(DELETE_LIST)
- XLSXW_2: XLSXW to $(SECTORS_NOT_MAPPED)
- XLSXW_3: XLSXW to $(SPATIALTYPE_NOT_MAPPED)

web_service_error (writer FFS_2)
    attributes: name varchar(200), format varchar(200), url varchar(200), data_collection_end_date varchar(200), data_collection_start_date varchar(200), resource_update_cycle varchar(200), spatial_type varchar(10), resources varchar(200), _uuid varchar(200), projection_name varchar(200), resource_update_cycle_code varchar(200), resource_update_cycle_fr varchar(200), id varchar(200), _element_index varchar(200), _error varchar(200), fme_rejection_code varchar(200), _response_body varchar(200), _http_status_code varchar(200), _url_failure_message varchar(200)
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer

Bookmark: Reading QC Geoportal datasets
Creator
    GEOMTYPE = Geometry Object
    NUM = 1
    CREATED -> Tester_3
Tester_3
    BOOL_OP = OR
    COMPOSITE_TEST = 1
    TEST_CLAUSE = TEST $(CATALOGUE_READER_SELECT) = Yes
    TEST_MODE = TEST
    PASSED -> CATALOGUE_READER
    FAILED -> FeatureReader [INITIATOR]
Note: Reading QC CKAN-API
CATALOGUE_READER
    CUSTOM_URL = $(CUSTOM_URL)
    Environnement = Manuel
    PYCSW_CSW_SELECT = PYCSW
    QUERY_1 = request=GetRecords&service=CSW&version=2.0.2&elementSetName=full&constraintLanguage=FILTER&typenames=gmd:MD_Metadata
    QUERY_2 = request=GetRecords&service=CSW&version=2.0.2&elementSetName=full&constraintLanguage=FILTER&outputSchema=http://www.isotc211.org/2005/gmd&typeNames=gmd:MD_Metadata&ElementSetName=full&resultType=results&startPosition=
    XML_FLAT_ATT_2 = MD_Metadata{}
    Résultats -> QC_DATA_READER
FeatureReader
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> QC_DATA_READER

Bookmark: Filtering and convertion to inhouse model.
QC_DATA_READER
    -> QC_DATE_FORMATTER
QC_DATE_FORMATTER
    -> RESOURCES_VALIDATOR

Bookmark: Attribute Validation
RESOURCES_VALIDATOR
    -> FORMAT_VALIDATOR
Note: Verfication if URL is valid WMS call for WMS formats
FORMAT_VALIDATOR
    -> EMAIL_FORMAT_TESTER
Note: Tests for '@' in email addresses
EMAIL_FORMAT_TESTER
    -> DEFAULT_ATTRIBUTE_MAPPER

Bookmark: Default value
Default_QC (reader XLSXR_1)
    attributes: default_key char(39), default_value char(190)
    -> DEFAULT_ATTRIBUTE_MAPPER [LOOKUP_TABLE_INPUT]
Note: Sets default attirbute values
DEFAULT_ATTRIBUTE_MAPPER
    -> SECTOR_MAPPER

Bookmark: Sector Mapper
Sector_QC (reader XLSXR_1)
    attributes: original_sector_value char(79), hnap_sector_value char(79), graphic_link char(128), fgp_publish char(4)
    -> SECTOR_MAPPER [LOOKUP_TABLE_INPUT]
SECTOR_MAPPER
    -> GEOSPATIAL_DATA_VALIDATOR
    UNMAPPED_OUTPUT -> SECTORS_NOT_MAPPED (writer XLSXW_2)
SECTORS_NOT_MAPPED (writer XLSXW_2)
    attributes: sector auto(20), id auto(20)

Bookmark: spatial data type management
Geospatial_QC (reader XLSXR_1)
    attributes: geospatial char(8), format char(8), spatial_type char(10)
    -> GEOSPATIAL_DATA_VALIDATOR [LOOKUP_TABLE_INPUT]
GEOSPATIAL_DATA_VALIDATOR
    KEYWORD_SEARCH = Photographie aérienne|Toponyme|Toponymie|photogrammétrie|GPS|cartographie
    -> SPATIAL_TYPE_SETTER
UUID_Spatial_QC (reader XLSXR_1)
    attributes: uuid char(37), spatial_representation_type char(10)
    -> SPATIAL_TYPE_SETTER [LOOKUP_TABLE_INPUT]
SPATIAL_TYPE_SETTER
    AERIAL_PHOTO_SEARCH = Photographie aérienne|photogrammétrie
    TABLE_SEARCH = Toponyme|Toponymie|GPS
    -> Tester_2
    UNMAPPED_OUTPUT -> SPATIALTYPE_NOT_MAPPED (writer XLSXW_3)
SPATIALTYPE_NOT_MAPPED (writer XLSXW_3)
    attributes: title string(96), id auto(20)

Bookmark: Sampler
Tester_2
    BOOL_OP = OR
    COMPOSITE_TEST = 1
    TEST_CLAUSE = TEST $(SAMPLE_SELECT) = Yes
    TEST_MODE = TEST
    PASSED -> Sampler
    FAILED -> QC_PROJECTION_GEOEXTENTS_EXTRACTOR
Sampler
    RATE = $(SAMPLE_SIZE)
    SAMPLE_MODE = Yes
    SAMPLE_TYPE_LONG = Every Nth Feature
    SAMPLED -> QC_PROJECTION_GEOEXTENTS_EXTRACTOR

Bookmark: Projection and GeoExtents Management
QC_PROJECTION_GEOEXTENTS_EXTRACTOR
    -> GEO_EXTENTS_MAPPER
Coord_QC (reader XLSXR_1)
    attributes: location char(20), south_bound_latitude number(6,2), west_bound_longitude number(7,2), east_bound_longitude x_coordinate, north_bound_latitude y_coordinate
    -> GEO_EXTENTS_MAPPER [LOOKUP_TABLE]
GEO_EXTENTS_MAPPER
    -> METADATA_VALUE_MAPPER [DATA_INPUT]

Bookmark: Attribute value mapper
Note: This section utilizes mulitple instances of the METADATA_VALUE_MAPPER to correct values to valid English values and to add the valid French equivalents and RI_CODES where applicable. It can be utilized for mulitple metadata items by accessing custom look up tables applicable to specific items. / Turn the error mapping options and the data items to be mapped on or off by clicking on the transformer and selecting yes/no. / - ERROR_NOT_MAPPED: enables mapping of data item values that cannot be found in the lookup tables. / - ENGLISH_REFRESH: enables updating of English attribute values. / - FRENCH_REFRESH: enables updating of French attribute values. / - CODE_REFRESH: enables updating of RI_CODE values. / Enter the attribute key name by clicking on the transformer and selecting the drop down menu next to the 'att_to_map' text box and selecting the 'Open text editor...' option. Explicitly enter the attribute key name in the text editor (ie: contacts{}.role). / IMPORTANT: Do not select the 'Attribute Value' option from the drop down menu to select the attribute key name.
Update (reader XLSXR_1)
    attributes: original_value char(13), real_value_english char(12), real_value_french char(14), code_value char(7)
    -> METADATA_VALUE_MAPPER [LOOKUP_TABLE_INPUT]
Note: Maps update cycle to HNAP standards
METADATA_VALUE_MAPPER
    ATT_TO_MAP = update_frequency
    CODE_REFRESH = YES
    ENGLISH_REFRESH = YES
    ERROR_NOT_MAPPED = YES
    FRENCH_REFRESH = YES
    -> MAPPING_ERROR_LIST_CREATOR
    -> METADATA_VALUE_MAPPER_2 [DATA_INPUT]
Progress (reader XLSXR_1)
    attributes: original_value char(18), real_value_english char(18), real_value_french char(18), code_value char(7)
    -> METADATA_VALUE_MAPPER_2 [LOOKUP_TABLE_INPUT]
Note: Maps progress code to HNAP standards
METADATA_VALUE_MAPPER_2
    ATT_TO_MAP = progress_code
    CODE_REFRESH = YES
    ENGLISH_REFRESH = YES
    ERROR_NOT_MAPPED = YES
    FRENCH_REFRESH = YES
    -> METADATA_VALUE_MAPPER_3 [DATA_INPUT]
    -> MAPPING_ERROR_LIST_CREATOR
SpatialRepresentation (reader XLSXR_1)
    attributes: original_value char(12), real_value_english char(12), real_value_french char(13), code_value char(7)
    -> METADATA_VALUE_MAPPER_3 [LOOKUP_TABLE_INPUT]
Note: Maps spatial_representation_type to HNAP standards
METADATA_VALUE_MAPPER_3
    ATT_TO_MAP = spatial_representation_type
    CODE_REFRESH = YES
    ENGLISH_REFRESH = YES
    ERROR_NOT_MAPPED = YES
    FRENCH_REFRESH = YES
    -> METADATA_FORMAT_MAPPER [DATA_INPUT]
    -> MAPPING_ERROR_LIST_CREATOR

Bookmark: Format value mapper
Note: This section utilizes the METADATA_FORMAT_MAPPER to correct data format values to valid data format values and to associate and add the French and English 'Resource Type' attribute to each data format type. It accesses a custom look up table applicable to data formats. / Turn the error mapping options and the data items to be mapped on or off by clicking on the transformer and selecting yes/no. / - ERROR_NOT_MAPPED: enables mapping of data item values that cannot be found in the lookup tables. / - REAL_VALUE_REFRESH: enables updating of data format attribute values. / - RES_TYPE_FR_REFRESH: enables mapping of French resource types. / - RES_TYPE_EN_REFRESH: enables mapping of English resource types. / Enter the attribute key name by clicking on the transformer and selecting the drop down menu next to the 'att_to_map' text box and selecting the 'Open text editor...' option. Explicitly enter the attribute key name in the text editor (ie: resources{}.format). / IMPORTANT: Do not select the 'Attribute Value' option from the drop down menu to select the attribute key name.
Format (reader XLSXR_1)
    attributes: original_value char(160), real_value char(10), resource_type_fr char(20), resource_type_en char(20)
    -> METADATA_FORMAT_MAPPER [LOOKUP_TABLE_INPUT]
METADATA_FORMAT_MAPPER
    ATT_TO_MAP = resources{}.format
    ERROR_NOT_MAPPED = YES
    REAL_VALUE_REFRESH = YES
    RES_TYPE_EN_REFRESH = YES
    RES_TYPE_FR_REFRESH = YES
    -> MAPPING_ERROR_LIST_CREATOR
    -> RESOURCE_NAME_UNDERSCORE_REMOVER

Bookmark: Mapping error list creator
Note: Creates list of errors found and corrected in mapping
MAPPING_ERROR_LIST_CREATOR
    LIST_ATTR = mapping_errors{}
    LIST_NAME = mapping_errors{}
    -> ATTRIBUTE_MAPPING_ERRORS (writer FFS_1)
ATTRIBUTE_MAPPING_ERRORS (writer FFS_1)
    attributes: error varchar(200), _element_index varchar(200)

Bookmark: Data preparation for metadata section
Note: Removes all underscores from resources{}.name attributes. Long compounded names joined by underscores in this field can cause display formatting issues when published to the FGP.
RESOURCE_NAME_UNDERSCORE_REMOVER
    -> GMD_SECTION_DATA_EXTRACTION
Note: Creates lists and removes duplicates for GMD_Section
GMD_SECTION_DATA_EXTRACTION
    -> MORE_INFO_MANAGER
Note: Tests the more_info{}.link list for valid attribute values and filters them out where missing
MORE_INFO_MANAGER
    -> URL_CHARACTER_ENCODER

Bookmark: URL Character Encoder
URL_CHARACTER_ENCODER
    -> REMOVE_BROKEN_URL_WMS_ESRI_REST

Bookmark: Data cleanup. Dropping broken web services
Note: Tests WMS/ESRI_REST resource URL's and removes them where broken
REMOVE_BROKEN_URL_WMS_ESRI_REST
    -> WMS_REST_LANGUAGE_FORMATTER
    FAULTY_URL_OUTPUT -> web_service_error (writer FFS_2)

Bookmark: HNAP Rules- 1 web service per language.
Note: Formats WMS and ESRI REST resources to add French versions and formats French and English versions with valid supporting attributes
WMS_REST_LANGUAGE_FORMATTER
    -> DUPLICATE_SERVICE_REMOVER
Note: Removes duplicate WMS or ESRI REST resources where they exist, that would otherwise invalidate the dataset
DUPLICATE_SERVICE_REMOVER
    -> METADATA_DELTA_FINDER

Bookmark: New Bookmark
METADATA_DELTA_FINDER
    Abstract_ATT = notes
    CSW_URL = $(CSW_URL)
    DateStamp_ATT = record_last_modified
    ID_ATT = id
    PYCSW_QUERY_1 = request=GetRecords&service=CSW&version=2.0.2&elementSetName=full&constraintLanguage=FILTER&typenames=gmd:MD_Metadata
    PYCSW_QUERY_2 = request=GetRecords&service=CSW&version=2.0.2&elementSetName=full&constraintLanguage=FILTER&outputSchema=http://www.isotc211.org/2005/gmd&typeNames=gmd:MD_Metadata&ElementSetName=full&resultType=results&startPosition=
    PYCSW_XML_FLAT_ATT_2 = MD_Metadata{}
    Provider = "Open Government Licence - British Columbia"
    Resources_Name_ATT = resources{}.name
    Resources_URL_ATT = resources{}.url
    Title_ATT = title
    -> AttributeExposer
AttributeExposer
    ATTR_LIST = PyCSW_Transaction
    -> AttributeFilter
AttributeFilter
    ATTR_NAME = PyCSW_Transaction
    ATTR_VALUES = <Empty>,<Missing>,<Null>,<Unfiltered>,No change,Update,Insert,Delete
    <EMPTY> -> Terminator
    <MISSING> -> Terminator
    <NULL> -> Terminator
    <UNFILTERED> -> Terminator
    No change -> Tester
    Update -> AWS_TRANSLATE
    Insert -> AWS_TRANSLATE
    Delete -> AttributeKeeper
Terminator
    MESSAGE = ERROR: Unknown _event value from Metadata_Delta
Tester
    BOOL_OP = OR
    COMPOSITE_TEST = 1
    TEST_CLAUSE = TEST $(PYCSW_OVERWRITE) = YES
    TEST_MODE = TEST
    PASSED -> AttributeCreator
    FAILED -> StatisticsCalculator
Note: Reset to update
AttributeCreator
    ATTR_TABLE = SET_TO PyCSW_Transaction = Update
    -> AWS_TRANSLATE
AttributeKeeper
    KEEP_ATTRS = id
    -> DELETE_LIST (writer XLSXW_1)
DELETE_LIST (writer XLSXW_1)
    attributes: id auto(20)
Creator_2
    GEOMTYPE = Geometry Object
    NUM = 1
    CREATED -> StatisticsCalculator
StatisticsCalculator
    COMPUTE_HISTOGRAM = NO
    COUNT_ATTR = _count
    PREPEND_ATTR_NAME_CHOICE = For multiple results only
    STATS_ATTRS = id
    SUMMARY -> AttributeCreator_2
AttributeCreator_2
    ATTR_TABLE = SET_TO _real_count = @Evaluate(@Value(_count)-1)
    -> StatisticsCalculator_Summary
StatisticsCalculator_Summary: Logger
    LOG_FEATURE = NONE
    MAXFEATS = 20
    MESSAGE:
      ************************
      **** Unchanged Report ****
      ************************

      @Value(_real_count) features were unchanged

      ************************
      ************************
      ************************
    SEVERITY = INFO

Bookmark: Language Translation
AWS_TRANSLATE
    ACTIVATE_TRANSLATION = $(ACTIVATE_TRANSLATION)
    MODE = French-->English
    -> XML_PUBLISHER

Bookmark: XML CREATION AND WRITING
Note: Excel config file to map QC attributes to those required by XML templates
Config_QC (reader XLSXR_1)
    attributes: HNAP_ATTRIBUTES char(54), FEATURE_ATTRIBUTES char(60), METADATA_SECTION char(191)
    -> XML_PUBLISHER [CONFIG_FILE]
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
XML_PUBLISHER
    CSW_URL = $(CSW_URL)
    LOCAL_WRITER = $(LOCAL_WRITER)
    TEMPLATE_GMD_CITEDRESPONSIBLEPARTY = $(TEMPLATE_GMD_CITEDRESPONSIBLEPARTY)
    TEMPLATE_GMD_CONTACT = $(TEMPLATE_GMD_CONTACT)
    TEMPLATE_GMD_DISTRIBUTIONFORMAT = $(TEMPLATE_GMD_DISTRIBUTIONFORMAT)
    TEMPLATE_GMD_DISTRIBUTOR = $(TEMPLATE_GMD_DISTRIBUTOR)
    TEMPLATE_GMD_KEYWORDS = $(TEMPLATE_GMD_KEYWORDS)
    TEMPLATE_GMD_MDMETADATA = $(TEMPLATE_GMD_MDMETADATA)
    TEMPLATE_GMD_REFERENCESYSTEMINFO = $(TEMPLATE_GMD_REFERENCESYSTEMINFO)
    TEMPLATE_GMD_RESOURCEMAINTENANCE = $(TEMPLATE_GMD_RESOURCEMAINTENANCE)
    TEMPLATE_GMD_TOPICCATEGORY = $(TEMPLATE_GMD_TOPICCATEGORY)
    TEMPLATE_GMD_TRANSFEROPTIONS = $(TEMPLATE_GMD_TRANSFEROPTIONS)
    LOCAL -> text_line (writer TEXTLINE_3)
    INSERT_PASSED -> text_line (writer TEXTLINE_1)
    INSERT_FAILED -> text_line (writer TEXTLINE_2)
    UPDATE_PASSED -> text_line (writer TEXTLINE_1)
    UPDATE_FAILED -> text_line (writer TEXTLINE_2)
