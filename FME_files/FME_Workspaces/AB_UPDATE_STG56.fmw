FME workspace AB_UPDATE_STG56.fmw

Parameters:
- AWS_TRANSLATE_ON = Yes
- CSW_URL = http://pycsw-6ee5e20/pycsw?   # CSW URL
- EMAIL_ADMIN = robert.bennett@canada.ca
- EMAIL_ENCRYPTION = SSL
- EMAIL_HOST = smtp.mail.yahoo.com
- EMAIL_PORT = 465
- EMAIL_SENDER = robbennett@rocketmail.com
- EMAIL_SENDER_PASSWORD =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
- ENTITY_SEARCH_LITERAL = Alberta
- FANOUT_DIRECTORY_FAILED = $(FME_SHAREDRESOURCE_DATA)\PT_Harvester\AB\XML_FAILED
- FANOUT_DIRECTORY_PASSED = $(FME_SHAREDRESOURCE_DATA)\PT_Harvester\AB\XML_PASSED
- IN_XLS_LOOKUP = $(FME_SHAREDRESOURCE_DATA)\PT_Harvester\P-T_ETL_LOOKUP_TABLES.xlsx
- LOG_FILE = $(FME_SHAREDRESOURCE_DATA)\PT_Harvester\AB\LOG\AB_Create.log
- METHOD_SELECT = Auto
- OUT_FFS_MAPPING_ERROR = $(FME_SHAREDRESOURCE_DATA)\PT_Harvester\AB\FFS\AttributeMappingErrors.ffs
- OUT_FFS_TRANSLATED = $(FME_SHAREDRESOURCE_DATA)\PT_Harvester\AB\FFS\AB_AllRecords_Translated.ffs
- OUT_FFS_WEBSERVICE_ERROR = $(FME_SHAREDRESOURCE_DATA)PT_Harvester\AB\FFS\web_service_error.ffs
- OUT_RESULT_FOLDER = $(FME_SHAREDRESOURCE_DATA)\PT_Harvester\AB\XML_LOCAL
- P-T_ABBR = AB
- SAMPLE_SELECT = No
- SAMPLE_SIZE = 50
- TEMPLATE_GMD_CITEDRESPONSIBLEPARTY = $(FME_SHAREDRESOURCE_DATA)\PT_Harvester\GMD_CITEDRESPONSIBLEPARTY.xml
- TEMPLATE_GMD_TRANSFEROPTIONS = $(FME_SHAREDRESOURCE_DATA)\PT_Harvester\GMD_TRANSFEROPTIONS.xml
- TEMPLATE_GMD_CONTACT = $(FME_SHAREDRESOURCE_DATA)\PT_Harvester\GMD_CONTACT.xml
- TEMPLATE_GMD_DISTRIBUTIONFORMAT = $(FME_SHAREDRESOURCE_DATA)\PT_Harvester\GMD_DISTRIBUTIONFORMAT.xml
- TEMPLATE_GMD_DISTRIBUTOR = $(FME_SHAREDRESOURCE_DATA)\PT_Harvester\GMD_DISTRIBUTOR.xml
- TEMPLATE_GMD_KEYWORDS = $(FME_SHAREDRESOURCE_DATA)\PT_Harvester\GMD_KEYWORDS.xml
- TEMPLATE_GMD_MDMETADATA = $(FME_SHAREDRESOURCE_DATA)\PT_Harvester\GMD_MDMETADATA.xml
- TEMPLATE_GMD_REFERENCESYSTEMINFO = $(FME_SHAREDRESOURCE_DATA)\PT_Harvester\GMD_REFERENCESYSTEMINFO.xml
- TEMPLATE_GMD_RESOURCEMAINTENANCE = $(FME_SHAREDRESOURCE_DATA)\PT_Harvester\GMD_RESOURCEMAINTENANCE.xml
- TEMPLATE_GMD_TOPICCATEGORY = $(FME_SHAREDRESOURCE_DATA)\PT_Harvester\GMD_TOPICCATEGORY.xml
- TIME_FILTER_DAYS = 7
- TIME_FILTER_MONTHS = 0
- FME_SHAREDRESOURCE_DATA = C:\Data   # FME Server Resource Data

Readers:
- XLSXR_1: XLSXR from $(FME_SHAREDRESOURCE_DATA)\PT_Harvester\P-T_ETL_LOOKUP_TABLES.xlsx

Writers:
- FFS_1: FFS to $(OUT_FFS_MAPPING_ERROR)
- TEXTLINE_1: TEXTLINE to $(FANOUT_DIRECTORY_FAILED)
- TEXTLINE_2: TEXTLINE to $(OUT_RESULT_FOLDER)
- FFS_2: FFS to $(OUT_FFS_WEBSERVICE_ERROR)
- TEXTLINE_3: TEXTLINE to $(FANOUT_DIRECTORY_PASSED)
- FFS_3: FFS to $(OUT_FFS_TRANSLATED)

FrenchTranslation (reader XLSXR_1)
    attributes: original_value char(5), real_value_french char(5)
    -> METADATA_VALUE_MAPPER_3 [LOOKUP_TABLE_INPUT]
web_service_error (writer FFS_2)
    attributes: id varchar(200), name_fr varchar(200), name varchar(200), url varchar(200), format varchar(200), protocol varchar(200), data_collection_end_date varchar(200), data_collection_start_date varchar(200), resource_update_cycle varchar(200), projection_name varchar(200), resources varchar(200), resource_update_cycle_code varchar(200), resource_update_cycle_fr varchar(200), _element_index varchar(200), _error varchar(200), fme_rejection_code varchar(200), _response_body varchar(200), _http_status_code varchar(200), _url_failure_message varchar(200)
ATTRIBUTE_MAPPING_ERRORS (writer FFS_1)
    attributes: error varchar(200)
Note: Writes XML to a local folder without publishing to PyCSW, and without the PyCSW transaction headers and footers
text_line (writer TEXTLINE_2)
    attributes: text_line_data buffer
Note: Writes XML published to the PyCSW to a local folder
text_line (writer TEXTLINE_3)
    attributes: text_line_data buffer
Note: Writes XML that failed to publish to the PyCSW to a local folder
text_line (writer TEXTLINE_1)
    attributes: text_line_data buffer
Note: Creates eMail notification of data translation results
NOTIFY_UPDATE
    CSW_ID = @Value(csw_id)
    EMAIL_ADMIN = robert.bennett@canada.ca
    EMAIL_ENCRYPTION = SSL
    EMAIL_HOST = smtp.mail.yahoo.com
    EMAIL_PORT = 465
    EMAIL_SENDER = robbennett@rocketmail.com
    EMAIL_SENDER_PASSWORD =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
    ID = @Value(id)

Bookmark: Extracting data from AB portal
Creator
    GEOMTYPE = Geometry Object
    NUM = 1
    CREATED -> AB_UPDATE_PRETRANSLATE [API_QUERY]
    CREATED -> AB_UPDATE_PRETRANSLATE [CSW_QUERY]
AB_UPDATE_PRETRANSLATE
    EMAIL_ADMIN = $(EMAIL_ADMIN)
    EMAIL_ENCRYPTION = $(EMAIL_ENCRYPTION)
    EMAIL_HOST = $(EMAIL_HOST)
    EMAIL_PORT = $(EMAIL_PORT)
    EMAIL_SENDER = $(EMAIL_SENDER)
    EMAIL_SENDER_PASSWORD = $(EMAIL_SENDER_PASSWORD)
    ENTITY_SEARCH_LITERAL = $(ENTITY_SEARCH_LITERAL)
    SAMPLE_SELECT = $(SAMPLE_SELECT)
    SAMPLE_SIZE = $(SAMPLE_SIZE)
    TIME_FILTER_DAYS = $(TIME_FILTER_DAYS)
    TIME_FILTER_MONTHS = $(TIME_FILTER_MONTHS)
    NO_DELETED_RECORDS_COUNT -> NOTIFY_UPDATE [NO_RECORDS_DELETED_COUNT]
    NEW_RECORDS_COUNT -> NOTIFY_UPDATE [NEW_RECORDS_COUNT]
    DELETED_RECORDS_COUNT -> NOTIFY_UPDATE [RECORDS_DELETED_COUNT]
    -> FORMAT_VALIDATOR [PythonCaller_Input]
    TOTAL_RECORDS_COUNT -> NOTIFY_UPDATE [TOTAL_RECORDS_COUNT]
    UPDATED_RECORDS_COUNT -> NOTIFY_UPDATE [UPDATED_RECORDS_COUNT]

Bookmark: Attribute_Validation
Note: Verfication if URL is valid WMS call for WMS formats
FORMAT_VALIDATOR
    PythonCaller_Output -> EMAIL_FORMAT_TESTER
Note: Tests for '@' in email addresses
EMAIL_FORMAT_TESTER
    -> DEFAULT_ATTRIBUTE_MAPPER

Bookmark: Data adjustement to be HNAP compliant
Default_AB (reader XLSXR_1)
    attributes: default_key char(39), default_value char(236)
    -> DEFAULT_ATTRIBUTE_MAPPER [LOOKUP_TABLE_INPUT]
Note: Sets default attirbute values
DEFAULT_ATTRIBUTE_MAPPER
    -> AB_RESOURCES_FORMATTER
ESRI_AB (reader XLSXR_1)
    attributes: lookup_title char(64), layer_name number(4,0)
    -> AB_RESOURCES_FORMATTER [LOOKUP_TABLE_INPUT]
Note: Converts WMS and ESRI REST to URL's to valid formats
AB_RESOURCES_FORMATTER
    WMS_NOT_MAPPED -> Junction
    -> AB_MISSING_ATTRIBUTE_MANAGER
Note: MAPPING_ERROR_LIST_CREATOR : INPUT
Junction
    -> Junction_2
Note: Tests mandatory attributes and creates default values where missing.
AB_MISSING_ATTRIBUTE_MANAGER
    -> SELECT

Bookmark: Attribute value mapper
Note: AB_RESOURCES_FORMATTER : WMS_NOT_MAPPED
Junction_2
    -> MAPPING_ERROR_LIST_CREATOR
Note: Correction bad translation
METADATA_VALUE_MAPPER_3
    ATT_TO_MAP = resources{}.name
    CODE_REFRESH = NO
    ENGLISH_REFRESH = NO
    ERROR_NOT_MAPPED = NO
    FRENCH_REFRESH = YES
    -> METADATA_VALUE_MAPPER [DATA_INPUT]
Role (reader XLSXR_1)
    attributes: original_value char(22), real_value_english char(22), real_value_french char(21), code_value char(7)
    -> METADATA_VALUE_MAPPER [LOOKUP_TABLE_INPUT]
Note: METADATA_VALUE_MAPPER [METADATA_VALUE_MAPPER] / [Linked] / User Parameters: / ATT_TO_MAP: contacts{}.role / ERROR_NOT_MAPPED: YES / ENGLISH_REFRESH: YES / FRENCH_REFRESH: YES / CODE_REFRESH: YES
METADATA_VALUE_MAPPER
    ATT_TO_MAP = contacts{}.role
    CODE_REFRESH = YES
    ENGLISH_REFRESH = YES
    ERROR_NOT_MAPPED = YES
    FRENCH_REFRESH = YES
    -> AttributeRemover_2
    -> MAPPING_ERROR_LIST_CREATOR
Note: Removing error list
AttributeRemover_2
    LIST_ATTRS = mapping_errors{}
    -> METADATA_VALUE_MAPPER_2 [DATA_INPUT]
Update (reader XLSXR_1)
    attributes: original_value char(13), real_value_english char(12), real_value_french char(14), code_value char(7)
    -> METADATA_VALUE_MAPPER_2 [LOOKUP_TABLE_INPUT]
Note: METADATA_VALUE_MAPPER_2 [METADATA_VALUE_MAPPER] / [Linked] / User Parameters: / ATT_TO_MAP: resource_update_cycle / ERROR_NOT_MAPPED: YES / ENGLISH_REFRESH: YES / FRENCH_REFRESH: YES / CODE_REFRESH: YES
METADATA_VALUE_MAPPER_2
    ATT_TO_MAP = resource_update_cycle
    CODE_REFRESH = YES
    ENGLISH_REFRESH = YES
    ERROR_NOT_MAPPED = YES
    FRENCH_REFRESH = YES
    -> MAPPING_ERROR_LIST_CREATOR
    -> AttributeRemover_3
Note: Removing error list
AttributeRemover_3
    LIST_ATTRS = mapping_errors{}
    -> METADATA_FORMAT_MAPPER [DATA_INPUT]
Note: This section utilizes mulitple instances of the METADATA_VALUE_MAPPER to correct values to valid English values and to add the valid French equivalents and RI_CODES where applicable. It can be utilized for mulitple metadata items by accessing custom look up tables applicable to specific items. / Turn the error mapping options and the data items to be mapped on or off by clicking on the transformer and selecting yes/no. / - ERROR_NOT_MAPPED: enables mapping of data item values that cannot be found in the lookup tables. / - ENGLISH_REFRESH: enables updating of English attribute values. / - FRENCH_REFRESH: enables updating of French attribute values. / - CODE_REFRESH: enables updating of RI_CODE values. / Enter the attribute key name by clicking on the transformer and selecting the drop down menu next to the 'att_to_map' text box and selecting the 'Open text editor...' option. Explicitly enter the attribute key name in the text editor (ie: contacts{}.role). / IMPORTANT: Do not select the 'Attribute Value' option from the drop down menu to select the attribute key name.
Format (reader XLSXR_1)
    attributes: original_value char(160), real_value char(10), resource_type_fr char(20), resource_type_en char(20)
    -> METADATA_FORMAT_MAPPER [LOOKUP_TABLE_INPUT]
    -> METADATA_FORMAT_MAPPER_2 [LOOKUP_TABLE_INPUT]
Note: METADATA_FORMAT_MAPPER [METADATA_FORMAT_MAPPER] / [Linked] / User Parameters: / ATT_TO_MAP: resources{}.format / ERROR_NOT_MAPPED: YES / REAL_VALUE_REFRESH: YES / RES_TYPE_FR_REFRESH: YES / RES_TYPE_EN_REFRESH: YES
METADATA_FORMAT_MAPPER
    ATT_TO_MAP = resources{}.format
    ERROR_NOT_MAPPED = YES
    REAL_VALUE_REFRESH = YES
    RES_TYPE_EN_REFRESH = YES
    RES_TYPE_FR_REFRESH = YES
    -> AttributeRemover_4
    -> MAPPING_ERROR_LIST_CREATOR
AttributeRemover_4
    LIST_ATTRS = mapping_errors{}
    -> METADATA_FORMAT_MAPPER_2 [DATA_INPUT]
Note: METADATA_FORMAT_MAPPER_2 [METADATA_FORMAT_MAPPER] / [Linked] / User Parameters: / ATT_TO_MAP: distributionList{}.format / ERROR_NOT_MAPPED: YES / REAL_VALUE_REFRESH: YES / RES_TYPE_FR_REFRESH: NO / RES_TYPE_EN_REFRESH: NO
METADATA_FORMAT_MAPPER_2
    ATT_TO_MAP = distributionList{}.format
    ERROR_NOT_MAPPED = YES
    REAL_VALUE_REFRESH = YES
    RES_TYPE_EN_REFRESH = NO
    RES_TYPE_FR_REFRESH = NO
    -> AttributeRemover_5
    -> MAPPING_ERROR_LIST_CREATOR
Note: Removing error list
AttributeRemover_5
    LIST_ATTRS = mapping_errors{}
    -> METADATA_VALUE_MAPPER_5 [DATA_INPUT]
Progress (reader XLSXR_1)
    attributes: original_value char(18), real_value_english char(18), real_value_french char(18), code_value char(7)
    -> METADATA_VALUE_MAPPER_5 [LOOKUP_TABLE_INPUT]
Note: METADATA_VALUE_MAPPER_5 [METADATA_VALUE_MAPPER] / [Linked] / User Parameters: / ATT_TO_MAP: progress_code / ERROR_NOT_MAPPED: YES / ENGLISH_REFRESH: YES / FRENCH_REFRESH: YES / CODE_REFRESH: YES
METADATA_VALUE_MAPPER_5
    ATT_TO_MAP = progress_code
    CODE_REFRESH = YES
    ENGLISH_REFRESH = YES
    ERROR_NOT_MAPPED = YES
    FRENCH_REFRESH = YES
    -> AttributeRemover_6
    -> MAPPING_ERROR_LIST_CREATOR
AttributeRemover_6
    LIST_ATTRS = mapping_errors{}
    -> METADATA_VALUE_MAPPER_6 [DATA_INPUT]
SpatialRepresentation (reader XLSXR_1)
    attributes: original_value char(12), real_value_english char(12), real_value_french char(13), code_value char(7)
    -> METADATA_VALUE_MAPPER_6 [LOOKUP_TABLE_INPUT]
Note: METADATA_VALUE_MAPPER_6 [METADATA_VALUE_MAPPER] / [Linked] / User Parameters: / ATT_TO_MAP: spatial_representation_type / ERROR_NOT_MAPPED: YES / ENGLISH_REFRESH: YES / FRENCH_REFRESH: YES / CODE_REFRESH: YES
METADATA_VALUE_MAPPER_6
    ATT_TO_MAP = spatial_representation_type
    CODE_REFRESH = YES
    ENGLISH_REFRESH = YES
    ERROR_NOT_MAPPED = YES
    FRENCH_REFRESH = YES
    -> MAPPING_ERROR_LIST_CREATOR
    -> AttributeRemover_7
AttributeRemover_7
    LIST_ATTRS = mapping_errors{}
    -> METADATA_VALUE_MAPPER_4 [DATA_INPUT]
SpatialRef (reader XLSXR_1)
    attributes: original_value char(47), real_value_english char(12)
    -> METADATA_VALUE_MAPPER_4 [LOOKUP_TABLE_INPUT]
Note: METADATA_VALUE_MAPPER_4 [METADATA_VALUE_MAPPER] / [Linked] / User Parameters: / ATT_TO_MAP: spatialref{}.projection_name / ERROR_NOT_MAPPED: NO / ENGLISH_REFRESH: YES / FRENCH_REFRESH: NO / CODE_REFRESH: NO
METADATA_VALUE_MAPPER_4
    ATT_TO_MAP = spatialref{}.projection_name
    CODE_REFRESH = NO
    ENGLISH_REFRESH = YES
    ERROR_NOT_MAPPED = NO
    FRENCH_REFRESH = NO
    -> MAPPING_ERROR_LIST_CREATOR
    -> AttributeRemover_8
AttributeRemover_8
    LIST_ATTRS = mapping_errors{}
    -> METADATA_VALUE_MAPPER_7 [DATA_INPUT]
Codespace (reader XLSXR_1)
    attributes: original_value char(30), reference_codespace_value char(5)
    -> METADATA_VALUE_MAPPER_7 [LOOKUP_TABLE_INPUT]
Note: METADATA_VALUE_MAPPER_7 [METADATA_VALUE_MAPPER] / [Linked] / User Parameters: / ATT_TO_MAP: spatialref{}.projection_system / ERROR_NOT_MAPPED: NO / ENGLISH_REFRESH: YES / FRENCH_REFRESH: NO / CODE_REFRESH: NO
METADATA_VALUE_MAPPER_7
    ATT_TO_MAP = spatialref{}.projection_system
    CODE_REFRESH = NO
    ENGLISH_REFRESH = YES
    ERROR_NOT_MAPPED = NO
    FRENCH_REFRESH = NO
    -> MAPPING_ERROR_LIST_CREATOR
    -> AttributeRemover_9
AttributeRemover_9
    LIST_ATTRS = mapping_errors{}
    -> METADATA_VALUE_MAPPER_9 [DATA_INPUT]
Keyword (reader XLSXR_1)
    attributes: original_value char(33), real_value_english char(33)
    -> METADATA_VALUE_MAPPER_9 [LOOKUP_TABLE_INPUT]
Note: METADATA_VALUE_MAPPER_9 [METADATA_VALUE_MAPPER] / [Linked] / User Parameters: / ATT_TO_MAP: iso_topic{}.topic_value / ERROR_NOT_MAPPED: NO / ENGLISH_REFRESH: YES / FRENCH_REFRESH: NO / CODE_REFRESH: NO
METADATA_VALUE_MAPPER_9
    ATT_TO_MAP = iso_topic{}.topic_value
    CODE_REFRESH = NO
    ENGLISH_REFRESH = YES
    ERROR_NOT_MAPPED = NO
    FRENCH_REFRESH = NO
    -> AttributeRemover_10
    -> MAPPING_ERROR_LIST_CREATOR
AttributeRemover_10
    LIST_ATTRS = mapping_errors{}
    -> METADATA_VALUE_MAPPER_10 [DATA_INPUT]
Country (reader XLSXR_1)
    attributes: original_value char(3), real_value_english char(7)
    -> METADATA_VALUE_MAPPER_10 [LOOKUP_TABLE_INPUT]
Note: METADATA_VALUE_MAPPER_10 [METADATA_VALUE_MAPPER] / [Linked] / User Parameters: / ATT_TO_MAP: contacts{}.country / ERROR_NOT_MAPPED: NO / ENGLISH_REFRESH: YES / FRENCH_REFRESH: NO / CODE_REFRESH: NO
METADATA_VALUE_MAPPER_10
    ATT_TO_MAP = contacts{}.country
    CODE_REFRESH = NO
    ENGLISH_REFRESH = YES
    ERROR_NOT_MAPPED = NO
    FRENCH_REFRESH = NO
    -> AttributeRemover_11
    -> MAPPING_ERROR_LIST_CREATOR
AttributeRemover_11
    LIST_ATTRS = mapping_errors{}
    -> MORE_INFO_MANAGER
Note: AB_MISSING_ATTRIBUTE_MANAGER : EMAIL_FORMAT_ERROR_OUTPUT
Junction_6
    -> MAPPING_ERROR_LIST_CREATOR
MAPPING_ERROR_LIST_CREATOR
    LIST_ATTR = mapping_errors{}
    LIST_NAME = mapping_errors{}
    -> ATTRIBUTE_MAPPING_ERRORS (writer FFS_1)

Bookmark: Language Translation
Note: NOTE: AWS_TRANSLATE tools only function in the AWS Server environment. Published parameter AWS_TRANSLATE_ON switches between translate tool or proxy. Using proxy saves on translation fees when developing/testing, or allows user to run tool outside of AWS Server.
SELECT: Tester
    BOOL_OP = OR
    COMPOSITE_TEST = 1
    TEST_CLAUSE = TEST $(AWS_TRANSLATE_ON) = Yes
    TEST_MODE = TEST
    PASSED -> AWS_TRANSLATE_ENGLISH_TO_FRENCH
    FAILED -> FRENCH_TRANSLATION_PROXY_BUILDER
Note: Proxy transformer used for development testing in place of AWS Translate.
FRENCH_TRANSLATION_PROXY_BUILDER
    -> METADATA_VALUE_MAPPER_3 [DATA_INPUT]
Note: Custom transformer sends specific extracted attributes to the Amazon translation service to be translated to French.
AWS_TRANSLATE_ENGLISH_TO_FRENCH
    -> METADATA_VALUE_MAPPER_3 [DATA_INPUT]
    -> AB_AllRecords_Translated (writer FFS_3)
AB_AllRecords_Translated (writer FFS_3)
    attributes: progress_code varchar(200), iso_topic{}.topic_value varchar(200), tags{}.display_name varchar(200), spatial_representation_type varchar(200), geodiscover_url varchar(200), geodiscover_url_formated varchar(200), method varchar(200), data_collection_start_date varchar(200), data_collection_end_date varchar(200), id varchar(200), record_last_modified varchar(200), metadata_standard varchar(200), metadata_standard_version varchar(200), title varchar(200), notes varchar(200), east_bound_longitude varchar(200), north_bound_latitude varchar(200), west_bound_longitude varchar(200), south_bound_latitude varchar(200), distributionList{} varchar(200), tags{} varchar(200), resource_update_cycle varchar(200), record_create_date varchar(200), record_publish_date varchar(200), iso_topic{} varchar(200), spatialref{} varchar(200), sector varchar(200), contacts varchar(200), name varchar(200), email varchar(200),
      role_code varchar(200), role varchar(200), role_fr varchar(200), position varchar(200), position_fr varchar(200), contacts{}.contacts varchar(200), contacts{}.name varchar(200), contacts{}.email varchar(200), contacts{}.role_code varchar(200), contacts{}.role varchar(200), contacts{}.role_fr varchar(200), contacts{}.position varchar(200), contacts{}.position_fr varchar(200), projectionList{}.codespace varchar(200), projectionList{}.projection_name varchar(200), projectionList{}.version varchar(200), resources{}.name varchar(200), resources{}.url varchar(200), resources{}.format varchar(200), resources{}.protocol varchar(200), resources{} varchar(200), resources{}.data_collection_end_date varchar(200), resources{}.data_collection_start_date varchar(200), resources{}.resource_update_cycle varchar(200), resources{0}.data_collection_start_date varchar(200), resources{0}.data_collection_end_date varchar(200), _element_count_resources varchar(200), _element_count_res varchar(200), contacts{}.phone varchar(200), contacts{}.facsimile varchar(200),
      contacts{}.address varchar(200), contacts{}.city varchar(200), contacts{}.postal_code varchar(200), contacts{}.administrative_area varchar(200), contacts{}.country varchar(200), distributionList{}.format varchar(200), title_fr varchar(200), sector_fr varchar(200), notes_fr varchar(200), tags{}.display_name_fr varchar(200), resources{}.name_fr varchar(200)

Bookmark: Data prepartion for medadata section
Note: Tests the more_info{}.link list for valid attribute values and filters them out where missing
MORE_INFO_MANAGER
    -> GMD_SECTION_DATA_EXTRACTION
Note: Creates lists and removes duplicates for GMD_Section
GMD_SECTION_DATA_EXTRACTION
    -> REMOVE_BROKEN_URL_WMS_ESRI_REST

Bookmark: Data cleanup. Dropping broken web services
Note: Tests WMS/ESRI_REST resource URL's and removes them where broken
REMOVE_BROKEN_URL_WMS_ESRI_REST
    -> WMS_REST_LANGUAGE_FORMATTER
    FAULTY_URL_OUTPUT -> web_service_error (writer FFS_2)

Bookmark: HNAP Rules- 1 web service per language.
Note: Formats WMS and ESRI REST resources to add French versions and formats French and English versions with valid supporting attributes
WMS_REST_LANGUAGE_FORMATTER
    ADMIN_EMAIL = $(EMAIL_ADMIN)
    EMAIL_ENCRYPTION = $(EMAIL_ENCRYPTION)
    EMAIL_HOST = $(EMAIL_HOST)
    EMAIL_PORT = $(EMAIL_PORT)
    EMAIL_SENDER = $(EMAIL_SENDER)
    EMAIL_SENDER_PASSWORD = $(EMAIL_SENDER_PASSWORD)
    -> DUPLICATE_SERVICE_REMOVER
Note: Removes duplicate WMS or ESRI REST resources where they exist, that would otherwise invalidate the dataset
DUPLICATE_SERVICE_REMOVER
    -> PythonCaller_3

Bookmark: XML CREATION AND WRITING
Note: Extracts and maps attributes to values required by the XML root template or sub-templates, compliles the templates to a single XML file, and publishes the XML to the PyCSW, or to a local folder. / NOTE: The publication method is defaulted to 'Auto', which will read the method attribute set in the CREATE transformer. Can override to 'Local', 'Insert' or 'Update' by selecting option in pubished parameter 'METHOD_SELECT'.
Note: Removing all white spaces
PythonCaller_3
    PYTHONSOURCE:
      import fme
      import fmeobjects
      # Template Function interface:
      # When using this function, make sure its name is set as the value of
      # the 'Class or Function to Process Features' transformer parameter
      def processFeature(feature):
          try:
              for att in feature.getAllAttributeNames():
                  value=feature.getAttribute(att)
                  if isinstance(value,str):
                      feature.setAttribute(att,value.lstrip().rstrip())


          except:
              pass
    PYTHONSYMBOL = processFeature
    -> XML_PUBLISHER
Note: Excel config file to map AB attributes to those required by XML templates
Config_AB (reader XLSXR_1)
    attributes: HNAP_ATTRIBUTES char(54), FEATURE_ATTRIBUTES char(60), METADATA_SECTION char(191)
    -> XML_PUBLISHER [CONFIG_FILE]
XML_PUBLISHER
    CSW_URL = http://pycsw-6ee5e20.nrn.awscloud.internal/pycsw?
    METHOD_SELECT = $(METHOD_SELECT)
    TEMPLATE_GMD_CITEDRESPONSIBLEPARTY = $(TEMPLATE_GMD_CITEDRESPONSIBLEPARTY)
    TEMPLATE_GMD_CONTACT = $(TEMPLATE_GMD_CONTACT)
    TEMPLATE_GMD_DISTRIBUTIONFORMAT = $(TEMPLATE_GMD_DISTRIBUTIONFORMAT)
    TEMPLATE_GMD_DISTRIBUTOR = $(TEMPLATE_GMD_DISTRIBUTOR)
    TEMPLATE_GMD_KEYWORDS = $(TEMPLATE_GMD_KEYWORDS)
    TEMPLATE_GMD_MDMETADATA = $(TEMPLATE_GMD_MDMETADATA)
    TEMPLATE_GMD_REFERENCESYSTEMINFO = $(TEMPLATE_GMD_REFERENCESYSTEMINFO)
    TEMPLATE_GMD_RESOURCEMAINTENANCE = $(TEMPLATE_GMD_RESOURCEMAINTENANCE)
    TEMPLATE_GMD_TOPICCATEGORY = $(TEMPLATE_GMD_TOPICCATEGORY)
    TEMPLATE_GMD_TRANSFEROPTIONS = $(TEMPLATE_GMD_TRANSFEROPTIONS)
    LOCAL -> text_line (writer TEXTLINE_2)
    INSERT_PASSED -> text_line (writer TEXTLINE_3)
    INSERT_PASSED -> NOTIFY_UPDATE [INSERTED]
    INSERT_FAILED -> text_line (writer TEXTLINE_1)
    INSERT_FAILED -> NOTIFY_UPDATE [INSERT_REJECTED]
    UPDATE_PASSED -> text_line (writer TEXTLINE_3)
    UPDATE_PASSED -> NOTIFY_UPDATE [UPDATED]
    UPDATE_FAILED -> text_line (writer TEXTLINE_1)
    UPDATE_FAILED -> NOTIFY_UPDATE [UPDATE_REJECTED]

Bookmark: Pretranslation and Translation Actions
Note: Custom transformer queries the Alberta open government portal API and exposes returned attributes and filters data by open, geospatial data and date. It also validates the currency of PyCSW metadata records and removes those that no longer exist in the AB open government portal.
