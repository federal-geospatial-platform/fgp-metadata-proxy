FME workspace SK_FGP_XML_BUILDER_PROD_10.fmw

Parameters:
- ACTIVATE_GEO = Yes
- ACTIVATE_NON_GEO = No
- ACTIVATE_TRANSLATION = No
- DCAT_READER_SELECT = Yes
- FORCED_PYCSW_URL =
- IN_FFS_TESTING_FILE = $(IN_OUT_WORKING_DIR)\$(P-T_ABBR)\Source_16May22.ffs
- LOCAL_SOURCE_METADATA_DELTA_FINDER = Yes
- LOCAL_WRITER = Yes
- P-T_ABBR = SK
- METADATA_OVERWRITE = NO   # METADATA OVERWRITE
- IN_OUT_WORKING_DIR = $(FME_SHAREDRESOURCE_DATA)\PT_Harvester
- SAMPLE_SIZE = 0
- URL_VALIDATION = Yes
- IN_CSV_LOOKUPTABLES_DIR = $(IN_OUT_WORKING_DIR)\LOOKUP_TABLES   # Lookup Tables Directory
- IN_GMD_XML_TEMPLATE_DIR = $(IN_OUT_WORKING_DIR)\XML_TEMPLATES
- IN_TBS_JSON_TEMPLATE_DIR = $(IN_OUT_WORKING_DIR)\JSON_TEMPLATES
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- FME_SHAREDRESOURCE_DATA = C:\Data   # FME Server Data Directory

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(OUT_XLS_NOTIFICATION_DIR)
- TEXTLINE_4: TEXTLINE to C:\Data\PT_Harvester\NS\JSON_LOCAL

Feature_IO_4 [off]
    FFS_FILE_PATH = $(IN_OUT_PATH)/$(IN_OUT_FILENAME).ffs
    IN_OUT_FILENAME = LICENSE_FILTER_NG
    IN_OUT_PATH = $(IN_OUT_FFS_TESTING_PATH:)
    Output_Mode = oui
Feature_IO_2 [off]
    FFS_FILE_PATH = $(IN_OUT_PATH)/$(IN_OUT_FILENAME).ffs
    IN_OUT_FILENAME = before_filtering_and_converting
    IN_OUT_PATH = $(IN_OUT_FFS_TESTING_PATH:)
    Output_Mode = no
Feature_IO_8 [off]
    FFS_FILE_PATH = $(IN_OUT_PATH)/$(IN_OUT_FILENAME).ffs
    IN_OUT_FILENAME = Date_conversion
    IN_OUT_PATH = $(IN_OUT_FFS_TESTING_PATH:)
    Output_Mode = oui
Feature_IO_3
    FFS_FILE_PATH = $(IN_OUT_PATH)/$(IN_OUT_FILENAME).ffs
    IN_OUT_FILENAME = before_Creation_de_la_liste
    IN_OUT_PATH = $(IN_OUT_FFS_TESTING_PATH:)
    Output_Mode = no
    -> SK_URL_FIXER
Feature_IO_5
    FFS_FILE_PATH = $(IN_OUT_PATH)/$(IN_OUT_FILENAME).ffs
    IN_OUT_FILENAME = before_Filtrage_geo_non_geo
    IN_OUT_PATH = $(IN_OUT_FFS_TESTING_PATH:)
    Output_Mode = no
Feature_IO_6
    FFS_FILE_PATH = $(IN_OUT_PATH)/$(IN_OUT_FILENAME).ffs
    IN_OUT_FILENAME = before_Metadata_value_mapping_GEO
    IN_OUT_PATH = $(IN_OUT_FFS_TESTING_PATH:)
    Output_Mode = oui
Feature_IO_7
    FFS_FILE_PATH = $(IN_OUT_PATH)/$(IN_OUT_FILENAME).ffs
    IN_OUT_FILENAME = before_New_bookmark
    IN_OUT_PATH = $(IN_OUT_FFS_TESTING_PATH:)
    Output_Mode = no
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer
VariableRetriever_12
    SCOPE = Global
    VALUE_ATTR = _timestamp
    VARNAME = _timestamp
    -> invalid_metadata (writer XLSXW_1)
invalid_metadata (writer XLSXW_1)
    attributes: id auto(20)
Feature_IO
    FFS_FILE_PATH = $(IN_OUT_PATH)/$(IN_OUT_FILENAME).ffs
    IN_OUT_FILENAME = before_Creation_de_la_liste
    IN_OUT_PATH = $(IN_OUT_FFS_TESTING_PATH:)
    Output_Mode = no

Bookmark: Lecture des données DCAT
Creator
    GEOMTYPE = Geometry Object
    NUM = 1
    CREATED -> DateTimeStamper
DateTimeStamper
    DATETIME_ATTR = _date_temp
    STAMP_TYPE = date
    TIMEZONE = local
    -> VariableSetter
VariableSetter
    SCOPE = Global
    VALUE = @Value(_date_temp)
    VARNAME = _timestamp
    -> Tester
Tester
    BOOL_OP = OR
    COMPOSITE_TEST = 1
    TEST_CLAUSE = TEST $(DCAT_READER_SELECT) = Yes
    TEST_MODE = TEST
    PASSED -> DCAT_Reader
    FAILED -> FeatureReader [INITIATOR]
DCAT_Reader
    GEO_HUB_SERVICE = Saskatchewan GeoHub
    Résultats -> DCAT_TO_CKAN_RENAMER
Note: Reads pre-generated FFS file for testing as substitute for ARCGIS_HUB_READER
FeatureReader
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> DCAT_TO_CKAN_RENAMER
DCAT_TO_CKAN_RENAMER
    -> ATTRIBUTE_VALUE_TEXT_CLEANER
ATTRIBUTE_VALUE_TEXT_CLEANER
    -> AttributeExposer
AttributeExposer
    ATTR_LIST = license,license_info
    -> LICENSE_FILTER_NG
LICENSE_FILTER_NG
    FEATURE_TYPE = License_SK
    IN_CSV_LOOKUP_TABLES_DIR = $(IN_CSV_LOOKUPTABLES_DIR)
    LICENSE_ATT = @Value(license_info)
    P-T_ABBR = $(P-T_ABBR)
    LICENSE_FILTER_PASSED -> AttributeExposer_24
    LICENSE_FILTER_PASSED -> Feature_IO_4
    LICENSE_FILTER_UNPASSED -> VariableRetriever_8
AttributeExposer_24
    ATTR_LIST = id
    -> DuplicateFilter
DuplicateFilter
    INPUT_ORDERED_CHOICE = No
    KEYATTR = id
    UNIQUE -> Feature_IO_2 [off]
    UNIQUE -> DEFAULT_ATTRIBUTE_MAPPER_NG
    DUPLICATE -> VariableRetriever_7
VariableRetriever_7
    SCOPE = Global
    VALUE_ATTR = _timestamp
    VARNAME = _timestamp
    -> Duplicated Feature (writer XLSXW_1)
Duplicated Feature (writer XLSXW_1)
    attributes: id string(200)
VariableRetriever_8
    SCOPE = Global
    VALUE_ATTR = _timestamp
    VARNAME = _timestamp
    -> unknown_licence (writer XLSXW_1)
unknown_licence (writer XLSXW_1)
    attributes: license_id string(200), id string(200), title string(200)

Bookmark: Filtering and converting to inhouse model.
Note: Creating default values for SK
DEFAULT_ATTRIBUTE_MAPPER_NG
    FEATURE_TYPE = Default_SK
    IN_CSV_LOOKUP_TABLES_DIR = $(IN_CSV_LOOKUPTABLES_DIR)
    P-T_ABBR = $(P-T_ABBR)
    -> AttributeExposer_7

Bookmark: Notes
AttributeExposer_7
    ATTR_LIST = _notes_A,_notes_B
    -> StringConcatenator
StringConcatenator
    ACTION = Create New Attribute
    PARM_LINE = fme_basicstring:16%16:@Value(_notes_A)@Value(_notes_B)
    VAL_ATTR = notes
    -> AttributeRemover
AttributeRemover
    REMOVE_ATTRS = _notes_A,_notes_B
    -> AttributeExposer_14

Bookmark: Date conversion
AttributeExposer_14
    ATTR_LIST = id,record_create_date,record_last_modified,record_publish_date,data_collection_start_date,data_collection_end_date
    -> DateTimeConverter
    -> Feature_IO_8 [off]
Note: Record created/modified/publish
DateTimeConverter
    DATETIME_ATTR = record_create_date record_last_modified record_publish_date
    OUT_FORMAT = %Y-%m-%d
    PASSTHROUGH = NO
    REPAIR_INPUT = YES
    -> DateTimeConverter_2
    <REJECTED> -> DateTimeConverter_2
Note: Data Collection start/end
DateTimeConverter_2
    DATETIME_ATTR = data_collection_end_date data_collection_start_date
    OUT_FORMAT = %Y-%m-%d
    PASSTHROUGH = NO
    REPAIR_INPUT = YES
    -> AttributeRemover_2
    <REJECTED> -> AttributeManager
AttributeManager
    ATTR_TABLE = SET_TO data_collection_start_date = 2000-01-01
    -> AttributeRemover_2
AttributeRemover_2
    REMOVE_ATTRS = fme_rejection_code
    -> AttributeExposer_6

Bookmark: Category
AttributeExposer_6
    ATTR_LIST = iso_topic{}.topic_value,tags{}
    -> ListSearcher
Note: iso_topic{}
ListSearcher
    ATTR_VALUE = Biota|Environment|Geoscientific information|Health|Imagery|Imagery, basemaps, and Earth cover|Planning and cadastre|Transportation
    INDEX_ATTR = _list_index
    LIST_ATTR = iso_topic{}.topic_value
    MATCHTYPE = REGULAR_EXPRESSION_ENCODED
    FOUND -> PythonCaller_8
    NOT_FOUND -> ListSearcher_2
PythonCaller_8
    PYTHONSOURCE:
      import fme
      import fmeobjects
      # Template Function interface:
      # When using this function, make sure its name is set as the value of
      # the 'Class or Function to Process Features' transformer parameter
      def processFeature(feature):
          _ndx=feature.getAttribute('_list_index')
          _category=feature.getAttribute('iso_topic{%i}.topic_value'%(_ndx))
          feature.setAttribute('category',_category)
          feature.removeAttribute('_list_index')
    PYTHONSYMBOL = processFeature
    -> Junction_3
Note: tags{}
ListSearcher_2
    ATTR_VALUE = Environment|geoscience|Geological Maps and Publications
    INDEX_ATTR = _list_index
    LIST_ATTR = tags{}
    MATCHTYPE = REGULAR_EXPRESSION_ENCODED
    FOUND -> PythonCaller_9
PythonCaller_9
    PYTHONSOURCE:
      import fme
      import fmeobjects
      # Template Function interface:
      # When using this function, make sure its name is set as the value of
      # the 'Class or Function to Process Features' transformer parameter
      def processFeature(feature):
          _ndx=feature.getAttribute('_list_index')
          _category=feature.getAttribute('tags{%i}'%(_ndx))
          feature.setAttribute('category',_category)
          feature.removeAttribute('_list_index')
    PYTHONSYMBOL = processFeature
    -> Junction_3
Junction_3
    -> PythonCaller_6

Bookmark: Alternate Attribute manager
Note: Remove prefix from email
PythonCaller_6
    PYTHONSOURCE:
      import fme
      import fmeobjects
      from Python.FME_utils import FME_utils

      # Template Function interface:
      # When using this function, make sure its name is set as the value of
      # the 'Class or Function to Process Features' transformer parameter
      def processFeature(feature):

          FME_utils.remove_mailto(feature,'contactPoint_email','contact_email',True)
    PYTHONSYMBOL = processFeature
    -> PythonCaller_5
Note: Add display_name to tags{}
PythonCaller_5
    PYTHONSOURCE:
      import fme
      import fmeobjects
      # Template Function interface:
      # When using this function, make sure its name is set as the value of
      # the 'Class or Function to Process Features' transformer parameter
      def processFeature(feature):
          i=0
          for elem in feature.getAttribute('tags{}'):
              feature.setAttribute('tags_copy{%i}'%(i),elem)
              i+=1

          feature.removeAttribute('tags{}')

          i=0
          for elem in feature.getAttribute('tags_copy{}'):
              feature.setAttribute('tags{%i}.display_name'%(i),elem)
              i+=1

          feature.removeAttribute('tags_copy{}')
    PYTHONSYMBOL = processFeature
    -> ATTRIBUTE_MANAGER_NG
Note: Create Attributes
ATTRIBUTE_MANAGER_NG
    IN_YAML_TEXT:
      resource.id:
          action: attribute_overwrite
          attr2set: id

      update_frequency:
          action: text_not_null
          attr2set: Unknown

      category:
          action: text_not_null
          attr2set: Unknown

      record_publish_date:
          action: attribute_not_null
          attr2set: record_create_date

      metadata.custom_fields.Detailed Metadata.Department:
          action: attribute_not_null
          attr2set: publisher

      resources{0}.name:
          action: attribute_not_null
          attr2set: title

      online_resource_protocol:
          action: attribute_overwrite
          attr2set: resources{0}.type
    -> METADATA_VALUE_MAPPER [DATA_INPUT]
Note: UpdateFrequency_SK
METADATA_VALUE_MAPPER: METADATA_VALUE_MAPPER_NG
    ATT_TO_MAP = update_frequency
    CODE_REFRESH = NO
    ENGLISH_REFRESH = YES
    ERROR_NOT_MAPPED = NO
    FEATURE_TYPE = UpdateFrequency_SK
    FRENCH_REFRESH = NO
    IN_CSV_LOOKUP_TABLES_DIR = $(IN_CSV_LOOKUPTABLES_DIR)
    P-T_ABBR = $(P-T_ABBR)
    -> AttributeExposer_4
AttributeExposer_4
    ATTR_LIST = resource.id
    -> UNIQUE_ID_CREATOR
    -> AttributeExposer_2
UNIQUE_ID_CREATOR
    UNIQUE_ATT = @Value(resource.id)
    -> Feature_IO [off]

Bookmark: Création de la liste des ressources pour les jeux de données
AttributeExposer_2
    ATTR_LIST = resource.id,id
    -> GEOPORTAL_WEBLINK_ADDER_NG
GEOPORTAL_WEBLINK_ADDER_NG
    FEATURE_TYPE = GeoportalWeblink_SK
    IN_CSV_LOOKUP_TABLES_DIR = $(IN_CSV_LOOKUPTABLES_DIR)
    P-T_ABBR = $(P-T_ABBR)
    URL_VALIDATION = Yes
    WEBLINK_WILDCARD = @Value(id)
    -> AttributeExposer_5
AttributeExposer_5
    ATTR_LIST = resources{}.url
    -> ListElementCounter
ListElementCounter
    CNT_ATTR = _element_count
    LIST_NAME = resources{}
    -> Tester_3
Tester_3
    BOOL_OP = OR
    COMPOSITE_TEST = 1
    TEST_CLAUSE = TEST @Value(_element_count) > 1
    TEST_MODE = TEST
    PASSED -> Feature_IO_3 [off]
SK_URL_FIXER
    -> AttributeExposer_16
AttributeExposer_16
    ATTR_LIST = resources{0}.url
    -> SK_RESOURCES_NAME_FINDER
SK_RESOURCES_NAME_FINDER
    FEATURE_TYPE = SK_ImmutableURLs.csv
    IN_CSV_LOOKUP_TABLES_DIR = $(IN_CSV_LOOKUPTABLES_DIR)
    LIST_ATTR = resources{}
    P-T_ABBR = $(P-T_ABBR)
    -> PythonCaller_3
    MISSING_URL -> VariableRetriever_4
    REJECTED_JSON -> VariableRetriever_6
    JSON_WITHOUT_NAME -> VariableRetriever_3
PythonCaller_3
    NEW_ATTRIBUTES = resources{}.name resources{}.url resources{}.format resources{}.name_fr
    PYTHONSOURCE:
      import fme
      import fmeobjects
      logger = fmeobjects.FMELogFile()
      # Template Function interface:
      # When using this function, make sure its name is set as the value of
      # the 'Class or Function to Process Features' transformer parameter
      def processFeature(feature):
          list_attr_name=[r'name_fr',r'fgp_publish']

          #Extracting number of resources
          list_url=feature.getAttribute('resources{}.url')
          if list_url:
              #Looping in resources
              for ndx in range(len(list_url)):
                  #Looping in attributes
                  for attr_name in list_attr_name:
                      feature.setAttribute('resources{%i}.%s'%(ndx,attr_name),'')
    PYTHONSYMBOL = processFeature
    -> EMPTY_FORMAT_MAPPER [DATA_INPUT]
EMPTY_FORMAT_MAPPER
    DATA_OUTPUT -> Feature_IO_5 [off]
    DATA_OUTPUT -> PythonCaller
VariableRetriever_6
    SCOPE = Global
    VALUE_ATTR = _timestamp
    VARNAME = _timestamp
    -> REJECTED JSON (writer XLSXW_1)
REJECTED JSON (writer XLSXW_1)
    attributes: license_id string(200), id string(200), title string(200)
VariableRetriever_4
    SCOPE = Global
    VALUE_ATTR = _timestamp
    VARNAME = _timestamp
    -> MISSING URL (writer XLSXW_1)
MISSING URL (writer XLSXW_1)
    attributes: id string(200), url string(200)
VariableRetriever_3
    SCOPE = Global
    VALUE_ATTR = _timestamp
    VARNAME = _timestamp
    -> JSON WITHOUT NAME (writer XLSXW_1)
JSON WITHOUT NAME (writer XLSXW_1)
    attributes: id string(200), url string(200)

Bookmark: Filtrage geo / non-geo
PythonCaller
    NEW_ATTRIBUTES = cl{}.value
    PYTHONSOURCE:
      import fme
      import fmeobjects
      # Template Function interface:
      # When using this function, make sure its name is set as the value of
      # the 'Class or Function to Process Features' transformer parameter
      def processFeature(feature):
          tags=feature.getAttribute('tags{}.display_name')

          i=0
          for tag in tags:
              feature.setAttribute('cl{%i}.value'%(i),tag.lower())
              i+=1
    PYTHONSYMBOL = processFeature
    -> GEO_NONE_GEO_SELECTOR
GEO_NONE_GEO_SELECTOR
    CSV_FILE_NAME = GeoSpatialValidation
    CSV_PATH = $(IN_CSV_LOOKUPTABLES_DIR)
    CSV_PROVINCE = $(P-T_ABBR)
    YAML_DIRECTIVES:
      resources{}.format:
        domain: lookup_table_format
        spatial_type: overwrite
        not_found: log
        search_type: equals
    GEOSPATIAL -> AttributeExposer_11
    NONE_GEOSPATIAL -> MANUAL_GEOSPATIAL_SETTER_NG [DATA_INPUT]
    LOG_ERROR -> VariableRetriever_13
SPATIAL_TYPE_MAPPER_NG
    FEATURE_TYPE = SpatialType_SK
    IN_CSV_LOOKUP_TABLES_DIR = $(IN_CSV_LOOKUPTABLES_DIR)
    P-T_ABBR = $(P-T_ABBR)
    DATA_OUTPUT_FAILED -> VariableRetriever
    DATA_OUTPUT_PASSED -> TestFilter
VariableRetriever
    SCOPE = Global
    VALUE_ATTR = _timestamp
    VARNAME = _timestamp
    -> Spatial_Type_Mapper_Failed (writer XLSXW_1)
Spatial_Type_Mapper_Failed (writer XLSXW_1)
    attributes: id string(20), title string(80), url string(80)
TestFilter
    DEFAULT_VALUE = <UNFILTERED>
    TEST_LIST = "BOOL_OP,OR,COMPOSITE_TEST,""""""1"""""",TEST_CLAUSE,TEST @LowerCase($(ACTIVATE_GEO)) = yes",GEO_ACTIVATE
    GEO_ACTIVATE -> Feature_IO_6 [off]
    GEO_ACTIVATE -> METADATA_VALUE_MAPPER_NG_2 [DATA_INPUT]
VariableRetriever_13
    SCOPE = Global
    VALUE_ATTR = _timestamp
    VARNAME = _timestamp
    -> unknown_format (writer XLSXW_1)
unknown_format (writer XLSXW_1)
    attributes: format auto(20)
MANUAL_GEOSPATIAL_SETTER_NG
    FEATURE_TYPE = UnmappedGeoData_SK
    IN_CSV_LOOKUP_TABLES_DIR = $(IN_CSV_LOOKUPTABLES_DIR)
    P-T_ABBR = $(P-T_ABBR)

Bookmark: Remove blank 'spatial_type' from 'resources{}'
AttributeExposer_11
    ATTR_LIST = resources{}
    -> ListElementCounter_3
ListElementCounter_3
    CNT_ATTR = _nb_resouces
    LIST_NAME = resources{}
    -> PythonCaller_10
PythonCaller_10
    PYTHONSOURCE:
      import fme
      import fmeobjects
      from Python.FME_utils import FME_utils
      # Template Function interface:
      # When using this function, make sure its name is set as the value of
      # the 'Class or Function to Process Features' transformer parameter
      def processFeature(feature):

          spatial_types = []

          i=0

          for _ in range(int(feature.getAttribute('_nb_resouces'))):
              _spatial_type=feature.getAttribute('resources{%i}.spatial_type'%(i))
              if _spatial_type is not None and _spatial_type == "":
                  feature.removeAttribute('resources{%i}.spatial_type'%(i))
              i=i+1

          feature.removeAttribute('_nb_resouces')
    PYTHONSYMBOL = processFeature
    -> SPATIAL_TYPE_MAPPER_NG [DATA_INPUT]

Bookmark: Metadata Value Mapping - GEO
Note: Topic
METADATA_VALUE_MAPPER_NG_2
    ATT_TO_MAP = category
    CODE_REFRESH = NO
    ENGLISH_REFRESH = YES
    ERROR_NOT_MAPPED = YES
    FEATURE_TYPE = Topic
    FRENCH_REFRESH = NO
    IN_CSV_LOOKUP_TABLES_DIR = $(IN_CSV_LOOKUPTABLES_DIR)
    P-T_ABBR = $(P-T_ABBR)
    -> METADATA_VALUE_MAPPER_NG_3 [DATA_INPUT]
Note: Role
METADATA_VALUE_MAPPER_NG_3
    ATT_TO_MAP = role
    CODE_REFRESH = YES
    ENGLISH_REFRESH = YES
    ERROR_NOT_MAPPED = YES
    FEATURE_TYPE = Role
    FRENCH_REFRESH = YES
    IN_CSV_LOOKUP_TABLES_DIR = $(IN_CSV_LOOKUPTABLES_DIR)
    P-T_ABBR = $(P-T_ABBR)
    -> METADATA_VALUE_MAPPER_NG_4 [DATA_INPUT]
Note: Update
METADATA_VALUE_MAPPER_NG_4
    ATT_TO_MAP = update_frequency
    CODE_REFRESH = YES
    ENGLISH_REFRESH = YES
    ERROR_NOT_MAPPED = YES
    FEATURE_TYPE = Update
    FRENCH_REFRESH = YES
    IN_CSV_LOOKUP_TABLES_DIR = $(IN_CSV_LOOKUPTABLES_DIR)
    P-T_ABBR = $(P-T_ABBR)
    -> METADATA_VALUE_MAPPER_NG_5 [DATA_INPUT]
Note: Progress
METADATA_VALUE_MAPPER_NG_5
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUPTABLES_DIR)
    P-T_ABBR = $(P-T_ABBR)
    -> METADATA_VALUE_MAPPER_NG_7 [DATA_INPUT]
Note: SpatialRepresentation
METADATA_VALUE_MAPPER_NG_7
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUPTABLES_DIR)
    P-T_ABBR = $(P-T_ABBR)
    -> METADATA_FORMAT_MAPPER_NG [DATA_INPUT]
Note: Format
METADATA_FORMAT_MAPPER_NG
    ATT_TO_MAP = resources{}.format
    ERROR_NOT_MAPPED = YES
    FEATURE_TYPE = Format
    IN_CSV_LOOKUP_TABLES_DIR = $(IN_CSV_LOOKUPTABLES_DIR)
    P-T_ABBR = $(P-T_ABBR)
    REAL_VALUE_REFRESH = YES
    RES_TYPE_EN_REFRESH = YES
    RES_TYPE_FR_REFRESH = YES
    -> METADATA_VALUE_MAPPER_ERROR_MANAGER
METADATA_VALUE_MAPPER_ERROR_MANAGER
    ERROR_OUTPUT -> VariableRetriever_11
    DATA_OUTPUT -> AttributeRemover_6
Note: Removing error list
AttributeRemover_6
    LIST_ATTRS = mapping_errors{}
    -> RESOURCE_NAME_UNDERSCORE_REMOVER
VariableRetriever_11
    SCOPE = Global
    VALUE_ATTR = _timestamp
    VARNAME = _timestamp
    -> GEO_ATTRIBUTE_MAPPING_ERRORS (writer XLSXW_1)
GEO_ATTRIBUTE_MAPPING_ERRORS (writer XLSXW_1)
    attributes: error string(200), id string(200), _element_index string(200), _timestamp string(200)

Bookmark: Remove all underscores from resources{}.name attributes
RESOURCE_NAME_UNDERSCORE_REMOVER
    DATA_OUTPUT -> REMOVE_BROKEN_URL_WMS_ESRI_REST

Bookmark: Drop Broken Web Services
REMOVE_BROKEN_URL_WMS_ESRI_REST
    -> WMS_REST_LANGUAGE_FORMATTER
    FAULTY_URL_OUTPUT -> VariableRetriever_2
VariableRetriever_2
    SCOPE = Global
    VALUE_ATTR = _timestamp
    VARNAME = _timestamp
    -> MAP_SERVICE_URL_ERRORMAP (writer XLSXW_1)
MAP_SERVICE_URL_ERRORMAP (writer XLSXW_1)
    attributes: id string(200), url string(200), format string(200), _url_failure_message string(200), _timestamp string(200)

Bookmark: HNAP RULES
WMS_REST_LANGUAGE_FORMATTER
    -> DUPLICATE_SERVICE_REMOVER
DUPLICATE_SERVICE_REMOVER
    -> GMD_SECTION_DATA_EXTRACTION
GMD_SECTION_DATA_EXTRACTION
    -> Feature_IO_7 [off]
    -> AttributeCreator_3

Bookmark: New Bookmark
AttributeCreator_3
    ATTR_TABLE = SET_TO csw_url = $(FORCED_PYCSW_URL)
    -> AttributeExposer_8
AttributeExposer_8
    ATTR_LIST = search_criteria_pycsw,csw_url
    -> METADATA_DELTA_FINDER_NG
METADATA_DELTA_FINDER_NG
    ABSTRACT_ATT_NEW = notes
    ABSTRACT_ATT_REF = MD_Metadata.identificationInfo.MD_DataIdentification.abstract.CharacterString
    CSW_FILTER = @Value(search_criteria_pycsw)
    CUSTOM_CSW_CKAN_URL = @Value(csw_url)
    DATESTAMP_ATT_NEW = record_last_modified
    DATESTAMP_ATT_REF = MD_Metadata.dateStamp.Date
    ID_ATT_NEW = id
    ID_ATT_REF = MD_Metadata.fileIdentifier.CharacterString
    LOCAL_SOURCE = Yes
    LOCAL_SOURCE_DIR = $(OUT_XML_LOCAL_DIR)
    LOCAL_SOURCE_FORMAT = XML
    METADATA_OVERWRITE = $(METADATA_OVERWRITE)
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    No_Change -> AttributeExposer_3
    Update -> AttributeExposer_3
Note: Exposes PyCSW_Transaction attribute
AttributeExposer_3
    ATTR_LIST = PyCSW_Transaction
    -> AttributeFilter
Note: Filters items by PyCSW transaction type
AttributeFilter
    ATTR_NAME = PyCSW_Transaction
    ATTR_VALUES = <Empty>,<Missing>,<Null>,<Unfiltered>,No change,Update,Insert,Delete
    <EMPTY> -> Terminator
    <MISSING> -> Terminator
    <NULL> -> Terminator
    <UNFILTERED> -> Terminator
    No change -> Tester_2
    Update -> Junction_2
    Insert -> Junction_2
    Delete -> AttributeKeeper
Terminator
    MESSAGE = ERROR: Unknown _event value from Metadata_Delta
Note: Selects items with no change for publishing, overwriting all existing data
Tester_2
    BOOL_OP = OR
    COMPOSITE_TEST = 1
    TEST_CLAUSE = TEST $(METADATA_OVERWRITE) = YES
    TEST_MODE = TEST
    PASSED -> AttributeCreator
    FAILED -> AttributeExposer_10
AttributeExposer_10
    ATTR_LIST = id
    -> StatisticsCalculator
Note: Reset to update
AttributeCreator
    ATTR_TABLE = SET_TO PyCSW_Transaction = Update
    -> Junction_2
Junction_2
    -> AWS_TRANSLATE_2
Note: Retains ID for list of deleted items
AttributeKeeper
    KEEP_ATTRS = id
    -> VariableRetriever_9
VariableRetriever_9
    SCOPE = Global
    VALUE_ATTR = _timestamp
    VARNAME = _timestamp
    -> AttributeExposer_12
AttributeExposer_12
    ATTR_LIST = id
    -> DELETEDRECORDS (writer XLSXW_1)
DELETEDRECORDS (writer XLSXW_1)
    attributes: _timestamp string(200), id string(200)
Creator_2
    GEOMTYPE = Geometry Object
    NUM = 1
    CREATED -> StatisticsCalculator
StatisticsCalculator
    COMPUTE_HISTOGRAM = NO
    COUNT_ATTR = _count
    PREPEND_ATTR_NAME_CHOICE = For multiple results only
    STATS_ATTRS = id
    SUMMARY -> AttributeCreator_2
AttributeCreator_2
    ATTR_TABLE = SET_TO _real_count = @Evaluate(@Value(_count)-1)
    -> StatisticsCalculator_Summary
StatisticsCalculator_Summary: Logger
    LOG_FEATURE = NONE
    MAXFEATS = 20
    MESSAGE:
      ************************
      **** Unchanged Report ****
      ************************

      @Value(_real_count) features were unchanged

      ************************
      ************************
      ************************
    SEVERITY = INFO

Bookmark: AWS Translation
Note: English to french / notes, / title, / tags_en / resources name
AWS_TRANSLATE_2
    ACTIVATE_TRANSLATION = $(ACTIVATE_TRANSLATION)
    ATTR_2_TRANSLATE = notes,title,sector
    ATTR_LIST_2_TRANSLATE = tags{}.display_name,resources{}.name
    MODE = English-->French
    -> AttributeExposer_20
    TRANSLATION_PROBLEM -> VariableRetriever_5
AttributeExposer_20
    ATTR_LIST = _typedataset
    -> Tester_6
Tester_6
    BOOL_OP = OR
    COMPOSITE_TEST = 1
    TEST_CLAUSE = TEST @Value(_typedataset) = NONGEO
    TEST_MODE = TEST
    PASSED -> AttributeExposer_17
    FAILED -> AttributeExposer_9
VariableRetriever_5
    SCOPE = Global
    VALUE_ATTR = _timestamp
    VARNAME = _timestamp
    -> Translation_errors (writer XLSXW_1)
Translation_errors (writer XLSXW_1)
    attributes: id string(20), _timestamp string(20)

Bookmark: Rebuilding tags list
AttributeExposer_9
    ATTR_LIST = tags{}
    -> ListElementCounter_2
ListElementCounter_2
    CNT_ATTR = _nb_tags
    LIST_NAME = tags{}
    -> PythonCaller_2
PythonCaller_2
    NEW_ATTRIBUTES = tags{}.display_name_lower tags{}.display_name_fr_lower
    PYTHONSOURCE:
      import fme
      import fmeobjects
      # Template Function interface:
      # When using this function, make sure its name is set as the value of
      # the 'Class or Function to Process Features' transformer parameter
      def processFeature(feature):
          i=0

          for j in range(int(feature.getAttribute('_nb_tags'))):
              feature.setAttribute('tags{%i}.display_name_lower'%(i),feature.getAttribute('tags{%i}.display_name'%(j)).lower())
              feature.setAttribute('tags{%i}.display_name_fr_lower'%(i),feature.getAttribute('tags{%i}.display_name_fr'%(j)).lower())
              i=i+1
    PYTHONSYMBOL = processFeature
    -> XML_PUBLISHER_NG

Bookmark: XML CREATION AND WRITING
XML_PUBLISHER_NG
    FEATURE_TYPE = Config_SK
    IN_CSV_LOOKUP_TABLES_DIR = $(IN_CSV_LOOKUPTABLES_DIR)
    LOCAL_WRITER = YES
    P-T_ABBR = $(P-T_ABBR)
    TEMPLATE_GMD_CITEDRESPONSIBLEPARTY = $(IN_GMD_XML_TEMPLATE_DIR)/GMD_CITEDRESPONSIBLEPARTY.xml
    TEMPLATE_GMD_CONTACT = $(IN_GMD_XML_TEMPLATE_DIR)/GMD_CONTACT.xml
    TEMPLATE_GMD_DISTRIBUTIONFORMAT = $(IN_GMD_XML_TEMPLATE_DIR)/GMD_DISTRIBUTIONFORMAT.xml
    TEMPLATE_GMD_DISTRIBUTOR = $(IN_GMD_XML_TEMPLATE_DIR)/GMD_DISTRIBUTOR.xml
    TEMPLATE_GMD_KEYWORDS = $(IN_GMD_XML_TEMPLATE_DIR)/GMD_KEYWORDS.xml
    TEMPLATE_GMD_MDMETADATA = $(IN_GMD_XML_TEMPLATE_DIR)/GMD_MDMETADATA.xml
    TEMPLATE_GMD_REFERENCESYSTEMINFO = $(IN_GMD_XML_TEMPLATE_DIR)/GMD_REFERENCESYSTEMINFO.xml
    TEMPLATE_GMD_RESOURCEMAINTENANCE = $(IN_GMD_XML_TEMPLATE_DIR)/GMD_RESOURCEMAINTENANCE.xml
    TEMPLATE_GMD_TOPICCATEGORY = $(IN_GMD_XML_TEMPLATE_DIR)/GMD_TOPICCATEGORY.xml
    TEMPLATE_GMD_TRANSFEROPTIONS = $(IN_GMD_XML_TEMPLATE_DIR)/GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    InvalidMetadata -> text_line (writer TEXTLINE_2)
    UPDATE_FAILED -> VariableRetriever_12

Bookmark: JSON CREATION AND WRITING
AttributeExposer_17
    ATTR_LIST = TBS_Topic{}.value,TBS_Subject{}.value,tags{}.display_name,tags{}.display_name_fr
    -> PythonCaller_7
PythonCaller_7
    PYTHONSOURCE:
      import fme
      import fmeobjects
      # Template Function interface:
      # When using this function, make sure its name is set as the value of
      # the 'Class or Function to Process Features' transformer parameter
      def processFeature(feature):
          for i in range(len(feature.getAttribute('resources{}.url'))):
              feature.setAttribute('resources{%d}.language_list'%(i),'["en"]')
    PYTHONSYMBOL = processFeature
    -> JSON_PUBLISHER
    -> JSON_PUBLISHER_NG
JSON_PUBLISHER_NG
    FEATURE_TYPE = SK_JSON_CONFIG
    IN_CSV_LOOKUP_TABLES_DIR = $(IN_CSV_LOOKUPTABLES_DIR)
    JSON_RESOURCE_TEMPLATE = $(IN_TBS_JSON_TEMPLATE_DIR)\TBS_RESOURCES_TEMPLATE.json
    JSON_ROOT_TEMPLATE = $(IN_TBS_JSON_TEMPLATE_DIR)\TBS_ROOT_TEMPLATE.json
    Keywords_EN = tags{}.display_name
    Keywords_FR = tags{}.display_name_fr
    P-T_ABBR = $(P-T_ABBR)
    Subject_LIST = subject_tbs
    Topic_LIST = topics_tbs
    OUTPUT_LOCAL -> AttributeExposer_18
Note: NS_JSON_CONFIG
LOOKUP_TABLES_READER_NG_19
    CSV_ENCODING = utf-8
    CSV_PATH = $(IN_CSV_LOOKUPTABLES_DIR)
    FEATURE_TYPE = SK_JSON_CONFIG
    PT = $(P-T_ABBR)
    -> JSON_PUBLISHER [CONFIG_FILE]
JSON_PUBLISHER
    JSON_RESOURCE_TEMPLATE = $(IN_TBS_JSON_TEMPLATE_DIR)\TBS_RESOURCES_TEMPLATE.json
    JSON_ROOT_TEMPLATE = $(IN_TBS_JSON_TEMPLATE_DIR)\TBS_ROOT_TEMPLATE.json
    Keywords_EN = tags{}.display_name
    Keywords_FR = tags{}.display_name_fr
    Subject_LIST = subject_tbs
    Topic_LIST = topic_tbs
    OUTPUT_LOCAL -> AttributeExposer_18
AttributeExposer_18
    ATTR_LIST = json_file,id,sector
    -> AttributeCreator_8
AttributeCreator_8
    ATTR_TABLE = SET_TO text_line_data = @Value(json_file)
    -> text_line (writer TEXTLINE_4)
text_line (writer TEXTLINE_4)
    attributes: text_line_data buffer

FME custom transformer GEO_NONE_GEO_SELECTOR
Description 
This custom transformer fans out the metadata records between two types of metadata (GeoSpatial and None GeoSpatial). When a metadata record cannot be validates as GeoSpatial it is declared None Geospatial. In order to determine the type of metadata record, the transformer analyse attributes according to the YAML directives. See the section Content of the YAML directives below for a complete description of the YAML directives.
This custom transformer also adds the attribute _typedatasets which contains the value geo for the geospatial features and nonegeo for the none geospatial features.
Input Ports 
DATA_INPUT: The input metadata records to process.
Output Ports 
GEOSPATIAL: Output port for all gepspatial metadata records;
NON-GEOSPATIAL: Output port for all none geospatial metadata records;
ERROR_LOG: Output port for metadata records that need to be logged according to the YAML directives.
Note: All the input records will go through either the GeoSpatial the None GeoSpatial port. Some input records may be duplicated and sent through the LOG_ERROR port if requested by the YAML directives.
Parameters 
CSV_FILE_NAME: Name lookup table file name in CSV format. 
CSV_PATH: File path of the CSV file. 
CSV_PROVINCE: Code of the province (two letters) . 
YAML_DIRECTIVES: YAML directives for determining the Geospatial and None Geospatial records. See the section Content of the YAML directives below for a description of the YAML directives.
Content of the YAML directives 
The YAML directives are used by the custom transformer to decide the type of the metadata records: GeoSpatial or None GeoSpatial. Here's an exemple of a YAML directives:
resources{}.format:  
domain: lookup_table_format  
spatial_type: overwrite  
not_found: log  
search_type: equals  
#  
description:  
domain: [spatial, geographic]  
spatial_type: no_overwrite  
not_found: no_log  
search_type: contains 
Description of the YAML directives
The first part of the YAML is the name of the FME attribute to use to validate the record, it can be a list attribute (ex.: resources{}..format) or a simple attribute (ex.: description). If it's a list attribute,the name must contain the 2 characters:"{}". The content of that attribute will be used to determine if the record is GeoSpatial or None GeoSpatial.
Following the FME attribute to validate, there are 4 keywords: domain, spatial_type, not_found and search_type.
The first keyword domain defines the domain of values that are used to determine if a metadata record is GeoSpatial or None GeoSpatial. Two values are possible: lookup_table_format or a list of word defining the domain between brackets (ex.: [point, line, poygone]). When using the keyword lookup_table_format, the custom transformer will use the content of the column name format of the CSV fileto define the domain of values. The record type will be GeoSpatial if the column fgp_publish is set to "oui". When using a domain list, the metadata record will be GeoSpatial if the value of the FME attribute is contained in the domain list.
The second keyword spatial_type defines how to set the spatial type when there is a domain match of the FME attribute. Three values are possible: no_overwite, overwrite and if_null_overwrite. no_overwite means that even if there is a match do not try to overwrite the spatial type. overwite means that if there is a match, take the spatial type value associated in the CSV file (column name: spatial_type) and assign it (or create it if empty) to the corresponding FME attribute. if_null_overwite as the same meaning as overwrite but only when the content of the spatial type is empty or missing. The values overwrite and if_null_overwrite can only be used when the domain keyword value is lookup_table_format.
The third keyword not_found defines how the custom transformer behaves when an FME attribute is not found in the domain of values. Two values are possible: log and no_log. log means create a duplicate (clone) of the record and send it through the LOG_ERROR output port. no_log means do not log any error when the FME attribute is not found in the domain of values.
The fourth keyword search type defines how to search the content of the FME attribute. Two values are possible: equals or contains. equals means that the value of the FME attribute must be exactly the same. contains means that one of the word the FME attribute must be in the domain values (usefull when we search for one word in a sentence).
You can define more than one FME attribute to search. Do not duplicate the FME attribute name because the last one will overwrite the others.

Parameters:
- CSV_FILE_NAME = GeoSpatialValidation
- CSV_PATH = .
- CSV_PROVINCE =
- YAML_DIRECTIVES =   # " " YAML_DIRECTIVES

INPUT (input)
    -> AttributeCreator_2
Note: _order = 3
AttributeCreator_2
    ATTR_TABLE = SET_TO _order = 3
    -> Sorter_2
Note: YMAL reader
Creator
    GEOMTYPE = Geometry Object
    NUM = 1
    CREATED -> AttributeCreator_3
Note: _order = 2 / YAML content
AttributeCreator_3
    ATTR_TABLE:
      SET_TO _order = 2
      SET_TO _yaml_str = $(YAML_DIRECTIVES)
    -> Sorter_2
Note: Sort CSV feature first
Sorter_2
    SORT_PARM = _order NUMERIC ASCENDING
    SORTED -> PythonCaller
Note: Call GeoNoneGeoSelector python code
PythonCaller
    PYTHONSOURCE = from Python.GEO_NONE_GEO_SELECTOR import GeoNoneGeoSelector
    PYTHONSYMBOL = GeoNoneGeoSelector
    -> AttributeExposer
AttributeExposer
    ATTR_LIST = _geo_none_geo_status
    -> PythonCaller_2
Note: Lower case attribute: resources{}.format
PythonCaller_2
    PYTHONSOURCE = from Python.GEO_NONE_GEO_SELECTOR import lower_resources_format
    PYTHONSYMBOL = lower_resources_format
    -> PythonCaller_3
Note: Copy attribute id, notes and title in the attribute list resources{}
PythonCaller_3
    PYTHONSOURCE = from Python.GEO_NONE_GEO_SELECTOR import copy_attributes_in_resources
    PYTHONSYMBOL = copy_attributes_in_resources
    -> AttributeRemover
Note: Remove attribute created by the custom transformer
AttributeRemover
    REMOVE_ATTRS = _order,_creation_instance,_yaml_str
    -> TestFilter
Note: Sort Geo and None geo features
TestFilter
    DEFAULT_VALUE = <UNFILTERED>
    TEST_LIST = "BOOL_OP,OR,COMPOSITE_TEST,""""""1"""""",TEST_CLAUSE,TEST @Value(_geo_none_geo_status) = geo",GEO,"BOOL_OP,OR,COMPOSITE_TEST,""""""1"""""",TEST_CLAUSE,TEST @Value(_geo_none_geo_status) = none_geo",NONE_GEO,"BOOL_OP,OR,COMPOSITE_TEST,""""""1"""""",TEST_CLAUSE,TEST @Value(_geo_none_geo_status) = log_error",LOG_ERROR
    GEO -> AttributeRemover_2
    NONE_GEO -> AttributeRemover_3
    LOG_ERROR -> AttributeExposer_2
    <UNFILTERED> -> Terminator
Note: Remove unnecessary attributes
AttributeRemover_2
    REMOVE_ATTRS = _geo_none_geo_status
    -> AttributeCreator_11
Note: Add geo attribute
AttributeCreator_11
    ATTR_TABLE = SET_TO _typedatasets = geo
    -> GEOSPATIAL (output)
GEOSPATIAL (output)
Note: Remove unnecessary attributes
AttributeRemover_3
    REMOVE_ATTRS = _geo_none_geo_status
    -> AttributeCreator_12
Note: Add nonegeo attribute
AttributeCreator_12
    ATTR_TABLE = SET_TO _typedatasets = nongeo
    -> NONE_GEOSPATIAL (output)
NONE_GEOSPATIAL (output)
AttributeExposer_2
    ATTR_LIST = id,_not_found_err_msg,format
    -> Logger
    -> LOG_ERROR (output)
LOG_ERROR (output)
Logger
    LOG_FEATURE = LOG_ONLY
    MAXCOORDS = 20
    MAXFEATS = 20
    MESSAGE = ERROR in GEOSPATIAL_DATA_VALIDATOR transforme: @value(_not_found_err_msg)  See PROCESS_REPORT_MANUAL_TASKS.xls file in XLS directory for details.
    SEVERITY = WARN
Terminator
    MESSAGE = Unknown attribute _geo_none_geo_status @Value(_geo_none_geo_status)Translation Terminated

Bookmark: Reading CSV file
Note: Reading GeospatialValidation CSV file
LOOKUP_TABLES_READER_NG
    CSV_ENCODING = utf-8
    CSV_PATH = $(CSV_PATH)
    FEATURE_TYPE = $(CSV_FILE_NAME)
    PT = $(CSV_PROVINCE)
    -> AttributeCreator
Note: _order = 1
AttributeCreator
    ATTR_TABLE = SET_TO _order = 1
    -> Sorter_2

FME custom transformer GEO_NONE_GEO_SELECTOR_2
Description 
This custom transformer fans out the metadata records between two types of metadata (GeoSpatial and None GeoSpatial). When a metadata record cannot be validates as GeoSpatial it is declared None Geospatial. In order to determine the type of metadata record, the transformer analyse attributes according to the YAML directives. See the section Content of the YAML directives below for a complete description of the YAML directives.
This custom transformer also adds the attribute _typedatasets which contains the value geo for the geospatial features and nonegeo for the none geospatial features.
Input Ports 
DATA_INPUT: The input metadata records to process.
Output Ports 
GEOSPATIAL: Output port for all gepspatial metadata records;
NON-GEOSPATIAL: Output port for all none geospatial metadata records;
ERROR_LOG: Output port for metadata records that need to be logged according to the YAML directives.
Note: All the input records will go through either the GeoSpatial the None GeoSpatial port. Some input records may be duplicated and sent through the LOG_ERROR port if requested by the YAML directives.
Parameters 
CSV_FILE_NAME: Name lookup table file name in CSV format. 
CSV_PATH: File path of the CSV file. 
CSV_PROVINCE: Code of the province (two letters) . 
YAML_DIRECTIVES: YAML directives for determining the Geospatial and None Geospatial records. See the section Content of the YAML directives below for a description of the YAML directives.
Content of the YAML directives 
The YAML directives are used by the custom transformer to decide the type of the metadata records: GeoSpatial or None GeoSpatial. Here's an exemple of a YAML directives:
resources{}.format:  
domain: lookup_table_format  
spatial_type: overwrite  
not_found: log  
search_type: equals  
#  
description:  
domain: [spatial, geographic]  
spatial_type: no_overwrite  
not_found: no_log  
search_type: contains 
Description of the YAML directives
The first part of the YAML is the name of the FME attribute to use to validate the record, it can be a list attribute (ex.: resources{}..format) or a simple attribute (ex.: description). If it's a list attribute,the name must contain the 2 characters:"{}". The content of that attribute will be used to determine if the record is GeoSpatial or None GeoSpatial.
Following the FME attribute to validate, there are 4 keywords: domain, spatial_type, not_found and search_type.
The first keyword domain defines the domain of values that are used to determine if a metadata record is GeoSpatial or None GeoSpatial. Two values are possible: lookup_table_format or a list of word defining the domain between brackets (ex.: [point, line, poygone]). When using the keyword lookup_table_format, the custom transformer will use the content of the column name format of the CSV fileto define the domain of values. The record type will be GeoSpatial if the column fgp_publish is set to "oui". When using a domain list, the metadata record will be GeoSpatial if the value of the FME attribute is contained in the domain list.
The second keyword spatial_type defines how to set the spatial type when there is a domain match of the FME attribute. Three values are possible: no_overwite, overwrite and if_null_overwrite. no_overwite means that even if there is a match do not try to overwrite the spatial type. overwite means that if there is a match, take the spatial type value associated in the CSV file (column name: spatial_type) and assign it (or create it if empty) to the corresponding FME attribute. if_null_overwite as the same meaning as overwrite but only when the content of the spatial type is empty or missing. The values overwrite and if_null_overwrite can only be used when the domain keyword value is lookup_table_format.
The third keyword not_found defines how the custom transformer behaves when an FME attribute is not found in the domain of values. Two values are possible: log and no_log. log means create a duplicate (clone) of the record and send it through the LOG_ERROR output port. no_log means do not log any error when the FME attribute is not found in the domain of values.
The fourth keyword search type defines how to search the content of the FME attribute. Two values are possible: equals or contains. equals means that the value of the FME attribute must be exactly the same. contains means that one of the word the FME attribute must be in the domain values (usefull when we search for one word in a sentence).
You can define more than one FME attribute to search. Do not duplicate the FME attribute name because the last one will overwrite the others.

Parameters:
- CSV_FILE_NAME = GeoSpatialValidation
- CSV_PATH = .
- CSV_PROVINCE =
- YAML_DIRECTIVES =   # " " YAML_DIRECTIVES

INPUT (input)
    -> AttributeCreator_2
Note: _order = 3
AttributeCreator_2
    ATTR_TABLE = SET_TO _order = 3
    -> Sorter_2
Note: YMAL reader
Creator
    GEOMTYPE = Geometry Object
    NUM = 1
    CREATED -> AttributeCreator_3
Note: _order = 2 / YAML content
AttributeCreator_3
    ATTR_TABLE:
      SET_TO _order = 2
      SET_TO _yaml_str = $(YAML_DIRECTIVES)
    -> Sorter_2
Note: Sort CSV feature first
Sorter_2
    SORT_PARM = _order NUMERIC ASCENDING
    SORTED -> PythonCaller
Note: Call GeoNoneGeoSelector python code
PythonCaller
    PYTHONSOURCE = from Python.GEO_NONE_GEO_SELECTOR import GeoNoneGeoSelector
    PYTHONSYMBOL = GeoNoneGeoSelector
    -> AttributeExposer
AttributeExposer
    ATTR_LIST = _geo_none_geo_status
    -> PythonCaller_2
Note: Lower case attribute: resources{}.format
PythonCaller_2
    PYTHONSOURCE = from Python.GEO_NONE_GEO_SELECTOR import lower_resources_format
    PYTHONSYMBOL = lower_resources_format
    -> PythonCaller_3
Note: Copy attribute id, notes and title in the attribute list resources{}
PythonCaller_3
    PYTHONSOURCE = from Python.GEO_NONE_GEO_SELECTOR import copy_attributes_in_resources
    PYTHONSYMBOL = copy_attributes_in_resources
    -> AttributeRemover
Note: Remove attribute created by the custom transformer
AttributeRemover
    REMOVE_ATTRS = _order,_creation_instance,_yaml_str
    -> TestFilter
Note: Sort Geo and None geo features
TestFilter
    DEFAULT_VALUE = <UNFILTERED>
    TEST_LIST = "BOOL_OP,OR,COMPOSITE_TEST,""""""1"""""",TEST_CLAUSE,TEST @Value(_geo_none_geo_status) = geo",GEO,"BOOL_OP,OR,COMPOSITE_TEST,""""""1"""""",TEST_CLAUSE,TEST @Value(_geo_none_geo_status) = none_geo",NONE_GEO,"BOOL_OP,OR,COMPOSITE_TEST,""""""1"""""",TEST_CLAUSE,TEST @Value(_geo_none_geo_status) = log_error",LOG_ERROR
    GEO -> AttributeRemover_2
    NONE_GEO -> AttributeRemover_3
    LOG_ERROR -> AttributeExposer_2
    <UNFILTERED> -> Terminator
Note: Remove unnecessary attributes
AttributeRemover_2
    REMOVE_ATTRS = _geo_none_geo_status
    -> AttributeCreator_11
Note: Add geo attribute
AttributeCreator_11
    ATTR_TABLE = SET_TO _typedatasets = geo
    -> GEOSPATIAL (output)
GEOSPATIAL (output)
Note: Remove unnecessary attributes
AttributeRemover_3
    REMOVE_ATTRS = _geo_none_geo_status
    -> AttributeCreator_12
Note: Add nonegeo attribute
AttributeCreator_12
    ATTR_TABLE = SET_TO _typedatasets = nongeo
    -> NONE_GEOSPATIAL (output)
NONE_GEOSPATIAL (output)
AttributeExposer_2
    ATTR_LIST = id,_not_found_err_msg,format
    -> Logger
    -> LOG_ERROR (output)
LOG_ERROR (output)
Logger
    LOG_FEATURE = LOG_ONLY
    MAXCOORDS = 20
    MAXFEATS = 20
    MESSAGE = ERROR in GEOSPATIAL_DATA_VALIDATOR transforme: @value(_not_found_err_msg)  See PROCESS_REPORT_MANUAL_TASKS.xls file in XLS directory for details.
    SEVERITY = WARN
Terminator
    MESSAGE = Unknown attribute _geo_none_geo_status @Value(_geo_none_geo_status)Translation Terminated

Bookmark: Reading CSV file
Note: Reading GeospatialValidation CSV file
LOOKUP_TABLES_READER_NG
    CSV_ENCODING = utf-8
    CSV_PATH = $(CSV_PATH)
    FEATURE_TYPE = $(CSV_FILE_NAME)
    PT = $(CSV_PROVINCE)
    -> AttributeCreator
Note: _order = 1
AttributeCreator
    ATTR_TABLE = SET_TO _order = 1
    -> Sorter_2
