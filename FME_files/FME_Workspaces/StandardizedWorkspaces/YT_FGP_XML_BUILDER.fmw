FME workspace YT_FGP_XML_BUILDER.fmw

Parameters:
- ACTIVATE_GEO = Yes
- ACTIVATE_NON_GEO = No
- ACTIVATE_TRANSLATION = Yes
- CATALOGUE_READER_SELECT = Yes
- FORCED_PYCSW_URL =
- IN_CSV_LOOKUP_TABLES_DIR = $(FME_SHAREDRESOURCE_DATA)\PT_Harvester\Lookup_tables
- IN_FFS_TESTING_FILE =
- IN_GMD_XML_TEMPLATE_DIR = $(FME_SHAREDRESOURCE_DATA)\PT_Harvester\XML_TEMPLATES
- IN_TBS_JSON_TEMPLATE_DIR = $(FME_SHAREDRESOURCE_DATA)\PT_Harvester\JSON_TEMPLATES
- LOCAL_SOURCE_METADATA_DELTA_FINDER = No
- LOCAL_WRITER = No
- LOG_FILE = $(FME_SHAREDRESOURCE_DATA)\PT_Harvester\YT\LOG\YT_FGP_XML_BUILDER.log
- OUT_JSON_LOCAL_DIR = $(FME_SHAREDRESOURCE_DATA)\PT_Harvester\YT\JSON_LOCAL
- OUT_XLS_NOTIFICATION_DIR = $(FME_SHAREDRESOURCE_DATA)\PT_Harvester\YT\XLS
- OUT_XML_FAILED_DIR = $(FME_SHAREDRESOURCE_DATA)\PT_Harvester\YT\XML_FAILED
- OUT_XML_LOCAL_DIR = $(FME_SHAREDRESOURCE_DATA)\PT_Harvester\YT\XML_LOCAL
- OUT_XML_PASSED_DIR = $(FME_SHAREDRESOURCE_DATA)\PT_Harvester\YT\XML_PASSED
- P-T_ABBR = YT
- PYCSW_OVERWRITE = NO
- SAMPLE_SELECT = No
- SAMPLE_SIZE = 10
- FME_SHAREDRESOURCE_DATA = C:\Data   # FME Server Resource Data

Writers:
- XLSXW_1: XLSXW to $(OUT_XLS_NOTIFICATION_DIR)
- TEXTLINE_1: TEXTLINE to $(OUT_XML_PASSED_DIR)
- TEXTLINE_2: TEXTLINE to $(OUT_XML_FAILED_DIR)
- TEXTLINE_3: TEXTLINE to $(OUT_XML_LOCAL_DIR)

Note: Disabled placeholder for future TBS processing

Bookmark: ETL PROCESS INITIATION
Creator
    GEOMTYPE = Geometry Object
    NUM = 1
    CREATED -> DateTimeStamper

Bookmark: SETTING DATE/TIME FOR PROCESS REPORT
DateTimeStamper
    DATETIME_ATTR = _toto
    STAMP_TYPE = date
    TIMEZONE = local
    -> VariableSetter
VariableSetter
    SCOPE = Global
    VALUE = @Value(_toto)
    VARNAME = _timestamp
    -> Tester_3

Bookmark: READING YT API/TEST FILE
Tester_3
    BOOL_OP = OR
    COMPOSITE_TEST = 1
    TEST_CLAUSE = TEST $(CATALOGUE_READER_SELECT) = Yes
    TEST_MODE = TEST
    PASSED -> YT_CATALOGUE_READER
    FAILED -> FeatureReader [INITIATOR]
Note: Fetches data from the Yukon DKAN API
YT_CATALOGUE_READER
    UNIQUE_ATT = orig_name
    DATA_OUTPUT -> ATTRIBUTE_VALUE_TEXT_CLEANER
    ERROR_OUTPUT -> VariableRetriever_4
VariableRetriever_4
    SCOPE = Global
    VALUE_ATTR = _timestamp
    VARNAME = _timestamp
    -> MISSING_RESULT_LIST_ATTRIBUTES (writer XLSXW_1)
MISSING_RESULT_LIST_ATTRIBUTES (writer XLSXW_1)
    attributes: name auto(20), _response_body auto(20), _timestamp auto(20)
FeatureReader
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> ATTRIBUTE_VALUE_TEXT_CLEANER

Bookmark: CONVERSION OF EXTRACTED DATA TO IN-HOUSE MODEL
Note: Removes whitespace from attributes
ATTRIBUTE_VALUE_TEXT_CLEANER
    -> AttributeExposer_3
AttributeExposer_3
    ATTR_LIST = license_title
    -> LICENSE_FILTER
LOOKUP_TABLES_READER_16
    CSV_ENCODING = utf-8
    CSV_PATH = $(IN_CSV_LOOKUP_TABLES_DIR)
    FEATURE_TYPE = License_YT
    PT = YT
    -> LICENSE_FILTER [LOOKUP_TABLE_INPUT]
LICENSE_FILTER
    LICENSE_ATT = @Value(license_title)
    LICENSE_FILTER_PASSED -> DEFAULT_ATTRIBUTE_MAPPER
    UNKNOWN_LICENSE -> VariableRetriever_14
VariableRetriever_14
    SCOPE = Global
    VALUE_ATTR = _timestamp
    VARNAME = _timestamp
    -> unknown_license (writer XLSXW_1)
unknown_license (writer XLSXW_1)
    attributes: license_id auto(20), id auto(20), _timestamp auto(20)
Note: Reading Default_YT
LOOKUP_TABLES_READER_5
    CSV_ENCODING = utf-8
    CSV_PATH = $(IN_CSV_LOOKUP_TABLES_DIR)
    FEATURE_TYPE = Default_YT
    PT = YT
    -> DEFAULT_ATTRIBUTE_MAPPER [LOOKUP_TABLE_INPUT]
DEFAULT_ATTRIBUTE_MAPPER
    -> YT_DATA_READER
YT_DATA_READER
    -> YT_GEOLOGY_DATA_EXTRACTOR
    DroppedDatasets -> VariableRetriever_3
Note: Extracting url from geology portal
YT_GEOLOGY_DATA_EXTRACTOR
    Unworking_geology_url -> VariableRetriever_2
    -> YT_GEOWEB_EXTRACTOR
Note: Extraction of attributes found in XML files from the YT Geoweb
YT_GEOWEB_EXTRACTOR
    XML_LINK_ERROR -> VariableRetriever_5
    EXTRACTED_LINK_ERROR -> VariableRetriever_6
    -> GEOPORTAL_WEBLINK_ADDER
VariableRetriever_5
    SCOPE = Global
    VALUE_ATTR = _timestamp
    VARNAME = _timestamp
    -> XML_LINK_ERROR (writer XLSXW_1)
XML_LINK_ERROR (writer XLSXW_1)
    attributes: url_ori auto(20), name_ori auto(20), _timestamp auto(20)
VariableRetriever_6
    SCOPE = Global
    VALUE_ATTR = _timestamp
    VARNAME = _timestamp
    -> EXTRACTED_LINK_ERROR (writer XLSXW_1)
EXTRACTED_LINK_ERROR (writer XLSXW_1)
    attributes: url auto(20), url_ori auto(20), name_ori auto(20), _timestamp auto(20)
VariableRetriever_2
    SCOPE = Global
    VALUE_ATTR = _timestamp
    VARNAME = _timestamp
    -> BROKEN_GEOLOGY_LINKS (writer XLSXW_1)
BROKEN_GEOLOGY_LINKS (writer XLSXW_1)
    attributes: url auto(20), copy_url auto(20), sector auto(20), contact auto(20), contact_email auto(20), id auto(20), UNIQUE_ATT auto(20), name auto(20), result auto(20), license_title auto(20), contacts__.email auto(20), contacts__.name auto(20), contacts__.role auto(20), iso_topic__ auto(20), iso_topic__.topic_value auto(20), projectionList__.codespace auto(20), projectionList__.projection_name auto(20), projectionList__.version auto(20), tags__.display_name auto(20), metadata_created auto(20), metadata_modified auto(20), notes auto(20), title auto(20), orig_name auto(20), data_collection_start_date auto(20), date_created auto(20), date_last_modified auto(20), resource_update_cycle auto(20), data_collection_end_date auto(20), format auto(20),
      _list_index auto(20), _uuid auto(20), _element_index auto(20), _error auto(20), fme_rejection_code auto(20), _response_body auto(20), _http_status_code auto(20), _timestamp auto(20)
VariableRetriever_3
    SCOPE = Global
    VALUE_ATTR = _timestamp
    VARNAME = _timestamp
    -> DROPPED_DATASETS (writer XLSXW_1)
DROPPED_DATASETS (writer XLSXW_1)
    attributes: sector auto(20), contact auto(20), contact_email auto(20), id auto(20), UNIQUE_ATT auto(20), name auto(20), result auto(20), license_title auto(20), contacts__.email auto(20), contacts__.name auto(20), contacts__.role auto(20), iso_topic__ auto(20), iso_topic__.topic_value auto(20), projectionList__.codespace auto(20), projectionList__.projection_name auto(20), projectionList__.version auto(20), resources__.data_collection_end_date auto(20), resources__.data_collection_start_date auto(20), resources__.format auto(20), resources__.name auto(20), resources__.resource_update_cycle auto(20), resources__.url auto(20), tags__.display_name auto(20), groups__.title auto(20), metadata_created auto(20), metadata_modified auto(20), notes auto(20), title auto(20), url auto(20), orig_name auto(20),
      nb_res auto(20), data_collection_start_date auto(20), date_created auto(20), date_last_modified auto(20), resource_update_cycle auto(20), _timestamp auto(20)

Bookmark: ADD GEOPORTAL WEBLINK
LOOKUP_TABLES_READER_6
    CSV_ENCODING = utf-8
    CSV_PATH = $(IN_CSV_LOOKUP_TABLES_DIR)
    FEATURE_TYPE = GeoportalWeblink_YT
    PT = YT
    -> GEOPORTAL_WEBLINK_ADDER [LOOKUP_TABLE_INPUT]
Note: Concatenates a base url with "orig_name" attribute to create an additional transfer option
GEOPORTAL_WEBLINK_ADDER
    WEBLINK_WILDCARD = @Value(orig_name)
    -> YT_DATE_FORMATTER

Bookmark: P/T SPECIFIC TRANSFORMATIONS
Note: Sets date values to iso yyyy-mm-dd format
YT_DATE_FORMATTER
    -> YT_MISSING_ATTRIBUTE_MANAGER
YT_MISSING_ATTRIBUTE_MANAGER
    -> YT_CONTACTS_MERGER
YT_CONTACTS_MERGER
    -> EMPTY_FORMAT_MAPPER [DATA_INPUT]

Bookmark: PRE METADATA MAPPING TRANSFORMATIONS
EMPTY_FORMAT_MAPPER
    DATA_OUTPUT -> URL_HTTPS_MAKER [UUIDGenerator_Input]
Note: Making HTTPS url to avoid issues
URL_HTTPS_MAKER
    -> FORMAT_VALIDATOR
Note: Verfication if URL is valid WMS call for WMS formats
FORMAT_VALIDATOR
    -> EMAIL_FORMAT_TESTER
EMAIL_FORMAT_TESTER
    DEFAULT_CONTACT_EMAIL = @Value(default_contact_email)
    -> FeatureMerger [REQUESTOR]

Bookmark: SPATIAL DATA TYPE MANAGMENT & GEO/NON-GEO FILTERING
Note: Reading geokeyword_url
LOOKUP_TABLES_READER_15
    CSV_ENCODING = utf-8
    CSV_PATH = $(IN_CSV_LOOKUP_TABLES_DIR)
    FEATURE_TYPE = geokeyword_url
    PT = YT
    -> AttributeExposer_2
AttributeExposer_2
    ATTR_LIST = keyword
    -> ListBuilder
ListBuilder
    LIST_ATTRS_TO_INCLUDE = keyword
    LIST_NAME = _list
    -> ListConcatenator
ListConcatenator
    DROP_EMPTY_PARTS = No
    LIST_ATTR = _list{}.keyword
    SEP = |
    VAL_ATTR = _url_keyword
    -> FeatureMerger [SUPPLIER]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> GEOSPATIAL_DATA_VALIDATOR
    UNMERGED_REQUESTOR -> Terminator_2
    UNUSED_SUPPLIER -> Terminator_2
    <REJECTED> -> Terminator_2
Terminator_2
    MESSAGE = Translation Terminated
Note: Reading GeospatialValidation
LOOKUP_TABLES_READER
    CSV_ENCODING = utf-8
    CSV_PATH = $(IN_CSV_LOOKUP_TABLES_DIR)
    FEATURE_TYPE = GeospatialValidation
    PT = YT
    -> GEOSPATIAL_DATA_VALIDATOR [LOOKUP_TABLE_INPUT]
Note: Second geospatial data validator using different filtering criteria
GEOSPATIAL_DATA_VALIDATOR
    KEYWORD_SEARCH = @Value(_url_keyword)
    LIST_SEARCH_ATTRIBUTE = resources{}.url
    GEOSPATIAL -> SPATIAL_TYPE_MAPPER [DATA_INPUT]
    NON-GEOSPATIAL -> MANUAL_GEOSPATIAL_SETTER [DATA_INPUT]
    UNKNOWN_FORMAT -> VariableRetriever_11
VariableRetriever_11
    SCOPE = Global
    VALUE_ATTR = _timestamp
    VARNAME = _timestamp
    -> GEOSPATIAL_FORMAT_NOT_MAPPED (writer XLSXW_1)
GEOSPATIAL_FORMAT_NOT_MAPPED (writer XLSXW_1)
    attributes: id auto(20), format auto(20), _timestamp auto(20)
Note: Reading UUID_Spatial_YT
LOOKUP_TABLES_READER_3
    CSV_ENCODING = utf-8
    CSV_PATH = $(IN_CSV_LOOKUP_TABLES_DIR)
    FEATURE_TYPE = UUID_Spatial_YT
    PT = YT
    -> SPATIAL_TYPE_MAPPER [LOOKUP_TABLE_INPUT]
SPATIAL_TYPE_MAPPER
    DATA_OUTPUT_FAILED -> VariableRetriever_12
    DATA_OUTPUT_PASSED -> Tester_6
VariableRetriever_12
    SCOPE = Global
    VALUE_ATTR = _timestamp
    VARNAME = _timestamp
    -> SPATIAL_TYPE_NOT_MAPPED (writer XLSXW_1)
SPATIAL_TYPE_NOT_MAPPED (writer XLSXW_1)
    attributes: id auto(20), notes auto(20), title auto(20), url auto(20), _timestamp auto(20)
Note: Reading UnmappedGeoData_YT
LOOKUP_TABLES_READER_2
    CSV_ENCODING = utf-8
    CSV_PATH = $(IN_CSV_LOOKUP_TABLES_DIR)
    FEATURE_TYPE = UnmappedGeodata_YT
    PT = YT
    -> MANUAL_GEOSPATIAL_SETTER [LOOKUP_TABLE_INPUT]
Note: Additional filtering step required for YT data. Items identified as NON-GEOSPATIAL in GEOSPATIAL_DATA_VALIDATOR were analyzed manually and a lookup table was created to identify non-filtered geo data and create the spatial_representation_type
MANUAL_GEOSPATIAL_SETTER
    GEOSPATIAL -> Tester_6
    NON-GEOSPATIAL -> Tester_2
    UNMAPPED_DATA -> VariableRetriever_13
Note: Select Geo
Tester_6
    BOOL_OP = OR
    COMPOSITE_TEST = 1
    TEST_CLAUSE = TEST $(ACTIVATE_GEO) = Yes
    TEST_MODE = TEST
    PASSED -> Tester_4
Note: Select Non-Geo
Tester_2
    BOOL_OP = OR
    COMPOSITE_TEST = 1
    TEST_CLAUSE = TEST $(ACTIVATE_NON_GEO) = Yes
    TEST_MODE = TEST
    PASSED -> Tester_7
VariableRetriever_13
    SCOPE = Global
    VALUE_ATTR = _timestamp
    VARNAME = _timestamp
    -> UNMAPPED_GEODATA_YT (writer XLSXW_1)
UNMAPPED_GEODATA_YT (writer XLSXW_1)
    attributes: id auto(20), notes auto(20), title auto(20), url auto(20), _timestamp auto(20)

Bookmark: GEO SAMPLER
Tester_4
    BOOL_OP = OR
    COMPOSITE_TEST = 1
    TEST_CLAUSE = TEST $(SAMPLE_SELECT) = Yes
    TEST_MODE = TEST
    PASSED -> Sampler_2
    FAILED -> METADATA_VALUE_MAPPER [DATA_INPUT]
Sampler_2
    RATE = $(SAMPLE_SIZE)
    SAMPLE_MODE = No
    SAMPLE_TYPE_LONG = First N Features
    SAMPLED -> METADATA_VALUE_MAPPER [DATA_INPUT]

Bookmark: GEO SAMPLER
Tester_7
    BOOL_OP = OR
    COMPOSITE_TEST = 1
    TEST_CLAUSE = TEST $(SAMPLE_SELECT) = Yes
    TEST_MODE = TEST
    PASSED -> Sampler_3
    FAILED -> Junction_2
Sampler_3
    RATE = $(SAMPLE_SIZE)
    SAMPLE_MODE = No
    SAMPLE_TYPE_LONG = First N Features
    SAMPLED -> Junction_2

Bookmark: NON-GEODATA OUTPUT
Junction_2 [off]

Bookmark: METADATA VALUE MAPPING
Note: Reading Role
Note: This section utilizes mulitple instances of the METADATA_VALUE_MAPPER to correct values to valid English values and to add the valid French equivalents and RI_CODES where applicable. It can be utilized for mulitple metadata items by accessing custom look up tables applicable to specific items. / Turn the error mapping options and the data items to be mapped on or off by clicking on the transformer and selecting yes/no. / - ERROR_NOT_MAPPED: enables mapping of data item values that cannot be found in the lookup tables. / - ENGLISH_REFRESH: enables updating of English attribute values. / - FRENCH_REFRESH: enables updating of French attribute values. / - CODE_REFRESH: enables updating of RI_CODE values. / Enter the attribute key name by clicking on the transformer and selecting the drop down menu next to the 'att_to_map' text box and selecting the 'Open text editor...' option. Explicitly enter the attribute key name in the text editor (ie: contacts{}.role). / IMPORTANT: Do not select the 'Attribute Value' option from the drop down menu to select the attribute key name.
LOOKUP_TABLES_READER_7
    CSV_ENCODING = utf-8
    CSV_PATH = $(IN_CSV_LOOKUP_TABLES_DIR)
    FEATURE_TYPE = role
    PT = YT
    -> METADATA_VALUE_MAPPER [LOOKUP_TABLE_INPUT]
Note: Maps contacts{}.role to HNAP standards
METADATA_VALUE_MAPPER
    ATT_TO_MAP = contacts{}.role
    CODE_REFRESH = YES
    ENGLISH_REFRESH = YES
    ERROR_NOT_MAPPED = YES
    FRENCH_REFRESH = YES
    -> METADATA_VALUE_MAPPER_2 [DATA_INPUT]
Note: Reading SpatialRepresentation
LOOKUP_TABLES_READER_8
    CSV_ENCODING = utf-8
    CSV_PATH = $(IN_CSV_LOOKUP_TABLES_DIR)
    FEATURE_TYPE = SpatialRepresentation
    PT = YT
    -> METADATA_VALUE_MAPPER_2 [LOOKUP_TABLE_INPUT]
Note: Maps spatial_representation_type to HNAP standards
METADATA_VALUE_MAPPER_2
    ATT_TO_MAP = spatial_representation_type
    CODE_REFRESH = YES
    ENGLISH_REFRESH = YES
    ERROR_NOT_MAPPED = YES
    FRENCH_REFRESH = YES
    -> METADATA_VALUE_MAPPER_3 [DATA_INPUT]
Note: Reading Progress
LOOKUP_TABLES_READER_9
    CSV_ENCODING = utf-8
    CSV_PATH = $(IN_CSV_LOOKUP_TABLES_DIR)
    FEATURE_TYPE = Progress
    PT = YT
    -> METADATA_VALUE_MAPPER_3 [LOOKUP_TABLE_INPUT]
Note: Maps progress_code to HNAP standards
METADATA_VALUE_MAPPER_3
    ATT_TO_MAP = progress_code
    CODE_REFRESH = YES
    ENGLISH_REFRESH = YES
    ERROR_NOT_MAPPED = YES
    FRENCH_REFRESH = YES
    -> METADATA_VALUE_MAPPER_4 [DATA_INPUT]
Note: Reading SpatialRef
LOOKUP_TABLES_READER_10
    CSV_ENCODING = utf-8
    CSV_PATH = $(IN_CSV_LOOKUP_TABLES_DIR)
    FEATURE_TYPE = SpatialRef
    PT = YT
    -> METADATA_VALUE_MAPPER_4 [LOOKUP_TABLE_INPUT]
Note: Maps spatailref_projection_name to HNAP standards
METADATA_VALUE_MAPPER_4
    ATT_TO_MAP = spatialref_projection_name
    CODE_REFRESH = NO
    ENGLISH_REFRESH = YES
    ERROR_NOT_MAPPED = YES
    FRENCH_REFRESH = NO
    -> METADATA_VALUE_MAPPER_5 [DATA_INPUT]
Note: Reading Update
LOOKUP_TABLES_READER_11
    CSV_ENCODING = utf-8
    CSV_PATH = $(IN_CSV_LOOKUP_TABLES_DIR)
    FEATURE_TYPE = Update
    PT = YT
    -> METADATA_VALUE_MAPPER_5 [LOOKUP_TABLE_INPUT]
Note: Maps resource_update_cycle to HNAP standards
METADATA_VALUE_MAPPER_5
    ATT_TO_MAP = resource_update_cycle
    CODE_REFRESH = YES
    ENGLISH_REFRESH = YES
    ERROR_NOT_MAPPED = YES
    FRENCH_REFRESH = YES
    -> METADATA_VALUE_MAPPER_6 [DATA_INPUT]
Note: Reading Email
LOOKUP_TABLES_READER_13
    CSV_ENCODING = utf-8
    CSV_PATH = $(IN_CSV_LOOKUP_TABLES_DIR)
    FEATURE_TYPE = Email
    PT = YT
    -> METADATA_VALUE_MAPPER_6 [LOOKUP_TABLE_INPUT]
Note: Maps contacts{}.email to HNAP standards
METADATA_VALUE_MAPPER_6
    ATT_TO_MAP = contacts{}.email
    CODE_REFRESH = NO
    ENGLISH_REFRESH = YES
    ERROR_NOT_MAPPED = NO
    FRENCH_REFRESH = NO
    -> METADATA_FORMAT_MAPPER [DATA_INPUT]

Bookmark: METADATA MAPPING
Note: Reading Format
LOOKUP_TABLES_READER_12
    CSV_ENCODING = utf-8
    CSV_PATH = $(IN_CSV_LOOKUP_TABLES_DIR)
    FEATURE_TYPE = Format
    PT = YT
    -> METADATA_FORMAT_MAPPER [LOOKUP_TABLE_INPUT]
Note: Maps resources{}.format to HNAP standards
METADATA_FORMAT_MAPPER
    ATT_TO_MAP = resources{}.format
    ERROR_NOT_MAPPED = YES
    REAL_VALUE_REFRESH = YES
    RES_TYPE_EN_REFRESH = YES
    RES_TYPE_FR_REFRESH = YES
    -> METADATA_VALUE_MAPPER_ERROR_MANAGER

Bookmark: MAPPING ERROR LIST CREATOR
Note: Writes mapping errors to XLS file
METADATA_VALUE_MAPPER_ERROR_MANAGER
    ERROR_OUTPUT -> VariableRetriever_7
    DATA_OUTPUT -> RESOURCE_NAME_UNDERSCORE_REMOVER
VariableRetriever_7
    SCOPE = Global
    VALUE_ATTR = _timestamp
    VARNAME = _timestamp
    -> METADATA_MAPPING_ERRORS (writer XLSXW_1)
METADATA_MAPPING_ERRORS (writer XLSXW_1)
    attributes: id string(200), error auto(20), _element_index auto(20), _timestamp auto(20)

Bookmark: RESOURCE NAME UNDERSCORE
Note: Removes all underscores from resources{}.name attributes. Long compounded names joined by underscores in this field can cause display formatting issues when published to the FGP.
RESOURCE_NAME_UNDERSCORE_REMOVER
    DATA_OUTPUT -> MORE_INFO_MANAGER

Bookmark: MORE INFO MANAGER
Note: Tests the more_info{}.link list for valid attribute values and filters them out where missing
MORE_INFO_MANAGER
    -> REMOVE_BROKEN_URL_WMS_ESRI_REST

Bookmark: DROPPING BROKEN WEB SERVICES
Note: Tests WMS/ESRI_REST resource URL's and removes them where broken
REMOVE_BROKEN_URL_WMS_ESRI_REST
    -> WMS_REST_LANGUAGE_FORMATTER
    FAULTY_URL_OUTPUT -> VariableRetriever_8
VariableRetriever_8
    SCOPE = Global
    VALUE_ATTR = _timestamp
    VARNAME = _timestamp
    -> MAP_SERVICE_URL_ERROR (writer XLSXW_1)
MAP_SERVICE_URL_ERROR (writer XLSXW_1)
    attributes: id string(200), url auto(20), format string(200), _url_failure_message auto(20), _timestamp auto(20)

Bookmark: HANP RULES - SETTING ONE SERVICE PER LANGUAGE
Note: Formats WMS and ESRI REST resources to add French versions and formats French and English versions with valid supporting attributes
WMS_REST_LANGUAGE_FORMATTER
    -> DUPLICATE_SERVICE_REMOVER
Note: Removes duplicate WMS or ESRI REST resources where they exist, that would otherwise invalidate the dataset
DUPLICATE_SERVICE_REMOVER
    -> AMPERSAND_CHARACTER_REFERENCE_REMOVER

Bookmark: AMPERSAND CLEANUP
Note: Removes amp; character reference from key attributes to avoid issues with reading characters from published data in METADATA_DELTA_FINDER
AMPERSAND_CHARACTER_REFERENCE_REMOVER: AMPERSAND CHARACTER REFERENCE REMOVER
    -> ListCopier

Bookmark: LIST & DUPLICATE MANAGEMENT
Note: Create distributionList{} from resources{}
ListCopier
    DEST_LIST = distributionList
    SRC_LIST = resources{}
    -> GMD_SECTION_DATA_EXTRACTION
Note: Creates lists and removes duplicates for GMD_Section
GMD_SECTION_DATA_EXTRACTION
    -> PYCSW_URL_MAPPER

Bookmark: PUBLISHING MANAGEMENT
Note: Reading PyCSW_config
LOOKUP_TABLES_READER_4
    CSV_ENCODING = utf-8
    CSV_PATH = $(IN_CSV_LOOKUP_TABLES_DIR)
    FEATURE_TYPE = PyCSW_config
    PT = YT
    -> PYCSW_URL_MAPPER [PYCSW_CONFIG]
PYCSW_URL_MAPPER
    FORCED_PYCSW_URL = $(FORCED_PYCSW_URL)
    PROVIDER = $(P-T_ABBR)
    -> AttributeExposer_4
AttributeExposer_4
    ATTR_LIST = search_criteria_pycsw
    -> METADATA_DELTA_FINDER
METADATA_DELTA_FINDER
    ABSTRACT_ATT_NEW = notes
    ABSTRACT_ATT_REF = MD_Metadata.identificationInfo.MD_DataIdentification.abstract.CharacterString
    CSW_FILTER = @Value(search_criteria_pycsw)
    CUSTOM_CSW_CKAN_URL = @Value(csw_url)
    DATESTAMP_ATT_NEW = date_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    -> AttributeExposer
Note: Exposes PyCSW_Transaction attribute
AttributeExposer
    ATTR_LIST = PyCSW_Transaction
    -> AttributeFilter
Note: Filters items by PyCSW transaction type
AttributeFilter
    ATTR_NAME = PyCSW_Transaction
    ATTR_VALUES = <Empty>,<Missing>,<Null>,<Unfiltered>,No change,Update,Insert,Delete
    <EMPTY> -> Terminator
    <MISSING> -> Terminator
    <NULL> -> Terminator
    <UNFILTERED> -> Terminator
    No change -> Tester_5
    Update -> AWS_TRANSLATE
    Insert -> AWS_TRANSLATE
    Delete -> AttributeKeeper
Terminator
    MESSAGE = ERROR: Unknown _event value from Metadata_Delta
Note: Selects items with no change for publishing, overwriting all existing data
Tester_5
    BOOL_OP = OR
    COMPOSITE_TEST = 1
    TEST_CLAUSE = TEST $(PYCSW_OVERWRITE) = YES
    TEST_MODE = TEST
    PASSED -> AttributeCreator
    FAILED -> StatisticsCalculator
Note: Reset to update
AttributeCreator
    ATTR_TABLE = SET_TO PyCSW_Transaction = Update
    -> AWS_TRANSLATE
Note: Retains ID for list of deleted items
AttributeKeeper
    KEEP_ATTRS = id
    -> VariableRetriever_9
VariableRetriever_9
    SCOPE = Global
    VALUE_ATTR = _timestamp
    VARNAME = _timestamp
    -> DELETED_RECORDS (writer XLSXW_1)
DELETED_RECORDS (writer XLSXW_1)
    attributes: id string(200), _timestamp auto(20)
Creator_2
    GEOMTYPE = Geometry Object
    NUM = 1
    CREATED -> StatisticsCalculator
StatisticsCalculator
    COMPUTE_HISTOGRAM = NO
    COUNT_ATTR = _count
    PREPEND_ATTR_NAME_CHOICE = For multiple results only
    STATS_ATTRS = id
    SUMMARY -> AttributeCreator_2
AttributeCreator_2
    ATTR_TABLE = SET_TO _real_count = @Evaluate(@Value(_count)-1)
    -> StatisticsCalculator_Summary
StatisticsCalculator_Summary: Logger
    LOG_FEATURE = NONE
    MAXFEATS = 20
    MESSAGE:
      ************************
      **** Unchanged Report ****
      ************************

      @Value(_real_count) features were unchanged

      ************************
      ************************
      ************************
    SEVERITY = INFO

Bookmark: LANGUAGE TRANSLATION
Note: Translates specific items from English to French
AWS_TRANSLATE
    ACTIVATE_TRANSLATION = $(ACTIVATE_TRANSLATION)
    ATTR_2_Translate = notes,title,sector
    ATTR_LIST_2_Translate = tags{}.display_name,resources{}.name
    MODE = English-->French
    -> XML_PUBLISHER
    TRANSLATION_PROBLEM -> VariableRetriever_10
VariableRetriever_10
    SCOPE = Global
    VALUE_ATTR = _timestamp
    VARNAME = _timestamp
    -> TRANSLATION_PROBLEMS (writer XLSXW_1)
TRANSLATION_PROBLEMS (writer XLSXW_1)
    attributes: _iteration auto(20), _aws_activation auto(20), _mode auto(20), _attr2translate auto(20), _attrlist2translate auto(20), _hash_prov auto(20), _type auto(20), RESOURCES_FORMAT_ATT auto(20), csw_url auto(20), data_collection_end_date auto(20), data_collection_start_date auto(20), sector auto(20), id string(200), UNIQUE_ATT auto(20), name auto(20), result auto(20), license_title auto(20), iso_topic__ auto(20), iso_topic__.topic_value auto(20), projectionList__.codespace auto(20), projectionList__.projection_name auto(20), projectionList__.version auto(20), metadata_created auto(20), metadata_modified auto(20), notes auto(20), title auto(20), orig_name auto(20), date_created auto(20), date_last_modified auto(20), resource_update_cycle auto(20),
      resources_to_add__.name auto(20), resources_to_add__.url auto(20), resources_to_add__.protocol auto(20), _nb_res_ori auto(20), _nb_res_new auto(20), _uuidResources auto(20), date_published auto(20), east_bound_longitude auto(20), north_bound_latitude auto(20), south_bound_latitude auto(20), west_bound_longitude auto(20), resources_to_add__.format auto(20), resources_to_add__.name auto(20), resources_to_add__.url auto(20), default_contact_email auto(20), progress_code auto(20), spatialref_projection_name auto(20), spatialref_projection_system auto(20), spatialref_projection_system_version auto(20), display_name auto(20), tags__.display_name auto(20), role auto(20), assignation auto(20), resources auto(20), contacts__.name auto(20), contacts__.role auto(20), contacts__.email auto(20), _list__.keyword auto(20), _url_keyword auto(20), orig_id auto(20),
      spatial_type auto(20), spatial_representation_type auto(20), mapping_errors__.error auto(20), _element_count auto(20), more_info__.protocol auto(20), more_info__.id auto(20), more_info__.link auto(20), more_info__._element_index auto(20), default_distribution_format_version auto(20), title_fr auto(20), _list_index_OGC_WMS auto(20), _list_index_esrirest auto(20), nb_OGCWMScount auto(20), nb_OGCWMSvalue auto(20), nb_esri_restcount auto(20), nb_esri_restvalue auto(20), _histogram__.count auto(20), _histogram__.value auto(20), protocol auto(20), xlink_role auto(20), url auto(20), format auto(20), name_fr auto(20), language_a auto(20), language_b auto(20), locale_a auto(20), locale_b auto(20), service_a auto(20), service_b auto(20), _element_index auto(20),
      resources__.protocol auto(20), projectionList__.protocol auto(20), distributionList__.protocol auto(20), resources__.xlink_role auto(20), projectionList__.xlink_role auto(20), distributionList__.xlink_role auto(20), resources__.orig_id auto(20), projectionList__.orig_id auto(20), distributionList__.orig_id auto(20), resources__.notes auto(20), projectionList__.notes auto(20), distributionList__.notes auto(20), resources__.title auto(20), projectionList__.title auto(20), distributionList__.title auto(20), resources__.url auto(20), projectionList__.url auto(20), distributionList__.url auto(20), resources__.data_collection_end_date auto(20), projectionList__.data_collection_end_date auto(20), distributionList__.data_collection_end_date auto(20), resources__.data_collection_start_date auto(20), projectionList__.data_collection_start_date auto(20), distributionList__.data_collection_start_date auto(20), resources__.format auto(20), projectionList__.format auto(20), distributionList__.format auto(20), resources__.name auto(20), projectionList__.name auto(20), distributionList__.name auto(20),
      resources__.resource_update_cycle auto(20), projectionList__.resource_update_cycle auto(20), distributionList__.resource_update_cycle auto(20), resources__.resources auto(20), projectionList__.resources auto(20), distributionList__.resources auto(20), resources__.spatial_type auto(20), projectionList__.spatial_type auto(20), distributionList__.spatial_type auto(20), resources__.name_fr auto(20), projectionList__.name_fr auto(20), distributionList__.name_fr auto(20), resources__.id auto(20), projectionList__.id auto(20), distributionList__.id auto(20), resources__.language_a auto(20), projectionList__.language_a auto(20), distributionList__.language_a auto(20), resources__.language_b auto(20), projectionList__.language_b auto(20), distributionList__.language_b auto(20), resources__.locale_a auto(20), projectionList__.locale_a auto(20), distributionList__.locale_a auto(20), resources__.locale_b auto(20), projectionList__.locale_b auto(20), distributionList__.locale_b auto(20), resources__.service_a auto(20), projectionList__.service_a auto(20), distributionList__.service_a auto(20),
      resources__.service_b auto(20), projectionList__.service_b auto(20), distributionList__.service_b auto(20), resources__.projection_name auto(20), distributionList__.projection_name auto(20), resources__.resource_update_cycle_code auto(20), projectionList__.resource_update_cycle_code auto(20), distributionList__.resource_update_cycle_code auto(20), resources__.resource_update_cycle_fr auto(20), projectionList__.resource_update_cycle_fr auto(20), distributionList__.resource_update_cycle_fr auto(20), updateList__.resource_update_cycle auto(20), updateList__.resource_update_cycle_code auto(20), updateList__.resource_update_cycle_fr auto(20), more_info_0_.link auto(20), search_criteria_pycsw auto(20), _global_hashkey auto(20), _hash_pycsw auto(20), csw_version auto(20), csw_schema auto(20), csw_typenames auto(20), csw_filter auto(20), result.file_id auto(20), csw_search_criteria auto(20), MD_Metadata.MD_Metadata auto(20), _OpenMapsFilter auto(20), result.results auto(20), _list_name auto(20), MD_Metadata.fileIdentifier.CharacterString auto(20), MD_Metadata.path_windows auto(20),
      MD_Metadata.path_extension auto(20), path_windows auto(20), path_extension auto(20), PyCSW_Transaction string(200), AWScopy__hash_prov auto(20), AWScopy__type auto(20), AWScopy_RESOURCES_FORMAT_ATT auto(20), AWScopy_csw_url auto(20), AWScopy_data_collection_end_date auto(20), AWScopy_data_collection_start_date auto(20), AWScopy_sector auto(20), AWScopy_id auto(20), AWScopy_UNIQUE_ATT auto(20), AWScopy_name auto(20), AWScopy_result auto(20), AWScopy_license_title auto(20), AWScopy_iso_topic__ auto(20), AWScopy_iso_topic__.topic_value auto(20), AWScopy_projectionList__.codespace auto(20), AWScopy_projectionList__.projection_name auto(20), AWScopy_projectionList__.version auto(20), AWScopy_metadata_created auto(20), AWScopy_metadata_modified auto(20), AWScopy_notes auto(20), AWScopy_title auto(20), AWScopy_orig_name auto(20), AWScopy_date_created auto(20), AWScopy_date_last_modified auto(20), AWScopy_resource_update_cycle auto(20), AWScopy_resources_to_add__.name auto(20),
      AWScopy_resources_to_add__.url auto(20), AWScopy_resources_to_add__.protocol auto(20), AWScopy__nb_res_ori auto(20), AWScopy__nb_res_new auto(20), AWScopy__uuidResources auto(20), AWScopy_date_published auto(20), AWScopy_east_bound_longitude auto(20), AWScopy_north_bound_latitude auto(20), AWScopy_south_bound_latitude auto(20), AWScopy_west_bound_longitude auto(20), AWScopy_ resources_to_add__.format auto(20), AWScopy_ resources_to_add__.name auto(20), AWScopy_ resources_to_add__.url auto(20), AWScopy_default_contact_email auto(20), AWScopy_progress_code auto(20), AWScopy_spatialref_projection_name auto(20), AWScopy_spatialref_projection_system auto(20), AWScopy_spatialref_projection_system_version auto(20), AWScopy_display_name auto(20), AWScopy_tags__.display_name auto(20), AWScopy_role auto(20), AWScopy_assignation auto(20), AWScopy_resources auto(20), AWScopy_contacts__.name auto(20), AWScopy_contacts__.role auto(20), AWScopy_contacts__.email auto(20), AWScopy__list__.keyword auto(20), AWScopy__url_keyword auto(20), AWScopy_orig_id auto(20), AWScopy_spatial_type auto(20),
      AWScopy_spatial_representation_type auto(20), AWScopy_mapping_errors__.error auto(20), AWScopy__element_count auto(20), AWScopy_more_info__.protocol auto(20), AWScopy_more_info__.id auto(20), AWScopy_more_info__.link auto(20), AWScopy_more_info__._element_index auto(20), AWScopy_default_distribution_format_version auto(20), AWScopy_title_fr auto(20), AWScopy__list_index_OGC_WMS auto(20), AWScopy__list_index_esrirest auto(20), AWScopy_nb_OGCWMScount auto(20), AWScopy_nb_OGCWMSvalue auto(20), fme_rejection_code auto(20), AWScopy_nb_esri_restcount auto(20), AWScopy_nb_esri_restvalue auto(20), AWScopy__histogram__.count auto(20), AWScopy__histogram__.value auto(20), AWScopy_protocol auto(20), AWScopy_xlink_role auto(20), AWScopy_url auto(20), AWScopy_format auto(20), AWScopy_name_fr auto(20), AWScopy_language_a auto(20), AWScopy_language_b auto(20), AWScopy_locale_a auto(20), AWScopy_locale_b auto(20), AWScopy_service_a auto(20), AWScopy_service_b auto(20), AWScopy__element_index auto(20),
      AWScopy_resources__.protocol auto(20), AWScopy_projectionList__.protocol auto(20), AWScopy_distributionList__.protocol auto(20), AWScopy_resources__.xlink_role auto(20), AWScopy_projectionList__.xlink_role auto(20), AWScopy_distributionList__.xlink_role auto(20), AWScopy_resources__.orig_id auto(20), AWScopy_projectionList__.orig_id auto(20), AWScopy_distributionList__.orig_id auto(20), AWScopy_resources__.notes auto(20), AWScopy_projectionList__.notes auto(20), AWScopy_distributionList__.notes auto(20), AWScopy_resources__.title auto(20), AWScopy_projectionList__.title auto(20), AWScopy_distributionList__.title auto(20), AWScopy_resources__.url auto(20), AWScopy_projectionList__.url auto(20), AWScopy_distributionList__.url auto(20), AWScopy_resources__.data_collection_end_date auto(20), AWScopy_projectionList__.data_collection_end_date auto(20), AWScopy_distributionList__.data_collection_end_date auto(20), AWScopy_resources__.data_collection_start_date auto(20), AWScopy_projectionList__.data_collection_start_date auto(20), AWScopy_distributionList__.data_collection_start_date auto(20), AWScopy_resources__.format auto(20), AWScopy_projectionList__.format auto(20), AWScopy_distributionList__.format auto(20), AWScopy_resources__.name auto(20), AWScopy_projectionList__.name auto(20), AWScopy_distributionList__.name auto(20),
      AWScopy_resources__.resource_update_cycle auto(20), AWScopy_projectionList__.resource_update_cycle auto(20), AWScopy_distributionList__.resource_update_cycle auto(20), AWScopy_resources__.resources auto(20), AWScopy_projectionList__.resources auto(20), AWScopy_distributionList__.resources auto(20), AWScopy_resources__.spatial_type auto(20), AWScopy_projectionList__.spatial_type auto(20), AWScopy_distributionList__.spatial_type auto(20), AWScopy_resources__.name_fr auto(20), AWScopy_projectionList__.name_fr auto(20), AWScopy_distributionList__.name_fr auto(20), AWScopy_resources__.id auto(20), AWScopy_projectionList__.id auto(20), AWScopy_distributionList__.id auto(20), AWScopy_resources__.language_a auto(20), AWScopy_projectionList__.language_a auto(20), AWScopy_distributionList__.language_a auto(20), AWScopy_resources__.language_b auto(20), AWScopy_projectionList__.language_b auto(20), AWScopy_distributionList__.language_b auto(20), AWScopy_resources__.locale_a auto(20), AWScopy_projectionList__.locale_a auto(20), AWScopy_distributionList__.locale_a auto(20), AWScopy_resources__.locale_b auto(20), AWScopy_projectionList__.locale_b auto(20), AWScopy_distributionList__.locale_b auto(20), AWScopy_resources__.service_a auto(20), AWScopy_projectionList__.service_a auto(20), AWScopy_distributionList__.service_a auto(20),
      AWScopy_resources__.service_b auto(20), AWScopy_projectionList__.service_b auto(20), AWScopy_distributionList__.service_b auto(20), AWScopy_resources__.projection_name auto(20), AWScopy_distributionList__.projection_name auto(20), AWScopy_resources__.resource_update_cycle_code auto(20), AWScopy_projectionList__.resource_update_cycle_code auto(20), AWScopy_distributionList__.resource_update_cycle_code auto(20), AWScopy_resources__.resource_update_cycle_fr auto(20), AWScopy_projectionList__.resource_update_cycle_fr auto(20), AWScopy_distributionList__.resource_update_cycle_fr auto(20), AWScopy_updateList__.resource_update_cycle auto(20), AWScopy_updateList__.resource_update_cycle_code auto(20), AWScopy_updateList__.resource_update_cycle_fr auto(20), AWScopy_more_info_0_.link auto(20), AWScopy_search_criteria_pycsw auto(20), AWScopy__global_hashkey auto(20), AWScopy__hash_pycsw auto(20), AWScopy_csw_version auto(20), AWScopy_csw_schema auto(20), AWScopy_csw_typenames auto(20), AWScopy_csw_filter auto(20), AWScopy_result.file_id auto(20), AWScopy_csw_search_criteria auto(20), AWScopy_MD_Metadata.MD_Metadata auto(20), AWScopy__OpenMapsFilter auto(20), AWScopy_result.results auto(20), AWScopy__list_name auto(20), AWScopy_MD_Metadata.fileIdentifier.CharacterString auto(20), AWScopy_MD_Metadata.path_windows auto(20),
      AWScopy_MD_Metadata.path_extension auto(20), AWScopy_path_windows auto(20), AWScopy_path_extension auto(20), AWScopy_PyCSW_Transaction auto(20), urls_https__ auto(20), urls_http__ auto(20), urls_ftp__ auto(20), length_issue auto(20), _total_number auto(20), _translation_problem auto(20), _timestamp auto(20)

Bookmark: XML CREATION & PUBLSHING
Note: Reading Config_YT
LOOKUP_TABLES_READER_14
    CSV_ENCODING = utf-8
    CSV_PATH = $(IN_CSV_LOOKUP_TABLES_DIR)
    FEATURE_TYPE = Config_YT
    PT = YT
    -> XML_PUBLISHER [CONFIG_FILE]
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
XML_PUBLISHER
    LOCAL_WRITER = $(LOCAL_WRITER)
    TEMPLATE_GMD_CITEDRESPONSIBLEPARTY = $(IN_GMD_XML_TEMPLATE_DIR)\GMD_CITEDRESPONSIBLEPARTY.xml
    TEMPLATE_GMD_CONTACT = $(IN_GMD_XML_TEMPLATE_DIR)\GMD_CONTACT.xml
    TEMPLATE_GMD_DISTRIBUTIONFORMAT = $(IN_GMD_XML_TEMPLATE_DIR)\GMD_DISTRIBUTIONFORMAT.xml
    TEMPLATE_GMD_DISTRIBUTOR = $(IN_GMD_XML_TEMPLATE_DIR)\GMD_DISTRIBUTOR.xml
    TEMPLATE_GMD_KEYWORDS = $(IN_GMD_XML_TEMPLATE_DIR)\GMD_KEYWORDS.xml
    TEMPLATE_GMD_MDMETADATA = $(IN_GMD_XML_TEMPLATE_DIR)\GMD_MDMETADATA.xml
    TEMPLATE_GMD_REFERENCESYSTEMINFO = $(IN_GMD_XML_TEMPLATE_DIR)\GMD_REFERENCESYSTEMINFO.xml
    TEMPLATE_GMD_RESOURCEMAINTENANCE = $(IN_GMD_XML_TEMPLATE_DIR)\GMD_RESOURCEMAINTENANCE.xml
    TEMPLATE_GMD_TOPICCATEGORY = $(IN_GMD_XML_TEMPLATE_DIR)\GMD_TOPICCATEGORY.xml
    TEMPLATE_GMD_TRANSFEROPTIONS = $(IN_GMD_XML_TEMPLATE_DIR)\GMD_TRANSFEROPTIONS.xml
    LOCAL -> text_line (writer TEXTLINE_3)
    INSERT_PASSED -> text_line (writer TEXTLINE_1)
    INSERT_FAILED -> text_line (writer TEXTLINE_2)
    UPDATE_PASSED -> text_line (writer TEXTLINE_1)
    UPDATE_FAILED -> text_line (writer TEXTLINE_2)

Bookmark: METADATA OUTPUT
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer

Bookmark: DATA EXTRACTION
Note: Reads pre-generated FFS file for testing as substitute for YT_CATALOGUE_READER
