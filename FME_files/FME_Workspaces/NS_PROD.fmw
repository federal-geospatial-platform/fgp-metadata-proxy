FME workspace NS_PROD.fmw
Title: NS_PROD
Description: Description 
This workbench read and trasform all the metadata for the province of Nova-Scotia (NS)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
METADATA_OVERWRITE: Enable the overwite of the PyCSW.  Can take two values: Yes: Overwrite the contentof the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: C:\Data\PT_Harvester\QC\LOG\QC.log
OUT_JSON_LOCAL_DIR: Source directory to output JSON files. Defined as: C:\Data\PT_Harvester\QC\JSON_LOCAL
OUT_XLS_NOTIFICATION: Source directory to output excel files. Defined as: C:\Data\PT_Harvester\QC\XLS
OUT_XML_FAILED_DIR: Source directory to output failed XML files. Defined as: C:\Data\PT_Harvester\QC\XML_FAILED
OUT_XML_LOCAL_DIR: Source directory to output Local Source XML files. Defined as: C:\Data\PT_Harvester\QC\XML_LOCAL
OUT_XML_PASSED_DIR: Source directory to output passedXML files. Defined as: C:\Data\PT_Harvester\QC\XML_PASSED
SAMPLE_SIZE: Number of features to process. Zero (0) means process all the features. A number n greater than 0 means sample or process only the first n features.
URL_VALIDATION : Indicates to validate or not created URL. (Should be Yes for prod)
VALIDATE_INSERT_PCT :Indicates to valide insert percentage. 75 % or less insert/update record  (Should be Yes for prod)

Parameters:
- ACTIVATE_GEO = Yes
- ACTIVATE_NON_GEO = Yes
- ACTIVATE_TRANSLATION = Yes
- CATALOGUE_READER_SELECT = Yes
- FORCED_PYCSW_URL =
- IN_FFS_TESTING_FILE =
- LOCAL_SOURCE_METADATA_DELTA_FINDER = No
- LOCAL_WRITER = No
- METADATA_OVERWRITE = NO
- IN_OUT_WORKING_DIR = $(FME_SHAREDRESOURCE_DATA)\PT_Harvester
- SAMPLE_SIZE = 0
- URL_VALIDATION = Yes
- VALIDATE_INSERT_PCT_JSON = Yes
- VALIDATE_INSERT_PCT_XML = Yes
- IN_CSV_LOOKUP_TABLES_DIR = $(IN_OUT_WORKING_DIR)\LOOKUP_TABLES   # DEFAULT_IN_CSV_LOOKUP_TABLES_DIR
- IN_GMD_XML_TEMPLATE_DIR = $(IN_OUT_WORKING_DIR)\XML_TEMPLATES
- IN_TBS_JSON_TEMPLATE_DIR = $(IN_OUT_WORKING_DIR)\JSON_TEMPLATES
- LOG_FILE = $(IN_OUT_WORKING_DIR)\$(P-T_ABBR)\LOG\$(P-T_ABBR).log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- FME_SHAREDRESOURCE_DATA = C:\Data   # FME Flow Data Directory

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(OUT_XLS_NOTIFICATION_DIR)
- TEXTLINE_4: TEXTLINE to $(OUT_JSON_LOCAL_DIR)

Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer
INVALID_METADATA (writer XLSXW_1)
    attributes: id auto(20)

Bookmark: lecture des données du portail socrata, filtrage de licence et fusion des métadonnées de vue externe
Creator_3
    GEOMTYPE = Geometry Object
    NUM = 1
    CREATED -> Tester_6
Tester_6
    BOOL_OP = OR
    TEST_CLAUSE = TEST $(CATALOGUE_READER_SELECT) = Yes
    TEST_MODE = TEST
    PASSED -> SOCRATA_READER_NG
    FAILED -> FeatureReader_2 [INITIATOR]
SOCRATA_READER_NG
    DOMAIN = https://data.novascotia.ca
    -> ATTRIBUTE_VALUE_TEXT_CLEANER
FeatureReader_2
    ATTR_ACCUM_MODE = Only Use Result
    CLIP_TO_ENVELOPE = NO
    COMBINE_GEOM = Use Result
    DATASET = $(IN_FFS_TESTING_FILE)
    FFS_USE_SEARCH_ENVELOPE = NO
    FORMAT = FFS
    INITIATOR_FIRST_OUTPUT = default
    INTERACT = NONE
    ORDER_RESULTS = No
    OUTPUT_ADD_SCHEMA_ATTRIBUTES = NO
    OUTPUT_FEATURES_DISPLAY = Schema and Data Features
    <OTHER> -> ATTRIBUTE_VALUE_TEXT_CLEANER
ATTRIBUTE_VALUE_TEXT_CLEANER
    -> AttributeExposer_3
AttributeExposer_3
    ATTR_TABLE = id,,licenseId,,name,
    -> NullAttributeMapper
NullAttributeMapper
    ATTRCHOICE_ACTION = SELECTED
    ATTRLIST = licenseId
    NEW_VALUE = none
    NULL_TREATMENT_LU = SETVALUE
    SOURCE_ATTR_VAL_LU = SETNULL EMPTY MISSINGATTR
    ATTRCHOICE = Selected Attributes
    NULL_TREATMENT = New Value
    SOURCE_ATTR_VAL = Null Empty "Missing (Selected Attributes Only)"
    -> LICENSE_FILTER_NG
Note: LICENSE_NS
LICENSE_FILTER_NG
    FEATURE_TYPE = License_NS
    IN_CSV_LOOKUP_TABLES_DIR = $(IN_CSV_LOOKUP_TABLES_DIR)
    LICENSE_ATT = @Value(licenseId)
    P-T_ABBR = $(P-T_ABBR)
    LICENSE_FILTER_PASSED -> Socrata_MetadataMerger
    UNKNOWN_LICENSE -> UNKNOWN_LICENCE (writer XLSXW_1)
Socrata_MetadataMerger: SOCRATA_METADATA_MERGER
    DOMAIN = https://data.novascotia.ca
    -> DEFAULT_ATTRIBUTE_MAPPER_NG
    UnmergedAdvancedView -> UNMERGED_ADVANCED_VIEW (writer XLSXW_1)
UNMERGED_ADVANCED_VIEW (writer XLSXW_1)
    attributes: url string(200), format string(200), _seriesID string(20)
UNKNOWN_LICENCE (writer XLSXW_1)
    attributes: license_id string(200), id string(200), name string(200)

Bookmark: Transformation vers modèle de travail et ajout des valeurs par défaults
Note: DEFAULT NS
DEFAULT_ATTRIBUTE_MAPPER_NG
    FEATURE_TYPE = Default_NS
    IN_CSV_LOOKUP_TABLES_DIR = $(IN_CSV_LOOKUP_TABLES_DIR)
    P-T_ABBR = $(P-T_ABBR)
    -> AttributeExposer_14
EXTRACT_COLLECTION_START_END_DATE
    CSV_PATH = $(IN_CSV_LOOKUP_TABLES_DIR)
    DATE_EXTENT = @Value(range_collection_date)
    FEATURE_TYPE = NS_Manual_end_start_collection_date
    PT = $(P-T_ABBR)
    -> AttributeExposer_16
    Unworking_extent -> AttributeExposer_20
AttributeExposer_20
    ATTR_TABLE = id,
    -> UNWORKING_DATE_COLLECTION_EXTENT (writer XLSXW_1)
UNWORKING_DATE_COLLECTION_EXTENT (writer XLSXW_1)
    attributes: unmatched_date_extent string(200), id string(200)

Bookmark: Date conversion
AttributeExposer_14
    ATTR_TABLE = publicationDate,,createdAt,,viewLastModified,,id,
    -> DateTimeConverter
Note: Formats all date fields to ISO yyyy-mm-dd
DateTimeConverter
    DATETIME_ATTR = viewLastModified createdAt publicationDate
    IN_FORMAT = %s$
    OUT_FORMAT = %Y-%m-%d
    PASSTHROUGH = NO
    REPAIR_INPUT = YES
    TEST_INPUT = 1611946240
    -> ATTRIBUTE_MANAGER_NG
    <REJECTED> -> ERROR_DATETIME (writer XLSXW_1)
ERROR_DATETIME (writer XLSXW_1)
    attributes: publicationDate string(200), fme_rejection_code string(20), id string(20)

Bookmark: Attribute Manager
Note: Default_Attributes
ATTRIBUTE_MANAGER_NG
    IN_YAML_TEXT:
      # Default value fot tags
      tags{0}:
          action: attribute_not_null
          attr2set: default_domain_tag

      # Default value for description
      description:
          action: attribute_not_null
          attr2set: name
    -> ATTRIBUTE_MANAGER_NG_2
Note: Create Attributes
ATTRIBUTE_MANAGER_NG_2
    IN_YAML_TEXT:
      resource.id:
          action: attribute_overwrite
          attr2set: id

      resource.type:
          action: attribute_overwrite
          attr2set: assetType

      tags_copy:
          action: attribute_overwrite
          attr2set: tags

      spatialref{0}.projection_name:
          action: attribute_overwrite
          attr2set: default_projection_name

      spatialref{0}.projection_system:
          action: attribute_overwrite
          attr2set: default_reference_system

      spatialref{0}.projection_system_version:
          action: attribute_overwrite
          attr2set: default_projection_system_version

      sector:
          action: attribute_overwrite
          attr2set: metadata.custom_fields.Detailed Metadata.Department

      notes:
          action: attribute_overwrite
          attr2set: description

      title:
          action: attribute_overwrite
          attr2set: name

      record_publish_date:
          action: attribute_overwrite
          attr2set: publicationDate

      record_last_modified:
          action: attribute_overwrite
          attr2set: viewLastModified

      record_create_date:
          action: attribute_overwrite
          attr2set: createdAt

      updated_frequency:
          action: attribute_overwrite
          attr2set: metadata.custom_fields.Detailed Metadata.Frequency

      progress_code:
          action: attribute_overwrite
          attr2set: metadata.custom_fields.Detailed Metadata.Frequency

      range_collection_date:
          action: attribute_overwrite
          attr2set: metadata.custom_fields.Detailed Metadata.Time Period Coverage

      subject_tbs:
          action: attribute_overwrite
          attr2set: category

      topic_tbs:
          action: attribute_overwrite
          attr2set: category
    -> AttributeRemover_8
Note: Gestion des Tags
METADATA_VALUE_MAPPER_NG_6
    ATT_TO_MAP = tags{}.display_name
    CODE_REFRESH = NO
    ENGLISH_REFRESH = YES
    ERROR_NOT_MAPPED = NO
    FEATURE_TYPE = Keyword_NS
    FRENCH_REFRESH = NO
    IN_CSV_LOOKUP_TABLES_DIR = $(IN_CSV_LOOKUP_TABLES_DIR)
    P-T_ABBR = $(P-T_ABBR)
    -> AttributeExposer_15
AttributeExposer_15
    ATTR_TABLE = resource.id,,range_collection_date,
    -> UNIQUE_ID_CREATOR_2
UNIQUE_ID_CREATOR_2
    UNIQUE_ATT = @Value(resource.id)
    -> EXTRACT_COLLECTION_START_END_DATE

Bookmark: Replace Tags_copy{}
AttributeRemover_8
    LIST_ATTRS = tags{}
    -> PythonCaller_4
PythonCaller_4
    NEW_ATTRIBUTES = tags{}.display_name buffer
    PYTHONSOURCE:
      import fme
      import fmeobjects
      # Template Function interface:
      # When using this function, make sure its name is set as the value of
      # the 'Class or Function to Process Features' transformer parameter
      def processFeature(feature):
          i=0
          for elem in feature.getAttribute('tags_copy{}'):
              feature.setAttribute('tags{%i}.display_name'%(i),elem)
              i+=1



      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> AttributeRemover_9
AttributeRemover_9
    LIST_ATTRS = tags_copy{}
    -> METADATA_VALUE_MAPPER_NG_6 [DATA_INPUT]

Bookmark: Création de la liste des ressources pour les jeux de données
AttributeExposer_16
    ATTR_TABLE = resource.id,
    -> GEOPORTAL_WEBLINK_ADDER_NG_2
Note: GeoportalWeblink_NS
GEOPORTAL_WEBLINK_ADDER_NG_2
    FEATURE_TYPE = GeoportalWeblink_NS
    IN_CSV_LOOKUP_TABLES_DIR = $(IN_CSV_LOOKUP_TABLES_DIR)
    P-T_ABBR = $(P-T_ABBR)
    URL_VALIDATION = $(URL_VALIDATION)
    WEBLINK_WILDCARD = @Value(resource.id)
    -> SOCRATA_ADDITIONAL_ACCESS_POINTS_RESOURCES_EXTRACTOR
Note: Extraction des ressources dans additional access points / Crée la liste additional_access_points_resources
SOCRATA_ADDITIONAL_ACCESS_POINTS_RESOURCES_EXTRACTOR
    -> SOCRATA_ATTACHEMENTS_EXTRACTOR
Note: Extraction des resources dans les attachements / Crée la liste attachement_resources
SOCRATA_ATTACHEMENTS_EXTRACTOR
    SBN_URL_ROOT = https://data.novascotia.ca
    URL_VALIDATION = $(URL_VALIDATION)
    -> SOCRATA_ADVANCED_VIEW_EXTRACTOR
Note: Extraction des ressources dans les vues avanacées / Crée la liste advancedview_resources
SOCRATA_ADVANCED_VIEW_EXTRACTOR
    -> SOCRATA_INSIDE_DB_EXTRACTOR_NG
SOCRATA_INSIDE_DB_EXTRACTOR_NG
    DOMAIN = https://data.novascotia.ca
    Field_datatype = NS_FieldType_NG
    Field_name = NS_GeoDataFieldName
    IN_CSV_LOOKUP_TABLES_DIR = $(IN_CSV_LOOKUP_TABLES_DIR)
    LinkBuilderNonGeo = NS_LINKBUILDER_NONGEO
    P-T_ABBR = $(P-T_ABBR)
    URL_VALIDATION = $(URL_VALIDATION)
    linkbuilder_geo = NS_LINKBUILDER_GEO
    -> AttributeExposer_5
    Unknown_field_datatype -> UNKNOWN_FIELD_DATATYPE (writer XLSXW_1)
ListElementCounter
    CNT_ATTR = _element_count
    LIST_NAME = resources{}
    -> Tester_2
Note: Uniquement les entités ayanty plus qu'une ressource
Tester_2
    BOOL_OP = OR
    TEST_CLAUSE = TEST @Value(_element_count) > 1
    TEST_MODE = TEST
    PASSED -> EMPTY_FORMAT_MAPPER_NG [DATA_INPUT]
Note: Extraction du format
EMPTY_FORMAT_MAPPER_NG
    CSV_FORMAT = Format
    CSV_MIME_TYPE = Mime_type
    IN_CSV_LOOKUP_TABLES_DIR = $(IN_CSV_LOOKUP_TABLES_DIR)
    P-T_ABBR = $(P-T_ABBR)
    URL_VALIDATION = $(URL_VALIDATION)
    DATA_OUTPUT -> GEO_NONE_GEO_SELECTOR_2
    UNKNOWN_MIME_TYPE -> UNKNOWN_MIME_TYPE (writer XLSXW_1)
UNKNOWN_MIME_TYPE (writer XLSXW_1)
    attributes: id string(200), _url_validation string(200), _unknown_mime_type string(200)
UNKNOWN_FIELD_DATATYPE (writer XLSXW_1)
    attributes: fieldName string(200), dataTypeName string(200), columns string(200)

Bookmark: Fusion des listes de resources dans une seule liste
AttributeExposer_5
    ATTR_TABLE = resources{}.url,
    -> ListCopier
ListCopier
    DEST_LIST = resources_copy
    SRC_LIST = resources{}
    -> AttributeRemover
AttributeRemover
    LIST_ATTRS = resources{}
    -> PythonCaller_3
PythonCaller_3
    NEW_ATTRIBUTES = resources{}.name buffer resources{}.url buffer resources{}.format buffer resources{}.name_fr buffer
    PYTHONSOURCE:
      import fme
      import fmeobjects
      logger = fmeobjects.FMELogFile()
      # Template Function interface:
      # When using this function, make sure its name is set as the value of
      # the 'Class or Function to Process Features' transformer parameter
      def processFeature(feature):
          list_list_name=[r'resources_copy',r'socrata_db_resources',r'advancedview_resources',r'additional_access_points_resources',r'attachement_resources']
          list_attr_name=[r'format',r'url',r'name',r'name_fr',r'spatial_type',r'fgp_publish']

          i=0





          for list_name in list_list_name:

              #Extracting number of resources
              list_url=feature.getAttribute('%s{}.url'%(list_name))
              if list_url:
                  #Looping in resources
                  for j in range(len(list_url)):
                      #Looping in attributes
                      for attr_name in list_attr_name:
                          feature.setAttribute('resources{%i}.%s'%(i,attr_name),feature.getAttribute('%s{%i}.%s'%(list_name,j,attr_name)))

                      #Changing index feature where new features
                      i=i+1
    PYTHONSYMBOL = processFeature
    -> ListDuplicateRemover_2
Note: Removing dupplicates on URL
ListDuplicateRemover_2
    SRC_LIST = resources{}.url
    -> AttributeExposer_7
AttributeExposer_7
    ATTR_TABLE = resources_copy{},,socrata_db_resources{},,advancedview_resources{},,additional_access_points_resources{},,attachement_resources{},
    -> AttributeRemover_7
Note: Retrait des liste mergées
AttributeRemover_7
    LIST_ATTRS = additional_access_points_resources{} advancedview_resources{} attachement_resources{} resources_copy{} socrata_db_resources{}
    -> ListElementCounter

Bookmark: Filtrage geo / non-geo
Note: Sélection par format
GEO_NONE_GEO_SELECTOR_2
    CSV_FILE_NAME = GeoSpatialValidation
    CSV_PATH = $(IN_CSV_LOOKUP_TABLES_DIR)
    CSV_PROVINCE = $(P-T_ABBR)
    YAML_DIRECTIVES:
      resources{}.format:
        domain: lookup_table_format
        spatial_type: overwrite
        not_found: log
        search_type: equals
    GEOSPATIAL -> AttributeExposer_4
    NONE_GEOSPATIAL -> GEO_NONE_GEO_SELECTOR_3
    LOG_ERROR -> AttributeExposer_22
AttributeExposer_22
    ATTR_TABLE = id,,format,
    -> GEOSPATIAL_FORMAT_NOT_MAPPED (writer XLSXW_1)
GEOSPATIAL_FORMAT_NOT_MAPPED (writer XLSXW_1)
    attributes: id string(200), _not_found_err_msg string(200), format string(200)
Note: Sélection par fgp publish et keyword
GEO_NONE_GEO_SELECTOR_3
    CSV_PATH = $(IN_CSV_LOOKUP_TABLES_DIR)
    CSV_PROVINCE = $(P-T_ABBR)
    YAML_DIRECTIVES:
      resources{}.fgp_publish:
       domain: [oui]
       spatial_type: no_overwrite
       not_found: no_log
       search_type: equals

      tags{}.display_name:
       domain: [lidar,elevation,geoscientific,topography]
       spatial_type: no_overwrite
       not_found: no_log
       search_type: equals
    GEOSPATIAL -> AttributeExposer_4
    NONE_GEOSPATIAL -> AttributeExposer_21
AttributeExposer_21
    ATTR_TABLE = id,,resource.id,
    -> MANUAL_GEOSPATIAL_SETTER_NG [DATA_INPUT]
MANUAL_GEOSPATIAL_SETTER_NG
    FEATURE_TYPE = UnmappedGeoData_NS
    IN_CSV_LOOKUP_TABLES_DIR = $(IN_CSV_LOOKUP_TABLES_DIR)
    P-T_ABBR = $(P-T_ABBR)
    GEOSPATIAL -> Tester_7
    NON-GEOSPATIAL -> AttributeRemover_5
    UNMAPPED_DATA -> UNMAPPED_DATA (writer XLSXW_1)
AttributeRemover_5
    REMOVE_ATTRS = id_temp
    -> Tester_3
UNMAPPED_DATA (writer XLSXW_1)
    attributes: id string(200), notes string(200), title string(200), url string(200)

Bookmark: Adding spatial type manually
AttributeExposer_4
    ATTR_TABLE = id,,resource.id,
    -> AttributeCreator_3
AttributeCreator_3
    ATTR_TABLE = SET_TO id_temp (varchar(200)) = @Value(id)
    -> AttributeCreator_4
AttributeCreator_4
    ATTR_TABLE = SET_TO id (varchar(200)) = @Value(resource.id)
    -> SPATIAL_TYPE_MAPPER_NG [DATA_INPUT]
Note: SpatialType_NS
SPATIAL_TYPE_MAPPER_NG
    FEATURE_TYPE = SpatialType_NS
    IN_CSV_LOOKUP_TABLES_DIR = $(IN_CSV_LOOKUP_TABLES_DIR)
    P-T_ABBR = $(P-T_ABBR)
    DATA_OUTPUT_FAILED -> AttributeExposer
    DATA_OUTPUT_PASSED -> AttributeExposer_13
AttributeExposer
    ATTR_TABLE = id,,title,,note,
    -> SPATIAL_TYPE_FAILED (writer XLSXW_1)
SPATIAL_TYPE_FAILED (writer XLSXW_1)
    attributes: id string(200), title string(200), note string(200)
AttributeExposer_13
    ATTR_TABLE = id_temp,
    -> AttributeRenamer
AttributeRenamer
    ATTR_TABLE = RENAME_SET_DEFAULT id_temp > id
    KEEP_RENAMED_ONLY = no
    MISSING_INPUT_ATTRS = PRESERVE
    -> Tester_7

Bookmark: Activate Geo and Sample or full content
Tester_7
    BOOL_OP = OR
    TEST_CLAUSE = TEST @UpperCase($(ACTIVATE_GEO)) = YES
    TEST_MODE = TEST
    PASSED -> TestFilter
TestFilter
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Socrata_BoundingBoxExtractor [feature_input]
    SAMPLES FEATURES -> Sampler_3
Sampler_3
    MODE = ORIGINAL
    RATE = $(SAMPLE_SIZE)
    SAMPLE_TYPE_MULTIPLIER = -1
    SAMPLE_MODE = No
    SAMPLE_TYPE_LONG = First N Features
    SAMPLED -> Socrata_BoundingBoxExtractor [feature_input]

Bookmark: Metadata Value Mapping - GEO
Socrata_BoundingBoxExtractor: SOCRATA_BOUNDING_BOX_EXTRACTOR
    DOMAIN = http://data.novascotia.ca
    SocrataAppToken = FL3Cxsebg0Vf6JQ0CnbMujHkQ
    feature_output -> METADATA_VALUE_MAPPER_NG_8 [DATA_INPUT]
Note: Topic
METADATA_VALUE_MAPPER_NG_8
    ATT_TO_MAP = category
    CODE_REFRESH = NO
    ENGLISH_REFRESH = YES
    ERROR_NOT_MAPPED = YES
    FEATURE_TYPE = Topic
    FRENCH_REFRESH = NO
    IN_CSV_LOOKUP_TABLES_DIR = $(IN_CSV_LOOKUP_TABLES_DIR)
    P-T_ABBR = $(P-T_ABBR)
    -> METADATA_VALUE_MAPPER_NG_2 [DATA_INPUT]
Note: Role
METADATA_VALUE_MAPPER_NG_2
    ATT_TO_MAP = role
    CODE_REFRESH = YES
    ENGLISH_REFRESH = YES
    ERROR_NOT_MAPPED = YES
    FEATURE_TYPE = Role
    FRENCH_REFRESH = YES
    IN_CSV_LOOKUP_TABLES_DIR = $(IN_CSV_LOOKUP_TABLES_DIR)
    P-T_ABBR = $(P-T_ABBR)
    -> METADATA_VALUE_MAPPER_NG_3 [DATA_INPUT]
Note: Update
METADATA_VALUE_MAPPER_NG_3
    ATT_TO_MAP = updated_frequency
    CODE_REFRESH = YES
    ENGLISH_REFRESH = YES
    ERROR_NOT_MAPPED = YES
    FEATURE_TYPE = Update
    FRENCH_REFRESH = YES
    IN_CSV_LOOKUP_TABLES_DIR = $(IN_CSV_LOOKUP_TABLES_DIR)
    P-T_ABBR = $(P-T_ABBR)
    -> METADATA_VALUE_MAPPER_NG_4 [DATA_INPUT]
Note: Progress
METADATA_VALUE_MAPPER_NG_4
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUP_TABLES_DIR)
    P-T_ABBR = $(P-T_ABBR)
    -> METADATA_VALUE_MAPPER_NG_5 [DATA_INPUT]
Note: SpatialRepresentation
METADATA_VALUE_MAPPER_NG_5
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUP_TABLES_DIR)
    P-T_ABBR = $(P-T_ABBR)
    -> METADATA_FORMAT_MAPPER_NG [DATA_INPUT]
Note: Format
METADATA_FORMAT_MAPPER_NG
    ATT_TO_MAP = resources{}.format
    ERROR_NOT_MAPPED = YES
    FEATURE_TYPE = Format
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_Geo (writer XLSXW_1)
    -> METADATA_VALUE_MAPPER_ERROR_MANAGER
METADATA_VALUE_MAPPER_ERROR_MANAGER
    ERROR_OUTPUT -> METADATA_MAPPING_ERRORS_GEO (writer XLSXW_1)
    DATA_OUTPUT -> AttributeRemover_6
Note: Removing error list
AttributeRemover_6
    LIST_ATTRS = mapping_errors{}
    -> RESOURCE_NAME_UNDERSCORE_REMOVER
METADATA_MAPPING_ERRORS_GEO (writer XLSXW_1)
    attributes: error string(200), id string(200)
UNKNOWN_MIME_TYPE_Geo (writer XLSXW_1)
    attributes: id string(200), _url_validation string(200), _unknown_mime_type string(200)

Bookmark: Remove all underscores from resources{}.name attributes
RESOURCE_NAME_UNDERSCORE_REMOVER
    DATA_OUTPUT -> REMOVE_BROKEN_URL_WMS_ESRI_REST

Bookmark: Drop Broken Web Services
REMOVE_BROKEN_URL_WMS_ESRI_REST
    URL_VALIDATION = $(URL_VALIDATION)
    -> WMS_REST_LANGUAGE_FORMATTER
    FAULTY_URL_OUTPUT -> MAP_SERVICE_URL_ERRORMAP (writer XLSXW_1)
MAP_SERVICE_URL_ERRORMAP (writer XLSXW_1)
    attributes: id string(200), url string(200), format string(200), _url_failure_message string(20)

Bookmark: HNAP RULES
WMS_REST_LANGUAGE_FORMATTER
    -> DUPLICATE_SERVICE_REMOVER
DUPLICATE_SERVICE_REMOVER
    -> GMD_SECTION_DATA_EXTRACTION
GMD_SECTION_DATA_EXTRACTION
    -> AttributeCreator

Bookmark: New Bookmark
AttributeCreator
    ATTR_TABLE = SET_TO csw_url (varchar(200)) = $(FORCED_PYCSW_URL)
    -> ATTRIBUTE_MANAGER_NG_4
AttributeExposer_8
    ATTR_TABLE = search_criteria_pycsw,,csw_url,,record_last_modified,,id,
    -> METADATA_DELTA_FINDER_GEN
METADATA_DELTA_FINDER_GEN
    ATTR_DATE_MODIFIED = record_last_modified
    CSW_FILTER = @Value(search_criteria_pycsw)
    LOCAL_SOURCE = $(LOCAL_SOURCE_METADATA_DELTA_FINDER)
    METADATA_OVERWRITE = $(METADATA_OVERWRITE)
    METADATA_TYPE = XML-HNAP
    SOURCE_DIRECTORY = $(OUT_XML_LOCAL_DIR)
    SOURCE_URL = @Value(csw_url)
    VALIDATE_INSERT_PCT = $(VALIDATE_INSERT_PCT_XML)
    YAML_FILE = $(IN_CSV_LOOKUP_TABLES_DIR)\$(P-T_ABBR)\metadata_delta_finder_$(P-T_ABBR)_geo.yaml
    Statistics -> StatisticsCalculator_Summary_2
    Update -> AWS_TRANSLATE_2
    Insert -> AWS_TRANSLATE_2
    Delete -> AttributeExposer_9
StatisticsCalculator_Summary_2: Logger
    LOG_FEATURE = NONE
    MAXFEATS = 20
    MESSAGE:
      **************************************
      ***********Unchanged Report************
      **************************************

      @Value(_real_count) features were unchanged

      **************************************
      **************************************
      **************************************
    SEVERITY = INFO
AttributeExposer_9
    ATTR_TABLE = id,
    -> DELETED_RECORDS (writer XLSXW_1)
DELETED_RECORDS (writer XLSXW_1)
    attributes: id string(200)

Bookmark: Listes Metadata_delta_finder
ATTRIBUTE_MANAGER_NG_4
    IN_YAML_TEXT:
      contacts{0}.role_code:
         action: attribute_not_null
         attr2set: role_code
      contacts{0}.role:
         action: attribute_not_null
         attr2set: role
      contacts{0}.role_fr:
         action: attribute_not_null
         attr2set: role_fr
      contacts{0}.p-t_entity:
         action: attribute_not_null
         attr2set: p-t_entity
      contacts{0}.p-t_entity_fr:
         action: attribute_not_null
         attr2set: p-t_entity_fr
      contacts{0}.sector:
         action: attribute_not_null
         attr2set: sector
      contacts{0}.sector_fr:
         action: attribute_not_null
         attr2set: sector
      contacts{0}.email:
         action: attribute_not_null
         attr2set: contact_form_en
      distributionList{0}.format_version:
         action: attribute_not_null
         attr2set: distribution_format_version
      resources{0}.language:
         action: attribute_not_null
         attr2set: transfer_desc_locale_default
      category{0}.value:
         action: attribute_not_null
         attr2set: category
    -> ATTRIBUTE_MANAGER_NG_5
ATTRIBUTE_MANAGER_NG_5
    IN_YAML_TEXT:
      contacts{}.role_code:
         action: attribute_not_null
         attr2set: role_code
      contacts{}.role:
         action: attribute_not_null
         attr2set: role
      contacts{}.role_fr:
         action: attribute_not_null
         attr2set: role_fr
      contacts{}.p-t_entity:
         action: attribute_not_null
         attr2set: p-t_entity
      contacts{}.p-t_entity_fr:
         action: attribute_not_null
         attr2set: p-t_entity_fr
      contacts{}.sector:
         action: attribute_not_null
         attr2set: sector
      contacts{}.sector_fr:
         action: attribute_not_null
         attr2set: sector
      contacts{}.email:
         action: attribute_not_null
         attr2set: contact_form_en
      distributionList{}.format_version:
         action: attribute_not_null
         attr2set: distribution_format_version
      resources{}.language:
         action: attribute_not_null
         attr2set: transfer_desc_locale_default
      category{}.value:
         action: attribute_not_null
         attr2set: category
    -> AttributeExposer_8

Bookmark: AWS Translation
Note: English to french / notes,title, tags_en / resources name
AWS_TRANSLATE_2
    ACTIVATE_TRANSLATION = $(ACTIVATE_TRANSLATION)
    ATTR_2_TRANSLATE = notes,title
    ATTR_LIST_2_TRANSLATE = tags{}.display_name,resources{}.name
    MODE = English-->French
    -> AttributeExposer_6
    TRANSLATION_PROBLEM -> AttributeExposer_12
AttributeExposer_12
    ATTR_TABLE = id,,title,
    -> TRANSLATION_PROBLEMS_GEO (writer XLSXW_1)
TRANSLATION_PROBLEMS_GEO (writer XLSXW_1)
    attributes: id string(20), title string(20)

Bookmark: Rebuilding tags list
AttributeExposer_6
    ATTR_TABLE = tags{},
    -> ListElementCounter_2
ListElementCounter_2
    CNT_ATTR = _nb_tags
    LIST_NAME = tags{}
    -> PythonCaller_2
PythonCaller_2
    NEW_ATTRIBUTES = tags{}.display_name_lower buffer tags{}.display_name_fr_lower buffer
    PYTHONSOURCE:
      import fme
      import fmeobjects
      # Template Function interface:
      # When using this function, make sure its name is set as the value of
      # the 'Class or Function to Process Features' transformer parameter
      def processFeature(feature):
          i=0

          for j in range(int(feature.getAttribute('_nb_tags'))):
              feature.setAttribute('tags{%i}.display_name_lower'%(i),feature.getAttribute('tags{%i}.display_name'%(j)).lower())
              feature.setAttribute('tags{%i}.display_name_fr_lower'%(i),feature.getAttribute('tags{%i}.display_name_fr'%(j)).lower())
              i=i+1
    PYTHONSYMBOL = processFeature
    -> XML_PUBLISHER_NG_2

Bookmark: XML CREATION AND WRITING
Note: Config_NS
XML_PUBLISHER_NG_2
    FEATURE_TYPE = Config_NS
    IN_CSV_LOOKUP_TABLES_DIR = $(IN_CSV_LOOKUP_TABLES_DIR)
    LOCAL_WRITER = $(LOCAL_WRITER)
    P-T_ABBR = $(P-T_ABBR)
    TEMPLATE_GMD_CITEDRESPONSIBLEPARTY = $(IN_GMD_XML_TEMPLATE_DIR)\GMD_CITEDRESPONSIBLEPARTY.xml
    TEMPLATE_GMD_CONTACT = $(IN_GMD_XML_TEMPLATE_DIR)\GMD_CONTACT.xml
    TEMPLATE_GMD_DISTRIBUTIONFORMAT = $(IN_GMD_XML_TEMPLATE_DIR)\GMD_DISTRIBUTIONFORMAT.xml
    TEMPLATE_GMD_DISTRIBUTOR = $(IN_GMD_XML_TEMPLATE_DIR)\GMD_DISTRIBUTOR.xml
    TEMPLATE_GMD_KEYWORDS = $(IN_GMD_XML_TEMPLATE_DIR)\GMD_KEYWORDS.xml
    TEMPLATE_GMD_MDMETADATA = $(IN_GMD_XML_TEMPLATE_DIR)\GMD_MDMETADATA.xml
    TEMPLATE_GMD_REFERENCESYSTEMINFO = $(IN_GMD_XML_TEMPLATE_DIR)\GMD_REFERENCESYSTEMINFO.xml
    TEMPLATE_GMD_RESOURCEMAINTENANCE = $(IN_GMD_XML_TEMPLATE_DIR)\GMD_RESOURCEMAINTENANCE.xml
    TEMPLATE_GMD_TOPICCATEGORY = $(IN_GMD_XML_TEMPLATE_DIR)\GMD_TOPICCATEGORY.xml
    TEMPLATE_GMD_TRANSFEROPTIONS = $(IN_GMD_XML_TEMPLATE_DIR)\GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    InvalidMetadata -> INVALID_METADATA (writer XLSXW_1)
    UPDATE_FAILED -> text_line (writer TEXTLINE_2)

Bookmark: Activate None Geo and Sample or fulle content
Tester_3
    BOOL_OP = OR
    TEST_CLAUSE = TEST @UpperCase($(ACTIVATE_NON_GEO)) = YES
    TEST_MODE = TEST
    PASSED -> TestFilter_2
TestFilter_2
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> METADATA_VALUE_MAPPER_NG_7 [DATA_INPUT]
    SAMPLES FEATURES -> Sampler_2
Sampler_2
    MODE = ORIGINAL
    RATE = $(SAMPLE_SIZE)
    SAMPLE_TYPE_MULTIPLIER = -1
    SAMPLE_MODE = No
    SAMPLE_TYPE_LONG = First N Features
    SAMPLED -> METADATA_VALUE_MAPPER_NG_7 [DATA_INPUT]

Bookmark: Metadata Value Mapping - NONGEO
Note: UpdateFrequency_TBS
METADATA_VALUE_MAPPER_NG_7
    ATT_TO_MAP = updated_frequency
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUP_TABLES_DIR)
    P-T_ABBR = $(P-T_ABBR)
    -> METADATA_FORMAT_MAPPER_NG_2 [DATA_INPUT]
Note: Format_TBS
METADATA_FORMAT_MAPPER_NG_2
    ATT_TO_MAP = resources{}.format
    ERROR_NOT_MAPPED = YES
    FEATURE_TYPE = Format_TBS
    IN_CSV_LOOKUP_TABLES_DIR = $(IN_CSV_LOOKUP_TABLES_DIR)
    P-T_ABBR = $(P-T_ABBR)
    REAL_VALUE_REFRESH = YES
    RES_TYPE_EN_REFRESH = NO
    RES_TYPE_FR_REFRESH = NO
    URL_VALIDATION = $(URL_VALIDATION)
    Unknown_Mime_Type -> UNKNOWN_MIME_TYPE_NoneGeo (writer XLSXW_1)
    -> METADATA_VALUE_MAPPER_NG_9 [DATA_INPUT]
Note: Subject_TBS
METADATA_VALUE_MAPPER_NG_9
    ATT_TO_MAP = subject_tbs
    CODE_REFRESH = NO
    ENGLISH_REFRESH = YES
    ERROR_NOT_MAPPED = YES
    FEATURE_TYPE = Subject_TBS
    FRENCH_REFRESH = NO
    IN_CSV_LOOKUP_TABLES_DIR = $(IN_CSV_LOOKUP_TABLES_DIR)
    P-T_ABBR = $(P-T_ABBR)
    -> METADATA_VALUE_MAPPER_NG_10 [DATA_INPUT]
Note: Topic_TBS
METADATA_VALUE_MAPPER_NG_10
    ATT_TO_MAP = topic_tbs
    CODE_REFRESH = NO
    ENGLISH_REFRESH = YES
    ERROR_NOT_MAPPED = YES
    FEATURE_TYPE = Topic_TBS
    FRENCH_REFRESH = NO
    IN_CSV_LOOKUP_TABLES_DIR = $(IN_CSV_LOOKUP_TABLES_DIR)
    P-T_ABBR = $(P-T_ABBR)
    -> AttributeExposer_19
AttributeExposer_19
    ATTR_TABLE = org_name,
    -> AttributeCreator_6
AttributeCreator_6
    ATTR_TABLE = SET_TO organization_name (varchar(200)) = @Value(org_name)
    -> METADATA_VALUE_MAPPER_ERROR_MANAGER_2
METADATA_VALUE_MAPPER_ERROR_MANAGER_2
    ERROR_OUTPUT -> NON_GEO_ATTRIBUTE_MAPPING_ERRORS (writer XLSXW_1)
    DATA_OUTPUT -> AttributeExposer_23
AttributeExposer_23
    ATTR_TABLE = record_last_modified,,id,
    -> METADATA_DELTA_FINDER_GEN_2
METADATA_DELTA_FINDER_GEN_2
    ATTR_DATE_MODIFIED = record_last_modified
    LOCAL_SOURCE = Yes
    METADATA_OVERWRITE = $(METADATA_OVERWRITE)
    METADATA_TYPE = JSON-CKANExtCa
    SOURCE_DIRECTORY = $(OUT_JSON_LOCAL_DIR)
    VALIDATE_INSERT_PCT = $(VALIDATE_INSERT_PCT_JSON)
    YAML_FILE = $(IN_CSV_LOOKUP_TABLES_DIR)\$(P-T_ABBR)\metadata_delta_finder_$(P-T_ABBR)_non_geo.yaml
    Statistics -> StatisticsCalculator_Summary_3
    Update -> AWS_TRANSLATE_3
    Insert -> AWS_TRANSLATE_3
    Delete -> AttributeExposer_2
StatisticsCalculator_Summary_3: Logger
    LOG_FEATURE = NONE
    MAXFEATS = 20
    MESSAGE:
      ************************
      **** NoneGeo Features: Unchanged Report ****
      ************************

      @Value(_real_count) features were unchanged

      ************************
      ************************
      ************************
    SEVERITY = INFO
AttributeExposer_2
    ATTR_TABLE = id,,title,
    -> DELETED_RECORDS_NON_GEO (writer XLSXW_1)
DELETED_RECORDS_NON_GEO (writer XLSXW_1)
    attributes: id string(200), title string(200)
Note: English to french / notes,title,tags_en / resources name
AWS_TRANSLATE_3
    ACTIVATE_TRANSLATION = $(ACTIVATE_TRANSLATION)
    ATTR_2_TRANSLATE = notes,title
    ATTR_LIST_2_TRANSLATE = tags{}.display_name,resources{}.name
    MODE = English-->French
    -> AttributeExposer_17
    TRANSLATION_PROBLEM -> AttributeExposer_10
AttributeExposer_10
    ATTR_TABLE = id,,title,
    -> TRANSLATION_PROBLEMS_NONE_GEO (writer XLSXW_1)
TRANSLATION_PROBLEMS_NONE_GEO (writer XLSXW_1)
    attributes: id string(20), title string(20)
NON_GEO_ATTRIBUTE_MAPPING_ERRORS (writer XLSXW_1)
    attributes: error string(200), id string(200)
UNKNOWN_MIME_TYPE_NoneGeo (writer XLSXW_1)
    attributes: id string(200), _url_validation string(200), _unknown_mime_type string(200)

Bookmark: JSON CREATION AND WRITING
AttributeExposer_17
    ATTR_TABLE = tags{}.display_name,,tags{}.display_name_fr,
    -> JSON_PUBLISHER_NG
Note: NS_JSON_CONFIG
JSON_PUBLISHER_NG
    FEATURE_TYPE = NS_JSON_CONFIG
    IN_CSV_LOOKUP_TABLES_DIR = $(IN_CSV_LOOKUP_TABLES_DIR)
    JSON_RESOURCE_TEMPLATE = $(IN_TBS_JSON_TEMPLATE_DIR)\TBS_RESOURCES_TEMPLATE_NG.json
    JSON_ROOT_TEMPLATE = $(IN_TBS_JSON_TEMPLATE_DIR)\TBS_ROOT_TEMPLATE_NG.json
    Keywords_EN = tags{}.display_name
    Keywords_FR = tags{}.display_name_fr
    P-T_ABBR = $(P-T_ABBR)
    Subject_LIST = subject_tbs
    Topic_LIST = topic_tbs
    OUTPUT_LOCAL -> AttributeExposer_18
AttributeExposer_18
    ATTR_TABLE = json_file,,id,,sector,
    -> AttributeCreator_8
AttributeCreator_8
    ATTR_TABLE = SET_TO text_line_data (varchar(200)) = @Value(json_file)
    -> text_line (writer TEXTLINE_4)
text_line (writer TEXTLINE_4)
    attributes: text_line_data buffer
