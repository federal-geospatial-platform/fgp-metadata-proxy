FME workspace NT_dev2.fmw

Parameters:
- ACTIVATE_GEO = Yes
- ACTIVATE_NON_GEO = Yes
- ACTIVATE_TRANSLATION = No
- NT_READER_SELECT = No
- IN_FFS_TESTING_FILE = C:\Data\PT_Harvester\NT\out_NT_0214.ffs
- FORCED_PYCSW_URL =
- LOCAL_SOURCE_METADATA_DELTA_FINDER = Yes
- LOCAL_WRITER = Yes
- METADATA_OVERWRITE = YES   # METADATA OVERWRITE
- P-T_ABBR = NT
- IN_OUT_WORKING_DIR = C:\Data\PT_Harvester
- SAMPLE_SIZE = 0
- URL_VALIDATION = Yes
- IN_CSV_LOOKUPTABLES_DIR = $(IN_OUT_WORKING_DIR)\LOOKUP_TABLES   # Lookup Tables Directory
- IN_GMD_XML_TEMPLATE_DIR = $(IN_OUT_WORKING_DIR)\XML_TEMPLATES
- IN_TBS_JSON_TEMPLATE_DIR = $(IN_OUT_WORKING_DIR)\JSON_TEMPLATES
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- IN_CSV_LOOKUP_TABLES_DIR = $(IN_OUT_WORKING_DIR)\LOOKUP_TABLES

Writers:
- XLSXW_1: XLSXW to $(IN_OUT_WORKING_DIR)
- TEXTLINE_1: TEXTLINE to $(OUT_XML_PASSED_DIR)
- TEXTLINE_2: TEXTLINE to $(OUT_XML_FAILED_DIR)
- TEXTLINE_3: TEXTLINE to $(OUT_XML_LOCAL_DIR)
- TEXTLINE_4: TEXTLINE to $(OUT_JSON_LOCAL_DIR)
- XLSXW_2: XLSXW to $(OUT_XLS_NOTIFICATION_DIR)

Bookmark: metadata_reader
Creator_2
    GEOMTYPE = Geometry Object
    NUM = 1
    CREATED -> Tester
Tester
    BOOL_OP = OR
    COMPOSITE_TEST = 1
    TEST_CLAUSE = TEST $(NT_READER_SELECT) = Yes
    TEST_MODE = TEST
    PASSED -> NT_CATALOGUE_READER
    FAILED -> FeatureReader [INITIATOR]
Note: NT_CATALOGUE_READER must be disabled when the feature reader is activated
NT_CATALOGUE_READER
    DATA_METADATA = Yes
    DOCUMENTS_METADATA = Yes
    MAPS_METADATA = Yes
    MAP_VIEWERS_METADATA = Yes
    REPORTS_METADATA = Yes
    WMS_METADATA = Yes
    DATA -> Junction_4
    MAPS -> Junction_4
    WMS -> Junction_4
    REPORTS -> Junction_4
    DOCUMENTS -> Junction_4
    MAP_VIEWERS -> Junction_4
Junction_4
    -> AttributeExposer
FeatureReader
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> AttributeExposer

Bookmark: Rename and filter duplicate attributes
AttributeExposer
    ATTR_LIST = description,title,resource_type,resource_category,data_category,publication_date,resources{0}.url,resources{}.url,resources{}.name,resources{}.format
    -> AttributeManager_4
NT_metadata_merger
    IN_OUT_WORKING_DIR = C:\Data\PT_Harvester
    ISO_TOPIC_0_.TOPIC_VALUE = @Value(iso_topic{0}.topic_value)
    NOTES = @Value(notes)
    P-T_ABBR = NT
    RECORD_CREATE_DATE = @Value(record_create_date)
    TITLE = @Value(title)
    -> Junction_2
Junction_2
    -> UNIQUE_ID_CREATOR
Note: Unique uuid created from metadata title
UNIQUE_ID_CREATOR
    UNIQUE_ATT = @Value(title)
    -> ATTRIBUTE_UNEXPOSER_2
ATTRIBUTE_UNEXPOSER_2
    -> NT_resources_merger
NT_resources_merger
    IN_CSV_LOOKUPTABLES_DIR = $(IN_CSV_LOOKUP_TABLES_DIR)
    IN_OUT_WORKING_DIR = $(IN_OUT_WORKING_DIR)
    P-T_ABBR = $(P-T_ABBR)
    feature_type = NT_metadata_merger
    Legend_or_UserGuide_in_title -> NT_metadata_merger (writer XLSXW_1)
    -> AttributeExposer_4
NT_metadata_merger (writer XLSXW_1)
    attributes: format auto(20)

Bookmark: Rename attributes
AttributeManager_4
    ATTR_TABLE:
      REMOVE _creation_instance
      REMOVE _html_code
      REMOVE _url_error
      REMOVE _html_detail
      RENAME_SET_VALUE description > notes
      RENAME_SET_VALUE publication_date > record_publish_date = FME_CONDITIONAL:DEFAULT_VALUE'_FME_NO_OP_'BOOL_OP;OR;COMPOSITE_TEST;1;CASE_INSENSITIVE_TEST @Value(record_publish_date) CONTAINS November 2011'2011-11-01'FME_NUM_CONDITIONS2___
      RENAME_SET_VALUE data_category > iso_topic{0}.topic_value
    -> AttributeCopier
AttributeCopier
    ATTR_TABLE:
      COPY record_publish_date > record_create_date
      COPY record_publish_date > record_last_modified
    -> TestFilter

Bookmark: merge Mackenzie Valley Air Photo data and exclude Oziexplorer and CanMatrix metadata
TestFilter
    DEFAULT_VALUE = <UNFILTERED>
    TEST_LIST:
      "BOOL_OP,OR,COMPOSITE_TEST,""""""1"""""",TEST_CLAUSE,CASE_INSENSITIVE_TEST @Value(notes) CONTAINS Mackenzie Valley Air Photo Digital Orthotiles",Mackenzie Valley Orthotiles,"BOOL_OP,OR,COMPOSITE_TEST,""""""1"""""",TEST_CLAUSE,CASE_INSENSITIVE_TEST @Value(notes) CONTAINS Mackenzie Valley Air Photo Contours Data",Mackenzie Valley Contours Data,"BOOL_OP,OR,COMPOSITE_TEST,""""""1"""""",TEST_CLAUSE,CASE_INSENSITIVE_TEST @Value(notes) CONTAINS Mackenzie Valley Air Photo Digital Elevation Model Data",Mackenzie Valley DEM,"BOOL_OP,OR,COMPOSITE_TEST,""""""1 OR 2"""""",TEST_CLAUSE,CASE_INSENSITIVE_TEST @Value(resource_category) CONTAINS Oziexplorer
      CASE_INSENSITIVE_TEST @Value(title) CONTAINS CanMatrix",Oziexplorer_CanMatrix,"BOOL_OP,OR,COMPOSITE_TEST,""""""1 OR 2"""""",TEST_CLAUSE,CASE_INSENSITIVE_TEST @Value(title) CONTAINS Government of Canada
      CASE_INSENSITIVE_TEST @Value(title) CONTAINS CCOG",Government of Canada dataset
    Mackenzie Valley Orthotiles -> AttributeManager_5
    Mackenzie Valley Contours Data -> AttributeManager_6
    Mackenzie Valley DEM -> AttributeManager_7
    <UNFILTERED> -> NT_metadata_merger
AttributeManager_5
    ATTR_TABLE:
      RENAME_SET_VALUE notes > title
      SET_TO resources{0}.url = https://www.geomatics.gov.nt.ca/Downloads/Raster/MVAP%20Orthotiles/
      SET_TO resources{0}.name = Mackenzie Valley Air Photo Digital Orthotiles
      SET_TO resources{0}.format = ftp
    -> DuplicateFilter_2
AttributeManager_6
    ATTR_TABLE:
      RENAME_SET_VALUE notes > title
      SET_TO resources{0}.url = https://www.geomatics.gov.nt.ca/Downloads/Vector/MVAP%20Contours/
      SET_TO resources{0}.name = Mackenzie Valley Air Photo Contours Data
      SET_TO resources{0}.format = ftp
    -> DuplicateFilter_2
AttributeManager_7
    ATTR_TABLE:
      RENAME_SET_VALUE notes > title
      SET_TO resources{0}.url = https://www.geomatics.gov.nt.ca/Downloads/Raster/MVAP%20DEM/
      SET_TO resources{0}.name = Mackenzie Valley Air Photo Digital Elevation Model Data
      SET_TO resources{0}.format = ftp
    -> DuplicateFilter_2
DuplicateFilter_2
    INPUT_ORDERED_CHOICE = No
    KEYATTR = title
    UNIQUE -> Junction_2

Bookmark: Date conversion
AttributeExposer_4
    ATTR_LIST = record_create_date,record_publish_date,record_last_modified
    -> DateTimeConverter_2
DateTimeConverter_2
    DATETIME_ATTR = record_create_date record_last_modified record_publish_date
    OUT_FORMAT = %Y-%m-%d
    PASSTHROUGH = NO
    REPAIR_INPUT = YES
    TEST_INPUT = 1599158641521
    -> Junction_5
    <REJECTED> -> AttributeRemover_2
AttributeRemover_2
    REMOVE_ATTRS = fme_rejection_code
    -> Junction_5
Junction_5
    -> ATTRIBUTE_UNEXPOSER
ATTRIBUTE_UNEXPOSER
    -> ATTRIBUTE_VALUE_TEXT_CLEANER

Bookmark: Attributes manager
ATTRIBUTE_VALUE_TEXT_CLEANER
    -> DEFAULT_ATTRIBUTE_MAPPER_NG
DEFAULT_ATTRIBUTE_MAPPER_NG
    FEATURE_TYPE = Default_NT
    IN_CSV_LOOKUP_TABLES_DIR = $(IN_CSV_LOOKUPTABLES_DIR)
    P-T_ABBR = $(P-T_ABBR)
    -> ATTRIBUTE_MANAGER_NG
ATTRIBUTE_MANAGER_NG
    IN_YAML_TEXT:
      iso_topic{0}.topic_value:
          action: attribute_not_null
          attr2set: default_topic


      record_last_modified:
          action: attribute_not_null
          attr2set: default_record_date

      record_publish_date:
          action: attribute_not_null
          attr2set: default_record_date

      record_create_date:
          action: attribute_not_null
          attr2set: default_record_date

      notes:
          action: attribute_not_null
          attr2set: title
    -> PythonCaller_4

Bookmark: Format and resources manager and validator
Note: If format isr EsriRest or other; remove format value so that it is added in empty format mapper ng; to ensure that only valid EsriRest format are added
PythonCaller_4
    PYTHONSOURCE:
      import fme
      import fmeobjects
      from Python.FME_utils import FME_utils

      #def processFeature(feature):
      #    pass

      # Template Class Interface:
      # When using this class, make sure its name is set as the value of
      # the 'Class or Function to Process Features' transformer parameter
      def FeatureProcessor(feature):
          i=0

          max_index=FME_utils.max_index_attribute_list(feature,'resources{}.format')
          for j in range(max_index+1):
              x = feature.getAttribute('resources{%i}.format'%(j))
              if x:
               if ('REST' or 'OTHER') in x.upper():
                feature.setAttributeNullWithType('resources{%i}.format'%(j),fmeobjects.FME_ATTR_ENCODED_STRING)
              i=i+1
    PYTHONSYMBOL = FeatureProcessor
    -> EMPTY_FORMAT_MAPPER_NG [DATA_INPUT]
EMPTY_FORMAT_MAPPER_NG
    CSV_FORMAT = Format
    CSV_MIME_TYPE = Mime_type
    IN_CSV_LOOKUP_TABLES_DIR = $(IN_CSV_LOOKUPTABLES_DIR)
    P-T_ABBR = $(P-T_ABBR)
    URL_VALIDATION = $(URL_VALIDATION)
    DATA_OUTPUT -> FORMAT_VALIDATOR
    UNKNOWN_MIME_TYPE -> unknown_mine_type (writer XLSXW_1)
unknown_mine_type (writer XLSXW_1)
    attributes: id string(200), UNIQUE_ATT string(200), resource.id string(200), _unknown_mime_type string(200)
FORMAT_VALIDATOR
    -> PythonCaller_5
Note: add resources{}.language and put defaut value to: english
PythonCaller_5
    PYTHONSOURCE:
      import fme
      import fmeobjects
      from Python.FME_utils import FME_utils

      # Template Function interface:
      # When using this function, make sure its name is set as the value of
      # the 'Class or Function to Process Features' transformer parameter
      def FeatureProcessor(feature):
          i=0

          max_index=FME_utils.max_index_attribute_list(feature,'resources{}')
          for j in range(max_index+1):
              feature.setAttribute('resources{%i}.language'%(j),"english")
              i=i+1
    PYTHONSYMBOL = FeatureProcessor
    -> NT_language_manager
Note: change resources{}.language value base on a look-up table (NT_resources_language)
NT_language_manager
    IN_CSV_LOOKUP_TABLES_DIR = $(IN_CSV_LOOKUP_TABLES_DIR)
    IN_OUT_WORKING_DIR = $(IN_OUT_WORKING_DIR)
    P-T_ABBR = $(P-T_ABBR)
    feature_type = NT_resources_language
    res_url_unknown_language -> Unknown_resource_language (writer XLSXW_2)
    -> RESOURCES_VALIDATOR
RESOURCES_VALIDATOR
    -> GEO_NONE_GEO_SELECTOR
Note: Possible values for NT_resources_language: / english; french; english_and_french
Unknown_resource_language (writer XLSXW_2)
    attributes: url auto(20)

Bookmark: Geo non-geo selector
GEO_NONE_GEO_SELECTOR
    CSV_FILE_NAME = GeoSpatialValidation
    CSV_PATH = $(IN_CSV_LOOKUPTABLES_DIR)
    CSV_PROVINCE = $(P-T_ABBR)
    YAML_DIRECTIVES:
      resources{}.format:
        domain: lookup_table_format
        spatial_type: overwrite
        not_found: log
        search_type: equals
    GEOSPATIAL -> SPATIAL_TYPE_MAPPER_NG [DATA_INPUT]
    NONE_GEOSPATIAL -> MANUAL_GEOSPATIAL_SETTER_NG [DATA_INPUT]
    LOG_ERROR -> unknown_format (writer XLSXW_1)
SPATIAL_TYPE_MAPPER_NG
    FEATURE_TYPE = SpatialType_$(P-T_ABBR)
    IN_CSV_LOOKUP_TABLES_DIR = $(IN_CSV_LOOKUPTABLES_DIR)
    P-T_ABBR = $(P-T_ABBR)
    DATA_OUTPUT_FAILED -> Spatial_Type_Mapper_Failed (writer XLSXW_1)
    DATA_OUTPUT_PASSED -> TestFilter_2
Spatial_Type_Mapper_Failed (writer XLSXW_1)
    attributes: id string(20), title string(80), url string(80)
MANUAL_GEOSPATIAL_SETTER_NG
    FEATURE_TYPE = UnmappedGeoData_$(P-T_ABBR)
    IN_CSV_LOOKUP_TABLES_DIR = $(IN_CSV_LOOKUPTABLES_DIR)
    P-T_ABBR = $(P-T_ABBR)
    GEOSPATIAL -> TestFilter_2
    NON-GEOSPATIAL -> TestFilter_4
    UNMAPPED_DATA -> unmapped_data (writer XLSXW_1)
TestFilter_2
    DEFAULT_VALUE = <UNFILTERED>
    TEST_LIST = "BOOL_OP,OR,COMPOSITE_TEST,""""""1"""""",TEST_CLAUSE,CASE_INSENSITIVE_TEST @LowerCase($(ACTIVATE_GEO)) = yes",GEO_ACTIVATE
    GEO_ACTIVATE -> TestFilter_5
unmapped_data (writer XLSXW_1)
    attributes: id string(200), notes string(200), title string(200), url string(200)
TestFilter_4
    DEFAULT_VALUE = <UNFILTERED>
    TEST_LIST = "BOOL_OP,OR,COMPOSITE_TEST,""""""1"""""",TEST_CLAUSE,CASE_INSENSITIVE_TEST $(ACTIVATE_NON_GEO) = yes",ACTIVATE_NON_GEO
    ACTIVATE_NON_GEO -> TestFilter_3
unknown_format (writer XLSXW_1)
    attributes: format auto(20)

Bookmark: Samples or full content
TestFilter_5
    DEFAULT_VALUE = SAMPLES FEATURES
    TEST_LIST = "BOOL_OP,OR,COMPOSITE_TEST,""""""1"""""",TEST_CLAUSE,TEST $(SAMPLE_SIZE) = 0",ALL FEATURES
    ALL FEATURES -> Junction_8
    SAMPLES FEATURES -> Sampler_2
Sampler_2
    RATE = $(SAMPLE_SIZE)
    SAMPLE_MODE = No
    SAMPLE_TYPE_LONG = First N Features
    SAMPLED -> Junction_8

Bookmark: Geo metadata processing
Junction_8
    -> METADATA_VALUE_MAPPER_NG_2 [DATA_INPUT]

Bookmark: Metadata Value Mapping - GEO
Note: Topic (categfory)
METADATA_VALUE_MAPPER_NG_2
    ATT_TO_MAP = iso_topic{}.topic_value
    CODE_REFRESH = NO
    ENGLISH_REFRESH = YES
    ERROR_NOT_MAPPED = YES
    FEATURE_TYPE = Topic
    FRENCH_REFRESH = NO
    IN_CSV_LOOKUP_TABLES_DIR = $(IN_CSV_LOOKUPTABLES_DIR)
    P-T_ABBR = $(P-T_ABBR)
    -> METADATA_VALUE_MAPPER_NG_14 [DATA_INPUT]
Note: resources{}.language
METADATA_VALUE_MAPPER_NG_14
    ATT_TO_MAP = resources{}.language
    CODE_REFRESH = NO
    ENGLISH_REFRESH = YES
    ERROR_NOT_MAPPED = YES
    FEATURE_TYPE = TransferLang_NT
    FRENCH_REFRESH = NO
    IN_CSV_LOOKUP_TABLES_DIR = $(IN_CSV_LOOKUP_TABLES_DIR)
    P-T_ABBR = $(P-T_ABBR)
    -> METADATA_VALUE_MAPPER_NG_3 [DATA_INPUT]
Note: Role
METADATA_VALUE_MAPPER_NG_3
    ATT_TO_MAP = role
    CODE_REFRESH = YES
    ENGLISH_REFRESH = YES
    ERROR_NOT_MAPPED = YES
    FEATURE_TYPE = Role
    FRENCH_REFRESH = YES
    IN_CSV_LOOKUP_TABLES_DIR = $(IN_CSV_LOOKUPTABLES_DIR)
    P-T_ABBR = $(P-T_ABBR)
    -> METADATA_VALUE_MAPPER_NG_4 [DATA_INPUT]
Note: Update
METADATA_VALUE_MAPPER_NG_4
    ATT_TO_MAP = update_frequency
    CODE_REFRESH = YES
    ENGLISH_REFRESH = YES
    ERROR_NOT_MAPPED = YES
    FEATURE_TYPE = Update
    FRENCH_REFRESH = YES
    IN_CSV_LOOKUP_TABLES_DIR = $(IN_CSV_LOOKUPTABLES_DIR)
    P-T_ABBR = $(P-T_ABBR)
    -> METADATA_VALUE_MAPPER_NG_5 [DATA_INPUT]
Note: Progress
METADATA_VALUE_MAPPER_NG_5
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUPTABLES_DIR)
    P-T_ABBR = $(P-T_ABBR)
    -> METADATA_VALUE_MAPPER_NG_7 [DATA_INPUT]
Note: SpatialRepresentation
METADATA_VALUE_MAPPER_NG_7
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUPTABLES_DIR)
    P-T_ABBR = $(P-T_ABBR)
    -> METADATA_FORMAT_MAPPER_NG [DATA_INPUT]
Note: Format
METADATA_FORMAT_MAPPER_NG
    ATT_TO_MAP = resources{}.format
    ERROR_NOT_MAPPED = YES
    FEATURE_TYPE = Format
    IN_CSV_LOOKUP_TABLES_DIR = $(IN_CSV_LOOKUPTABLES_DIR)
    P-T_ABBR = $(P-T_ABBR)
    REAL_VALUE_REFRESH = YES
    RES_TYPE_EN_REFRESH = YES
    RES_TYPE_FR_REFRESH = YES
    -> METADATA_VALUE_MAPPER_ERROR_MANAGER
METADATA_VALUE_MAPPER_ERROR_MANAGER
    ERROR_OUTPUT -> GEO_ATTRIBUTE_MAPPING_ERRORS (writer XLSXW_1)
    DATA_OUTPUT -> AttributeExposer_5
GEO_ATTRIBUTE_MAPPING_ERRORS (writer XLSXW_1)
    attributes: error string(200), id string(200), _element_index string(200)

Bookmark: Sector management
AttributeExposer_5
    ATTR_LIST = sector
    -> StringReplacer_3
Note: Remove 'Government of Northwest Territories' from sector
StringReplacer_3
    CASE = NO
    FIND_TEXT = Government of Northwest Territories
    NO_MATCH = _FME_NO_OP_
    REGEXP = NO
    SRC_ATTRS = sector
    -> RESOURCE_NAME_UNDERSCORE_REMOVER

Bookmark: Remove all underscores from resources{}.name attributes
RESOURCE_NAME_UNDERSCORE_REMOVER
    DATA_OUTPUT -> WMS_REST_LANGUAGE_FORMATTER

Bookmark: HNAP RULES
WMS_REST_LANGUAGE_FORMATTER
    -> DUPLICATE_SERVICE_REMOVER
DUPLICATE_SERVICE_REMOVER
    -> GMD_SECTION_DATA_EXTRACTION
GMD_SECTION_DATA_EXTRACTION
    -> REMOVE_BROKEN_URL_WMS_ESRI_REST

Bookmark: Drop Broken Web Services
REMOVE_BROKEN_URL_WMS_ESRI_REST
    URL_VALIDATION = Yes
    -> AttributeCreator_3
    FAULTY_URL_OUTPUT -> MAP_SERVICE_URL_ERRORMAP (writer XLSXW_1)
MAP_SERVICE_URL_ERRORMAP (writer XLSXW_1)
    attributes: id string(200), url string(200), format string(200), _url_failure_message string(200)

Bookmark: Metadata_delta_finder
AttributeCreator_3
    ATTR_TABLE = SET_TO csw_url = $(FORCED_PYCSW_URL)
    -> AttributeExposer_13
AttributeExposer_13
    ATTR_LIST = search_criteria_pycsw
    -> METADATA_DELTA_FINDER_NG
METADATA_DELTA_FINDER_NG
    ABSTRACT_ATT_NEW = notes
    ABSTRACT_ATT_REF = MD_Metadata.identificationInfo.MD_DataIdentification.abstract.CharacterString
    CSW_FILTER = @Value(search_criteria_pycsw)
    CUSTOM_CSW_CKAN_URL = @Value(csw_url)
    DATESTAMP_ATT_NEW = record_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    METADATA_OVERWRITE = $(METADATA_OVERWRITE)
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    Statistics -> StatisticsCalculator_Summary_2
    Update -> Junction
    Insert -> Junction
    Delete -> DELETEDRECORDS (writer XLSXW_1)
StatisticsCalculator_Summary_2: Logger
    LOG_FEATURE = NONE
    MAXFEATS = 20
    MESSAGE:
      ************************
      **** Unchanged Report ****
      ************************

      @Value(_real_count) features were unchanged

      ************************
      ************************
      ************************
    SEVERITY = INFO
Junction
    -> AWS_TRANSLATE_2
DELETEDRECORDS (writer XLSXW_1)
    attributes: _timestamp string(200), id string(200)

Bookmark: AWS Translation
AWS_TRANSLATE_2
    ACTIVATE_TRANSLATION = $(ACTIVATE_TRANSLATION)
    ATTR_2_TRANSLATE = notes,title,default_keyword
    ATTR_LIST_2_TRANSLATE = resources{}.name
    MODE = English-->French
    -> XML_PUBLISHER_NG
    TRANSLATION_PROBLEM -> Translation_errors (writer XLSXW_1)
Translation_errors (writer XLSXW_1)
    attributes: id string(20), _timestamp string(20)

Bookmark: XML CREATION AND WRITING
XML_PUBLISHER_NG
    FEATURE_TYPE = Config_NT
    IN_CSV_LOOKUP_TABLES_DIR = $(IN_CSV_LOOKUPTABLES_DIR)
    LOCAL_WRITER = $(LOCAL_WRITER)
    P-T_ABBR = $(P-T_ABBR)
    TEMPLATE_GMD_CITEDRESPONSIBLEPARTY = $(IN_GMD_XML_TEMPLATE_DIR)/GMD_CITEDRESPONSIBLEPARTY.xml
    TEMPLATE_GMD_CONTACT = $(IN_GMD_XML_TEMPLATE_DIR)/GMD_CONTACT.xml
    TEMPLATE_GMD_DISTRIBUTIONFORMAT = $(IN_GMD_XML_TEMPLATE_DIR)/GMD_DISTRIBUTIONFORMAT.xml
    TEMPLATE_GMD_DISTRIBUTOR = $(IN_GMD_XML_TEMPLATE_DIR)/GMD_DISTRIBUTOR.xml
    TEMPLATE_GMD_KEYWORDS = $(IN_GMD_XML_TEMPLATE_DIR)/GMD_KEYWORDS.xml
    TEMPLATE_GMD_MDMETADATA = $(IN_GMD_XML_TEMPLATE_DIR)/GMD_MDMETADATA.xml
    TEMPLATE_GMD_REFERENCESYSTEMINFO = $(IN_GMD_XML_TEMPLATE_DIR)/GMD_REFERENCESYSTEMINFO.xml
    TEMPLATE_GMD_RESOURCEMAINTENANCE = $(IN_GMD_XML_TEMPLATE_DIR)/GMD_RESOURCEMAINTENANCE.xml
    TEMPLATE_GMD_TOPICCATEGORY = $(IN_GMD_XML_TEMPLATE_DIR)/GMD_TOPICCATEGORY.xml
    TEMPLATE_GMD_TRANSFEROPTIONS = $(IN_GMD_XML_TEMPLATE_DIR)/GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    InvalidMetadata -> invalid_metadata (writer XLSXW_1)
    UPDATE_FAILED -> text_line (writer TEXTLINE_2)
Note: Writes XML to a local folder without publishing to PyCSW, and without the PyCSW transaction headers and footers
text_line (writer TEXTLINE_3)
    attributes: text_line_data buffer
text_line (writer TEXTLINE_1)
    attributes: text_line_data buffer
text_line (writer TEXTLINE_2)
    attributes: text_line_data buffer
invalid_metadata (writer XLSXW_1)
    attributes: id auto(20)

Bookmark: Samples or full content
TestFilter_3
    DEFAULT_VALUE = SAMPLES FEATURES
    TEST_LIST = "BOOL_OP,OR,COMPOSITE_TEST,""""""1"""""",TEST_CLAUSE,TEST $(SAMPLE_SIZE) = 0",ALL FEATURES
    ALL FEATURES -> Junction_6
    SAMPLES FEATURES -> Sampler_3
Sampler_3
    RATE = $(SAMPLE_SIZE)
    SAMPLE_MODE = No
    SAMPLE_TYPE_LONG = First N Features
    SAMPLED -> Junction_6

Bookmark: Non-geo metadata processing
Junction_6
    -> METADATA_VALUE_MAPPER_NG_10 [DATA_INPUT]
Note: Adjusting update frequency value
METADATA_VALUE_MAPPER_NG_10
    ATT_TO_MAP = update_frequency
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUPTABLES_DIR)
    P-T_ABBR = $(P-T_ABBR)
    -> METADATA_FORMAT_MAPPER_NG_2 [DATA_INPUT]
Note: resources{}.format
METADATA_FORMAT_MAPPER_NG_2
    ATT_TO_MAP = resources{}.format
    ERROR_NOT_MAPPED = YES
    FEATURE_TYPE = Format_TBS
    IN_CSV_LOOKUP_TABLES_DIR = $(IN_CSV_LOOKUPTABLES_DIR)
    P-T_ABBR = $(P-T_ABBR)
    REAL_VALUE_REFRESH = YES
    RES_TYPE_EN_REFRESH = YES
    RES_TYPE_FR_REFRESH = YES
    -> METADATA_VALUE_MAPPER_NG_11 [DATA_INPUT]
Note: resources{}.language
METADATA_VALUE_MAPPER_NG_11
    ATT_TO_MAP = resources{}.language
    CODE_REFRESH = NO
    ENGLISH_REFRESH = YES
    ERROR_NOT_MAPPED = YES
    FEATURE_TYPE = TransferLang_NT_tbs
    FRENCH_REFRESH = NO
    IN_CSV_LOOKUP_TABLES_DIR = $(IN_CSV_LOOKUP_TABLES_DIR)
    P-T_ABBR = $(P-T_ABBR)
    -> AttributeExposer_7
Note: Creates list of errors found and not corrected in mapping
METADATA_VALUE_MAPPER_ERROR_MANAGER_2
    ERROR_OUTPUT -> METADATA_MAPPING_ERRORS_NON_GEO (writer XLSXW_1)
    DATA_OUTPUT -> METADATA_DELTA_FINDER_NG_2
Note: Translates specific items from English to French
AWS_TRANSLATE_3
    ACTIVATE_TRANSLATION = $(ACTIVATE_TRANSLATION)
    ATTR_2_TRANSLATE = notes,title
    ATTR_LIST_2_TRANSLATE = tags{}.value,resources{}.name
    MODE = English-->French
    -> JSON_PUBLISHER_NG
    TRANSLATION_PROBLEM -> translation_problems_NONE_GEO (writer XLSXW_1)
translation_problems_NONE_GEO (writer XLSXW_1)
    attributes: id auto(20)
METADATA_MAPPING_ERRORS_NON_GEO (writer XLSXW_1)
    attributes: error string(200), id string(200), _element_index string(200)

Bookmark: TOPICS value mapper from iso_topic{}.topic_value list attributes
AttributeExposer_7
    ATTR_LIST = iso_topic{}.topic_value
    -> ListCopier_2
ListCopier_2
    DEST_LIST = topics
    SRC_LIST = iso_topic{}
    -> METADATA_VALUE_MAPPER_NG_12 [DATA_INPUT]
METADATA_VALUE_MAPPER_NG_12
    ATT_TO_MAP = topics{}.topic_value
    CODE_REFRESH = NO
    ENGLISH_REFRESH = YES
    ERROR_NOT_MAPPED = YES
    FEATURE_TYPE = Topic_TBS
    FRENCH_REFRESH = NO
    IN_CSV_LOOKUP_TABLES_DIR = $(IN_CSV_LOOKUPTABLES_DIR)
    P-T_ABBR = $(P-T_ABBR)
    -> AttributeExposer_8
AttributeExposer_8
    ATTR_LIST = topics{}.topic_value
    -> ListDuplicateRemover
ListDuplicateRemover
    SRC_LIST = topics{}.topic_value
    -> AttributeExposer_10

Bookmark: SUBJECTS value mapper from iso_topic{}.topic_value list attributes
AttributeExposer_10
    ATTR_LIST = iso_topic{}.topic_value
    -> ListCopier_3
ListCopier_3
    DEST_LIST = subjects
    SRC_LIST = iso_topic{}
    -> METADATA_VALUE_MAPPER_NG_13 [DATA_INPUT]
METADATA_VALUE_MAPPER_NG_13
    ATT_TO_MAP = subjects{}.topic_value
    CODE_REFRESH = NO
    ENGLISH_REFRESH = YES
    ERROR_NOT_MAPPED = YES
    FEATURE_TYPE = Subject_TBS
    FRENCH_REFRESH = NO
    IN_CSV_LOOKUP_TABLES_DIR = $(IN_CSV_LOOKUPTABLES_DIR)
    P-T_ABBR = $(P-T_ABBR)
    -> AttributeExposer_9
AttributeExposer_9
    ATTR_LIST = subjects{}.topic_value
    -> ListDuplicateRemover_2
ListDuplicateRemover_2
    SRC_LIST = subjects{}.topic_value
    -> METADATA_VALUE_MAPPER_ERROR_MANAGER_2

Bookmark: metadata delta finder
METADATA_DELTA_FINDER_NG_2
    ABSTRACT_ATT_NEW = notes
    ABSTRACT_ATT_REF = notes_translated.en
    DATESTAMP_ATT_NEW = record_last_modified
    DATESTAMP_ATT_REF = federated_date_modified
    ID_ATT_NEW = id
    ID_ATT_REF = id
    LOCAL_SOURCE = Yes
    LOCAL_SOURCE_DIR = $(OUT_JSON_LOCAL_DIR)
    LOCAL_SOURCE_FORMAT = JSON
    METADATA_OVERWRITE = $(METADATA_OVERWRITE)
    RES_FORMAT_ATT_NEW = resources{}.format
    RES_FORMAT_ATT_REF = resources{}.format
    RES_NAME_ATT_NEW = resources{}.name
    RES_NAME_ATT_REF = resources{}.name_translated.en
    RES_URL_ATT_NEW = resources{}.url
    RES_URL_ATT_REF = resources{}.url
    TITLE_ATT_NEW = title
    TITLE_ATT_REF = title_translated.en
    Statistics -> StatisticsCalculator_Summary_3
    Update -> Junction_7
    Insert -> Junction_7
    Delete -> DELETED_RECORDS_NONE_GEO (writer XLSXW_1)
Note: Log statistics
StatisticsCalculator_Summary_3: Logger
    LOG_FEATURE = NONE
    MAXFEATS = 20
    MESSAGE:
      ************************
      **** NoneGeo Features: Unchanged Report ****
      ************************

      @Value(_real_count) features were unchanged

      ************************
      ************************
      ************************
    SEVERITY = INFO
Junction_7
    -> AWS_TRANSLATE_3
Note: Log deleted features
DELETED_RECORDS_NONE_GEO (writer XLSXW_1)
    attributes: id auto(20)

Bookmark: JSON creation and writing
JSON_PUBLISHER_NG
    FEATURE_TYPE = JSON_CONFIG_$(P-T_ABBR)
    IN_CSV_LOOKUP_TABLES_DIR = $(IN_CSV_LOOKUPTABLES_DIR)
    JSON_RESOURCE_TEMPLATE = $(IN_TBS_JSON_TEMPLATE_DIR)\TBS_RESOURCES_TEMPLATE_NG.json
    JSON_ROOT_TEMPLATE = $(IN_TBS_JSON_TEMPLATE_DIR)\TBS_ROOT_TEMPLATE_NG.json
    Keywords_EN = tags{}.value_en
    Keywords_FR = tags{}.value_fr
    P-T_ABBR = $(P-T_ABBR)
    Subject_LIST = subjects{}.topic_value
    Topic_LIST = topics{}.topic_value
    OUTPUT_LOCAL -> AttributeExposer_11
AttributeExposer_11
    ATTR_LIST = json_file,id
    -> AttributeCreator_6
AttributeCreator_6
    ATTR_TABLE = SET_TO text_line_data = @Value(json_file)
    -> text_line (writer TEXTLINE_4)
text_line (writer TEXTLINE_4)
    attributes: text_line_data buffer

FME custom transformer METADATA_DELTA_FINDER_NG
Description 
This custom transformer identify the type of transaction (insert, update, delete, no change) for each metadata records read from the province.  In order to determine the type of transaction, the metadata reference records (from the PYCSW or from a Local Source) are read and are compared using a hash function (see note) with the records from the province (new records). There are four possible types of transaction:
Insert: A record read from the province is not found in the reference records (PYCSW or Local Source)
Update: A record read from the province is found in the reference records (PYCSW or Local Source) but with one or more differences in the content of the metadata record
Delete: A record is present in the reference record (PYCSW or Local Source) but not in the province
No change: A record read from the province is identical (all fields are the same) to a record found in the reference records (PYCSW or Local Source).
Input Ports 
Input: The input metadata records from the province.
Output Ports 
Statistics: The number of unchanged features to pass to the Logger Parameters transformers;
No Change: Features that were not modified in regards with the content of the referenced records (PYCSW or Local Source);
Update: Features that were updated (modified feature) in regards with the content of the referenced records (PYCSW or Local Source);
Insert: Features to insert (new feature) in regards to the content of the referenced records (PYCSW or Local Source);
Delete: Features to delete (feature removed) in regards to the content of the referenced records (PYCSW or Local Source).
Note: If the parameter METADATA_OVERWRITE is set to YES, all the unchanged features are flag as Insert.
Parameters 
ABSTRACT_ATT_NEW: Name of the attribute containing the description of the abstract for the new record from the province
ABSTRACT_ATT_REF: Name of the attribute containing the description of the abstract for the reference record (PYCSW or Local source)
DATESTAMP_ATT_NEW: Name of the attribute containing the date stamp for the new record from the province
DATESTAMP_ATT_REF: Name of the attribute containing the date stamp for the reference record (PYCSW or Local source)
ID_ATT_NEW: Name of the attribute containing the identification for the new record from the province
ID_ATT_REF: Name of the attribute containing the identification for the reference record (PYCSW or Local Source)
RES_NAME_ATT_NEW: Name of the attribute containing the resource name for the new record from the province
RES_NAME_ATT_REF: Name of the attribute containing the resource name for the reference record (PYCSW or Local Source)
RES_URL_ATT_NEW: Name of the attribute containing the resource URL for the new record from the province
RES_URL_ATT_REF: Name of the attribute containing the resource URL for the reference record (PYCSW or Local Source)
TITLE_ATT_NEW: Name of the attribute containing the title for the new record from the province
TITLE_ATT_REF: Name of the attribute containing the title for the reference record (PYCSW or Local Source)
CUSTOM_CSW_CKAN_URL: Name of the attribute containing the URL of the PYCSW server
CKAN_FILTER: Name of the attribute used to filter CKAN records in the PyCSW server
LOCAL_SOURCE: Flag indicating if the metadata record for identifying the action (insert, update, delete, no change) must be read from the PYCSW server or are stored on the local system. Can take 2 values: YES: read the records from the PYCSW; NO read the records from the Local source.
LOCAL_SOURCE_FORMAT: Flag indicating the type of metadata format format to process.  Can take 2 values: XML to process XML format records (geospatial data); JSON to process JSON format records (non geospatial data)
LOCAL_SOURCE_DIR: Name of the directory containing the local source of the referenced records. Used if LOCAL_SOURCE parameters is set to NO
CSW_FILTER: Name of the attribute used to filter CSW records in the PyCSW server in order to select records from one province only
RES_FORMAT_ATT_NEW: Name of the attribute containing the format of the resource for the new record from the province
RES_FORMAT_ATT_REF: Name of the attribute containing the format of the resource for the reference record (PYCSW or Local Source)
METADATA_OVERWRITE: Flag indicating to overwrite or not the metadata. Can take 2 values: YES: Overwrite the content of the PyCSW server; NO: Do not overwrite the content of the PyCSW server; 
Note:
A hash function using strategic attributes is used to determine if 2 metadata records (features) are the same.

Parameters:
- ABSTRACT_ATT_NEW = notes
- ABSTRACT_ATT_REF = MD_Metadata.identificationInfo.MD_DataIdentification.abstract.CharacterString
- DATESTAMP_ATT_NEW = record_last_modified
- DATESTAMP_ATT_REF =   # MD_Metadata.dateStamp.Date DATESTAMP_ATT_REF
- ID_ATT_NEW = id
- ID_ATT_REF =   # MD_Metadata.fileIdentifier.CharacterString ID_ATT_REF
- RES_NAME_ATT_NEW = resources{}.name
- RES_NAME_ATT_REF =
- RES_URL_ATT_NEW = resources{}.url
- RES_URL_ATT_REF =
- TITLE_ATT_NEW = title
- TITLE_ATT_REF =
- CUSTOM_CSW_CKAN_URL =
- CKAN_FILTER =   # fq=collection:fgp CKAN_FILTER
- LOCAL_SOURCE =
- LOCAL_SOURCE_FORMAT = XML
- LOCAL_SOURCE_DIR =
- CSW_FILTER =
- RES_FORMAT_ATT_NEW =
- RES_FORMAT_ATT_REF =
- METADATA_OVERWRITE = YES

INPUT (input)
    -> Sampler
    -> CreatingHashKeyFromAttributes [Cloner_Input]
No_Change (output)
Update (output)
Insert (output)
Delete (output)
Statistics (output)

Bookmark: Extract metadta records from PYCSW or Local Source as reference records
Note: Only one feature needed
Sampler
    RATE = 1
    SAMPLE_MODE = No
    SAMPLE_TYPE_LONG = First N Features
    SAMPLED -> TestFilter_2
Note: Using CatalogueReader transformer to readl from PYCSW
TestFilter_2
    DEFAULT_VALUE = <UNFILTERED>
    TEST_LIST = "BOOL_OP,OR,COMPOSITE_TEST,""""""1"""""",TEST_CLAUSE,TEST @UpperCase($(LOCAL_SOURCE)) = NO",PYCSW,"BOOL_OP,OR,COMPOSITE_TEST,""""""1"""""",TEST_CLAUSE,TEST @UpperCase($(LOCAL_SOURCE)) = YES",Local Source
    PYCSW -> Catalogue_Reader
    Local Source -> FeatureReader [INITIATOR]
Catalogue_Reader: Catalogue Reader
    CKAN_FILTER = $(CKAN_FILTER)
    CSW_ANYTEXT_FILTER = $(CSW_FILTER)
    CUSTOM_CSW_LIST_NAME = MD_Metadata{}
    CUSTOM_CSW_SCHEMA = http://www.isotc211.org/2005/gmd
    CUSTOM_CSW_VERSION = 2.0.2
    CUSTOM_URL = $(CUSTOM_CSW_CKAN_URL)
    CUSTOM_URL_CSW_TYPENAMES = gmd:MD_Metadata
    SOURCE_URL = Manuel
    Résultats -> AttributeExposer_3
AttributeExposer_3
    ATTR_LIST = MD_Metadata.fileIdentifier.CharacterString
    -> CreateHashingKey_XML_NAP [Cloner_Input]
FeatureReader
    ATTR_ACCUM_MODE = Only Use Result
    COMBINE_GEOM = Use Result
    DATASET = $(LOCAL_SOURCE_DIR)
    FORMAT = PATH
    OUTPUT_FEATURES_DISPLAY = Schema and Data Features
    PATH_GLOB_PATTERN = *
    PATH_NO_EMPTY_PROPERTIES = YES
    PATH_RECURSE_DIRECTORIES = NO
    PATH_RETRIEVE_FILE_PROPERTIES = NO
    PATH_TYPE = ANY
    <OTHER> -> AttributeExposer_4
AttributeExposer_4
    ATTR_LIST = path_windows,path_extension
    -> TestFilter
TestFilter
    DEFAULT_VALUE = <UNFILTERED>
    TEST_LIST:
      "BOOL_OP,AND,COMPOSITE_TEST,""""""1 AND 2"""""",TEST_CLAUSE,TEST $(LOCAL_SOURCE_FORMAT) = XML
      TEST @UpperCase(@Value(path_extension)) = XML",XML FORMAT,"BOOL_OP,AND,COMPOSITE_TEST,""""""1 AND 2"""""",TEST_CLAUSE,TEST $(LOCAL_SOURCE_FORMAT) = JSON
      TEST @UpperCase(@Value(path_extension)) = JSON",JSON FORMAT
    XML FORMAT -> XMLFlattener
    JSON FORMAT -> JSONFlattener
    <UNFILTERED> -> Terminator
XMLFlattener
    EMBEDDED_EXPRESSIONS = MD_Metadata
    FEATURE_TYPES_FORMAT_NAME = XML
    FILE_XML = @Value(path_windows)
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    XML_SOURCE_TYPE = XML file
    -> BulkAttributeRenamer
    <REJECTED> -> Terminator_2
BulkAttributeRenamer
    ATTRCHOICE = All Attributes
    MODE_CHOICE = RENAME
    PATTERN_ACTION_DISP = ADDPREFIX
    REPLACE_STR = MD_Metadata.
    -> CreateHashingKey_XML_NAP [Cloner_Input]
Terminator_2
    MESSAGE:
      XML Flattener rejected
      Translation Terminated
JSONFlattener
    ERROR_LIST_ATTR = _json_error
    FILEPATH_OR_URL = @Value(path_windows)
    READ_FROM_FILE = YES
    RECURSIVE = Yes
    -> CreateHashingKey_XML_NAP [Cloner_Input]
    <REJECTED> -> Terminator_3
Note: Crreating hash key for PYCSW or local source (reference) metadata records based on an inhouse hashing models. Attributes name come from parameters
CreateHashingKey_XML_NAP: CreatingHashKeyFromAttributes
    Abstract_ATT = $(ABSTRACT_ATT_REF)
    DateStamp_ATT = $(DATESTAMP_ATT_REF)
    ID_ATT = $(ID_ATT_REF)
    Resources_Format_ATT = $(RES_FORMAT_ATT_REF)
    Resources_Name_ATT = $(RES_NAME_ATT_REF)
    Resources_URL_ATT = $(RES_URL_ATT_REF)
    Title_ATT = $(TITLE_ATT_REF)
    AttributeKeeper_Output -> AttributeExposer_2
Terminator_3
    MESSAGE = Translation Terminated
Terminator
    MESSAGE:
      Invalid condition for parameter LOCAL_SOURCE_FORMAT ($(LOCAL_SOURCE_FORMAT))
      Translation Terminated

Bookmark: Compare reference records with new records from the province
AttributeExposer_2
    ATTR_LIST = _global_hashkey
    -> AttributeCreator_2
AttributeCreator_2
    ATTR_TABLE:
      SET_TO _hash_pycsw = @Value(_global_hashkey)
      SET_TO id = @Value($(ID_ATT_REF))
      SET_TO _type = A
    -> Sorter
Note: Crreating hash key for provincial portal metadata records based on in house models. Attributes name come from parameters
CreatingHashKeyFromAttributes
    Abstract_ATT = $(ABSTRACT_ATT_NEW)
    DateStamp_ATT = $(DATESTAMP_ATT_NEW)
    ID_ATT = $(ID_ATT_NEW)
    Resources_Format_ATT = $(RES_FORMAT_ATT_NEW)
    Resources_Name_ATT = $(RES_NAME_ATT_NEW)
    Resources_URL_ATT = $(RES_URL_ATT_NEW)
    Title_ATT = $(TITLE_ATT_NEW)
    AttributeKeeper_Output -> AttributeExposer
AttributeExposer
    ATTR_LIST = _global_hashkey,id
    -> AttributeCreator
AttributeCreator
    ATTR_TABLE:
      SET_TO _hash_prov = @Value(_global_hashkey)
      SET_TO _type = B
    -> Sorter
Note: Order all the reference records before the new records to process
Sorter
    SORT_PARM = _type ALPHA ASCENDING
    SORTED -> PythonCaller
Note: Identifying Insert/Update/Delete/ No change
PythonCaller
    NEW_ATTRIBUTES = PyCSW_Transaction
    PYTHONSOURCE:
      import fme
      import fmeobjects
      # Template Function interface:
      # When using this function, make sure its name is set as the value of
      # the 'Class or Function to Process Features' transformer parameter

      class FeatureProcessor(object):
          def __init__(self):
              # Create structure
              self.dictPyCSW = {}
              self.listProv = []

          def input(self,feature):
              # _type A or B (A=PYCSW, B=Prov
              # All the the PYCSW records are read first (sorted before)
              if feature.getAttribute('_type')=='A':
                  #Adding the PyCSW records in the dictionnary
                  self.dictPyCSW[feature.getAttribute('id')]={'hash':feature.getAttribute('_hash_pycsw')}

              else:
                  # Check for the type of transaction
                  id=feature.getAttribute('id')
                  if id in  self.dictPyCSW:
                      # id is present
                      if feature.getAttribute('_hash_prov')==self.dictPyCSW[id]['hash']:
                          feature.setAttribute('PyCSW_Transaction','No change')
                      else:
                          feature.setAttribute('PyCSW_Transaction','Update')
                  else:
                      # id is not present
                      feature.setAttribute('PyCSW_Transaction','Insert')

                  self.listProv.append(id)
                  self.pyoutput(feature)

          def close(self):
              for key in self.dictPyCSW:
                  if key not in self.listProv:
                      # id is in the PYCSW and not in the province list (deleted record)
                      newFeature = fmeobjects.FMEFeature()
                      newFeature.setAttribute('PyCSW_Transaction','Delete')
                      newFeature.setAttribute('id', key)
                      self.pyoutput(newFeature)
    PYTHONSYMBOL = FeatureProcessor
    -> AttributeExposer_5

Bookmark: Filter the features based on the type of transaction
Note: Exposes PyCSW_Transaction attribute
AttributeExposer_5
    ATTR_LIST = PyCSW_Transaction,id
    -> AttributeFilter
Note: Filters items by PyCSW transaction type
AttributeFilter
    ATTR_NAME = PyCSW_Transaction
    ATTR_VALUES = <Empty>,<Missing>,<Null>,<Unfiltered>,No change,Update,Insert,Delete
    <EMPTY> -> Junction
    <MISSING> -> Junction
    <NULL> -> Junction
    <UNFILTERED> -> Junction
    No change -> TestFilter_3
    Update -> Junction_2
    Insert -> ATTRIBUTE_UNEXPOSER_3
    Delete -> ATTRIBUTE_UNEXPOSER_4
Junction
    -> Terminator_4
Terminator_4
    MESSAGE = ERROR: Unknown _event value from Metadata_Delta
TestFilter_3
    DEFAULT_VALUE = No Overwrite
    TEST_LIST = "BOOL_OP,OR,COMPOSITE_TEST,""""""1"""""",TEST_CLAUSE,TEST @UpperCase($(METADATA_OVERWRITE)) = YES",Overwrite
    Overwrite -> AttributeCreator_5
    No Overwrite -> StatisticsCalculator_2
    No Overwrite -> No_Change (output)
Note: Reset to update
AttributeCreator_5
    ATTR_TABLE = SET_TO PyCSW_Transaction = Update
    -> Junction_2
Junction_2
    -> ATTRIBUTE_UNEXPOSER_2
Note: Unexpose all attributes for performance and readability
ATTRIBUTE_UNEXPOSER_2
    -> Update (output)
Note: Unexpose all attributes for performance and readability
ATTRIBUTE_UNEXPOSER_3
    -> Insert (output)
Note: Unexpose all attributes for performance and readability
ATTRIBUTE_UNEXPOSER_4
    -> Delete (output)
Creator_3
    GEOMTYPE = Geometry Object
    NUM = 1
    CREATED -> StatisticsCalculator_2
Note: Calculate statistics
StatisticsCalculator_2
    COMPUTE_HISTOGRAM = NO
    COUNT_ATTR = _count
    PREPEND_ATTR_NAME_CHOICE = For multiple results only
    STATS_ATTRS = id
    SUMMARY -> AttributeCreator_6
AttributeCreator_6
    ATTR_TABLE = SET_TO _real_count = @Evaluate(@Value(_count)-1)
    -> Statistics (output)

FME custom transformer CreatingHashKeyFromAttributes
Description 
This custom transformer is using a hashing function in order to create a unique identifier (value) for a metadata records.  Strategic fields (attributes) from the metadata records are used in the hashing function in order to create a very representative unique value for each metadata records.
Input Ports 
Input: The input metadata records to process.
Output Ports 
OUTPUT: The output metdata records with an attribute representing a unique hash value for the metadata record (_global_hashkey)
Parameters 
ID_ATT: Name of the attribute containing the identification of the metadata record
DATESTAMP_ATT: Name of the attribute containing the date stamp of the metadata record 
RES_URL_ATT: Name of the attribute containing the resource URL of the metadata record
RES_NAME_ATT: Name of the attribute containing the resource name of the metadata record
TITLE_ATT: Name of the attribute containing the title of the metadata record
ABSTRACT_ATT: Name of the attribute containing the description of the abstract of the metadata record
RES_FORMAT_ATT: Name of the attribute containing the format of the resource of the metadatarecord

Parameters:
- ID_ATT =
- DateStamp_ATT =
- Resources_URL_ATT =
- Resources_Name_ATT =
- Title_ATT =
- Abstract_ATT =
- Resources_Format_ATT =

Cloner_Input (input)
    -> AttributeCreator_4
AttributeKeeper_Output (output)

Bookmark: Creating hasing key to evaluate value
AttributeCreator_4
    ATTR_TABLE:
      SET_TO ID_ATT = $(ID_ATT)
      SET_TO TITLE_ATT = $(Title_ATT)
      SET_TO ABSTRACT_ATT = $(Abstract_ATT)
      SET_TO DATESTAMP_ATT = $(DateStamp_ATT)
      SET_TO RESOURCES_NAME_ATT = $(Resources_Name_ATT)
      SET_TO RESOURCES_URL_ATT = $(Resources_URL_ATT)
      SET_TO RESOURCES_FORMAT_ATT = $(Resources_Format_ATT)
    -> PythonCaller_2
Note: Creating hash key
PythonCaller_2
    PYTHONSOURCE:
      import fme
      import fmeobjects
      import hashlib
      # Template Function interface:
      # When using this function, make sure its name is set as the value of
      # the 'Class or Function to Process Features' transformer parameter

      class FeatureProcessor(object):
          def __init__(self):
              pass
          def input(self,feature):
              # Create the hash value for the ID
              id=feature.getAttribute(feature.getAttribute('ID_ATT')).replace('\t',' ').lstrip(' ').rstrip(' ')
              id_haskey=hashlib.sha256(id.encode('utf-8')).hexdigest()
      #        feature.setAttribute('_hash_id',id_haskey)

              # Create the hash value for the Date stamp
              datestamp=feature.getAttribute(feature.getAttribute('DATESTAMP_ATT')).replace('\t',' ').lstrip(' ').rstrip(' ')
              datestamp_haskey=hashlib.sha256(datestamp.encode('utf-8')).hexdigest()
      #        feature.setAttribute('_hash_datestamp',datestamp_haskey)

              # Create the hash value for the Abstract
              abstract=feature.getAttribute(feature.getAttribute('ABSTRACT_ATT')).replace('\n', ' ').replace('\r', '').replace('\t',' ').lstrip(' ').rstrip(' ')
              abstract_haskey=hashlib.sha256(abstract.encode('utf-8')).hexdigest()
      #        feature.setAttribute('_hash_abstract',abstract_haskey)

              # Create the hash value for the Title
              title=feature.getAttribute(feature.getAttribute('TITLE_ATT')).replace('\n', ' ').replace('\r', '').replace('\t',' ').lstrip(' ').rstrip(' ')
              title_haskey=hashlib.sha256(title.encode('utf-8')).hexdigest()
      #        feature.setAttribute('_hash_title',title_haskey)

              ## Create the hash value for the esources URL
              res_url=feature.getAttribute(feature.getAttribute('RESOURCES_URL_ATT'))
              url_hash=[]
              if res_url:
                  # Loop over each resources URL if it is a list
                  for url in res_url:
                      url_hash.append(hashlib.sha256(url.lstrip(' ').rstrip(' ').encode('utf-8')).hexdigest())

                  if len(url_hash)>1:
                      url_hash.sort()
                      url_hash=hashlib.sha256(''.join(url_hash).encode('utf-8')).hexdigest()
                  else:
                      url_hash=''.join(url_hash)
              else:
                  # It's not a list
                  res_url=feature.getAttribute(feature.getAttribute('RESOURCES_URL_ATT').replace('{}',''))
                  url_hash=hashlib.sha256(res_url.encode('utf-8')).hexdigest()
      #        feature.setAttribute('_hash_url',url_hash)

              # Create the hash value for the Resource_name
              res_name=feature.getAttribute(feature.getAttribute('RESOURCES_NAME_ATT'))
              name_hash=[]
              if res_name:
                  # Loop over each resources name if it is a list
                  for name in res_name:
                      name_hash.append(hashlib.sha256(name.replace('\t',' ').lstrip(' ').rstrip(' ').encode('utf-8')).hexdigest())

                  if len(name_hash)>1:
                      name_hash.sort()
                      name_hash=hashlib.sha256(''.join(name_hash).encode('utf-8')).hexdigest()
                  else:
                      name_hash=''.join(name_hash)
              else:
                  # It is not a list
                  res_name=feature.getAttribute(feature.getAttribute('RESOURCES_NAME_ATT').replace('{}',''))
                  name_hash=hashlib.sha256(res_name.encode('utf-8')).hexdigest()
      #        feature.setAttribute('_hash_name',name_hash)

              # Create the hash value for the Resource_format
              if feature.getAttribute('RESOURCES_FORMAT_ATT'):
                  res_format=feature.getAttribute(feature.getAttribute('RESOURCES_FORMAT_ATT'))
                  format_hash=[]
                  if res_format:
                      for format in res_format:
                          format_hash.append(hashlib.sha256(format.replace('\t',' ').lstrip(' ').rstrip(' ').encode('utf-8')).hexdigest())

                      if len(format_hash)>1:
                          format_hash.sort()
                          format_hash=hashlib.sha256(''.join(format_hash).encode('utf-8')).hexdigest()
                      else:
                          format_hash=''.join(format_hash)

                  else:
                      res_format=feature.getAttribute(feature.getAttribute('RESOURCES_FORMAT_ATT').replace('{}',''))
                      format_hash=hashlib.sha256(res_format.encode('utf-8')).hexdigest()

      #            feature.setAttribute('_hash_format',format_hash)
              else:
                  format_hash='not_validated'
      #            feature.setAttribute('_hash_format',format_hash)

              # Create the glabal hash value by using all the intermediate hash values
              global_string='%s%s%s%s%s%s%s'%(id_haskey,datestamp_haskey,abstract_haskey,title_haskey,url_hash,name_hash,format_hash)
              hashkey=hashlib.sha256(global_string.encode('utf-8'))
              feature.setAttribute('_global_hashkey',hashkey.hexdigest())

              self.pyoutput(feature)
          def close(self):
              pass
    PYTHONSYMBOL = FeatureProcessor
    -> AttributeRemover
AttributeRemover
    REMOVE_ATTRS = RESOURCES_NAME_ATT,RESOURCES_URL_ATT,ID_ATT,DATESTAMP_ATT,ABSTRACT_ATT,TITLE_ATT
    -> AttributeKeeper_Output (output)
