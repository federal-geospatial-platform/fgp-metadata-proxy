FME workspace export_pycsw.fmw

Parameters:
- OUT_XML_DIR =
- PYCSW_URL =
- PROVIDER =
- IN_LOOKUPTABLE_DIR = $(FME_SHAREDRESOURCE_DATA)/PT_Harvester/LOOKUP_TABLES

Writers:
- TEXTLINE_1: TEXTLINE to $(OUT_XML_DIR)

Creator
    GEOMTYPE = Geometry Object
    NUM = 1
    CREATED -> Tester
Tester
    BOOL_OP = OR
    TEST_CLAUSE = CASE_INSENSITIVE_TEST $(PROVIDER) = ALL
    TEST_MODE = CASE_INSENSITIVE_TEST
    PASSED -> AttributeCreator
    FAILED -> AttributeCreator_4
AttributeCreator
    ATTR_TABLE:
      SET_TO _csw_constraint_language (varchar(200)) = FILTER
      SET_TO _csw_list_name (varchar(200)) = MD_Metadata{}
      SET_TO _csw_output_schema (varchar(200)) = http://www.isotc211.org/2005/gmd
      SET_TO _csw_typenames (varchar(200)) = gmd:MD_Metadata
      SET_TO _csw_version (varchar(200)) = 2.0.2
      SET_TO root_url (varchar(200)) = $(PYCSW_URL)
      SET_TO _type_requete (varchar(200)) = CSW-AllRecords
      SET_TO _id (varchar(200))
    -> PythonCaller_2
AttributeCreator_4
    ATTR_TABLE = SET_TO path (varchar(200)) = $(IN_LOOKUPTABLE_DIR)\$(PROVIDER)\Default_$(PROVIDER).csv
    -> FeatureReader [INITIATOR]
FeatureReader
    ATTR_ACCUM_MODE = Only Use Result
    CLIP_TO_ENVELOPE = NO
    COMBINE_GEOM = Use Result
    CSV2_CASE_SENSITIVE_FIELD_NAMES = Yes
    CSV2_CHUNK_SIZE = 100000
    CSV2_DATA_START_LINE = 2
    CSV2_DELIMITER = ,
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 10000
    CSV2_SCAN_TYPES = Yes
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = @Value(path)
    FORMAT = CSV2
    INITIATOR_FIRST_OUTPUT = default
    INTERACT = NONE
    ORDER_RESULTS = No
    OUTPUT_ADD_SCHEMA_ATTRIBUTES = NO
    OUTPUT_FEATURES_DISPLAY = Schema and Data Features
    <OTHER> -> AttributeExposer_2
AttributeExposer_2
    ATTR_TABLE = default_key,,default_value,
    -> Tester_2
Tester_2
    BOOL_OP = OR
    TEST_CLAUSE = TEST @Value(default_key) = search_criteria_pycsw
    TEST_MODE = TEST
    PASSED -> AttributeCreator_3
AttributeCreator_3
    ATTR_TABLE:
      SET_TO _csw_constraint_language (varchar(200)) = FILTER
      SET_TO _csw_list_name (varchar(200)) = MD_Metadata{}
      SET_TO _csw_output_schema (varchar(200)) = http://www.isotc211.org/2005/gmd
      SET_TO _csw_typenames (varchar(200)) = gmd:MD_Metadata
      SET_TO _csw_version (varchar(200)) = 2.0.2
      SET_TO root_url (varchar(200)) = $(PYCSW_URL)
      SET_TO _type_requete (varchar(200)) = CSW-AllRecords
      SET_TO _id (varchar(200))
      SET_TO _csw_constraint (varchar(200)) = apiso%3AAnyText%20like%20@Value(default_value)
      SET_TO _csw_constraint_language (varchar(200)) = CQL_TEXT
    -> PythonCaller_2
Note: HTTP call for reading the CSW server and retreive the JSON records
PythonCaller_2
    NEW_ATTRIBUTES = _response_body buffer _status_code buffer _status_code_description buffer
    PYTHONSOURCE = from Python.Catalogue_Reader import ManageHttpCall
    PYTHONSYMBOL = ManageHttpCall
    -> XMLFragmenter
XMLFragmenter
    ATTRIBUTE_XML = _response_body
    DISABLE_EXTERNAL_ENTITY_PROCESSING = Yes
    EMBEDDED_EXPRESSIONS = gmd:MD_Metadata
    ENTITY_RESOLVER = Yes
    FEATURE_TYPES_FORMAT_NAME = XML
    IGNORE_DATASET_EXTERNAL_DTD = No
    MERGE_ATTRS = No
    REJECT_FEATURES_WITH_NO_FRAGMENTS = YES
    XML_SOURCE_TYPE = xml_attr
    FRAGMENTS -> XMLFlattener
XMLFlattener
    ATTRIBUTE_XML = xml_fragment
    DISABLE_EXTERNAL_ENTITY_PROCESSING = Yes
    EMBEDDED_EXPRESSIONS = gmd:fileIdentifier
    ENTITY_RESOLVER = Yes
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    IGNORE_DATASET_EXTERNAL_DTD = No
    XML_SOURCE_TYPE = xml_attr
    -> AttributeExposer
AttributeExposer
    ATTR_TABLE = CharacterString,
    -> AttributeSplitter
AttributeSplitter
    ATTR_NAME = xml_fragment
    DELIMITER = <gmd:fileIdentifier>
    DROP_EMPTY_PARTS = NO
    LIST_NAME = _list
    TRIM_TYPE = BOTH
    -> AttributeCreator_2
AttributeCreator_2
    ATTR_TABLE:
      SET_TO text_line_data (varchar(200)) = <?xml version="1.0" encoding="UTF-8"?>
        <gmd:MD_Metadata xmlns:xsi="http://www.w3.org/2001/XMLSchema-instance" xmlns:gml="http://www.opengis.net/gml/3.2" xmlns:gfc="http://www.isotc211.org/2005/gfc" xmlns:gts="http://www.isotc211.org/2005/gts" xmlns:gss="http://www.isotc211.org/2005/gss" xmlns:xlink="http://www.w3.org/1999/xlink" xmlns:gmx="http://www.isotc211.org/2005/gmx" xmlns:gsr="http://www.isotc211.org/2005/gsr" xmlns:gco="http://www.isotc211.org/2005/gco" xmlns:gmi="http://www.isotc211.org/2005/gmi" xmlns:srv="http://www.isotc211.org/2005/srv" xmlns:geonet="http://www.fao.org/geonetwork" xmlns:gmd="http://www.isotc211.org/2005/gmd" xmlns="http://www.isotc211.org/2005/gmd" xsi:schemaLocation="http://www.isotc211.org/2005/gmd http://nap.geogratis.gc.ca/metadata/tools/schemas/metadata/can-cgsb-171.100-2009-a/gmd/gmd.xsd http://www.isotc211.org/2005/srv http://nap.geogratis.gc.ca/metadata/tools/schemas/metadata/can-cgsb-171.100-2009-a/srv/srv.xsd http://www.geconnections.org/nap/napMetadataTools/napXsd/napm http://nap.geogratis.gc.ca/metadata/tools/schemas/metadata/can-cgsb-171.100-2009-a/napm/napm.xsd">
        			<gmd:fileIdentifier>
        				@Value(_list{1})
    -> text_line (writer TEXTLINE_1)
text_line (writer TEXTLINE_1)
    attributes: text_line_data buffer
