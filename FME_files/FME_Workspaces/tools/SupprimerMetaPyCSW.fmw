FME workspace SupprimerMetaPyCSW.fmw

Parameters:
- UUID_TO_DELETE = ALL
- CSW_URL =
- LOG_FILE =   # Log File
- XML_FILE =
- TEXT_FILE =
- CSW_ANYTEXT_FILTER =

Creator
    GEOMTYPE = Geometry Object
    NUM = 1
    CREATED -> TestFilter
TestFilter
    DEFAULT_VALUE = <UNFILTERED>
    PASSED_TEST_GROUP_OUTPUT = FIRST
    TEST_LIST = "BOOL_OP,OR,COMPOSITE_TEST,""""""1"""""",TEST_CLAUSE,TEST @LowerCase($(UUID_TO_DELETE)) = all",ALL,"BOOL_OP,OR,COMPOSITE_TEST,""""""1"""""",TEST_CLAUSE,TEST @LowerCase($(UUID_TO_DELETE)) = xml_file",XML_FILE,"BOOL_OP,OR,COMPOSITE_TEST,""""""1"""""",TEST_CLAUSE,CASE_INSENSITIVE_TEST $(UUID_TO_DELETE) = TEXT_FILE_CONTENT",TEXT_FILE_CONTENT
    ALL -> Catalogue_Reader
    XML_FILE -> FeatureReader [INITIATOR]
    TEXT_FILE_CONTENT -> FeatureReader_2 [INITIATOR]
    <UNFILTERED> -> AttributeCreator
Catalogue_Reader: Catalogue Reader
    CSW_ANYTEXT_FILTER = $(CSW_ANYTEXT_FILTER)
    CUSTOM_CSW_LIST_NAME = MD_Metadata{}
    CUSTOM_CSW_SCHEMA = http://www.isotc211.org/2005/gmd
    CUSTOM_CSW_VERSION = 2.0.2
    CUSTOM_URL = $(CSW_URL)
    CUSTOM_URL_CSW_TYPENAMES = gmd:MD_Metadata
    SOURCE_URL = Manuel
    Résultats -> AttributeExposer
FeatureReader
    ATTR_ACCUM_MODE = Only Use Result
    COMBINE_GEOM = Use Result
    DATASET = $(XML_FILE)
    FEATURETYPES = text_line
    FORMAT = TEXTLINE
    INITIATOR_FIRST_OUTPUT = default
    ORDER_RESULTS = No
    OUTPUT_ADD_SCHEMA_ATTRIBUTES = NO
    OUTPUT_FEATURES_DISPLAY = Schema and Data Features
    TEXTLINE_CREATE_FEATURE_TABLES_FROM_DATA = Yes
    TEXTLINE_ENCODING = utf-8
    TEXTLINE_READ_WHOLE_FILE_AT_ONCE = YES
    <OTHER> -> AttributeExposer_2
AttributeExposer_2
    ATTR_TABLE = text_line_data,
    -> XMLFlattener_2
XMLFlattener_2
    ATTRIBUTE_XML = text_line_data
    DISABLE_EXTERNAL_ENTITY_PROCESSING = Yes
    EMBEDDED_EXPRESSIONS = MD_Metadata
    ENTITY_RESOLVER = Yes
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    IGNORE_DATASET_EXTERNAL_DTD = No
    XML_SOURCE_TYPE = xml_attr
    -> BulkAttributeRenamer
BulkAttributeRenamer
    ATTRCHOICE_ACTION = NONPROTECTEDFME
    MODE_CHOICE = RENAME
    PATTERN_ACTION_DISP = ADDPREFIX
    REPLACE_STR = MD_Metadata.
    ATTRCHOICE = All Attributes
    -> AttributeExposer
AttributeExposer
    ATTR_TABLE = MD_Metadata.fileIdentifier.CharacterString,
    -> AttributeKeeper
AttributeKeeper
    CREATE_BULK_MODE_FEATURES = NO
    KEEP_ATTRS = MD_Metadata.fileIdentifier.CharacterString
    -> FeatureHolder
FeatureHolder
    -> AttributeCreator_3
FeatureReader_2
    ATTRIBUTES = text_line,"text_line_data,fme_geometry{0}"
    ATTR_ACCUM_MODE = Only Use Result
    COMBINE_GEOM = Use Result
    DATASET = $(TEXT_FILE)
    FEATURETYPES = text_line
    FORMAT = TEXTLINE
    INITIATOR_FIRST_OUTPUT = default
    ORDER_RESULTS = No
    OUTPUT_ADD_SCHEMA_ATTRIBUTES = NO
    OUTPUT_FEATURES_DISPLAY = Schema and Data Features
    TEXTLINE_CREATE_FEATURE_TABLES_FROM_DATA = Yes
    TEXTLINE_ENCODING = windows-1252
    TEXTLINE_READ_BOTTOM_UP = No
    TEXTLINE_READ_WHOLE_FILE_AT_ONCE = NO
    TEXTLINE_SKIP_FOOTER = 0
    TEXTLINE_SKIP_LINES = 0
    text_line -> AttributeCreator_6
AttributeCreator_6
    ATTR_TABLE = SET_TO MD_Metadata.fileIdentifier.CharacterString (varchar(200)) = @Value(text_line_data)
    -> AttributeCreator_3
AttributeCreator
    ATTR_TABLE = SET_TO MD_Metadata.fileIdentifier.CharacterString (varchar(200)) = $(UUID_TO_DELETE)
    -> AttributeCreator_3
AttributeCreator_3
    ATTR_TABLE:
      SET_TO where_clause (varchar(200)) =                 <ogc:PropertyIsEqualTo>
                            <ogc:PropertyName>dc:identifier</ogc:PropertyName>
                            <ogc:Literal>@Value(MD_Metadata.fileIdentifier.CharacterString)</ogc:Literal>
                        </ogc:PropertyIsEqualTo>
      SET_TO nombre_element (varchar(200)) = 1
    -> Counter_2
Counter_2
    CNT_ATTR = no_feature
    SCOPE = Local
    START = 0
    -> AttributeCreator_4
AttributeCreator_4
    ATTR_TABLE = SET_TO no_lot (varchar(200)) = @Evaluate(@floor(@Value(no_feature)/10))
    -> Aggregator
Aggregator
    ACCUM_ATTRS = All
    AGGREGATE_TYPE = Homogeneous Collection (If Possible)
    CONCAT_ATTRS = where_clause
    GROUP_BY = no_lot
    MODE = Geometry - Assemble One Level
    SUM = nombre_element
    AGGREGATE -> Tester_2
Tester_2
    BOOL_OP = OR
    TEST_CLAUSE = TEST @Value(nombre_element) != 1
    TEST_MODE = TEST
    PASSED -> AttributeCreator_2
    FAILED -> AttributeCreator_5
AttributeCreator_2
    ATTR_TABLE:
      SET_TO xml (varchar(200)) = <csw:Transaction xmlns:csw="http://www.opengis.net/cat/csw/2.0.2" xmlns:ogc="http://www.opengis.net/ogc" xmlns:apiso="http://www.opengis.net/cat/csw/apiso/1.0" xmlns:xsi="http://www.w3.org/2001/XMLSchema-instance" service="CSW" version="2.0.2" xsi:schemaLocation="http://www.opengis.net/cat/csw/2.0.2 http://schemas.opengis.net/csw/2.0.2/CSW-publication.xsd">
            <csw:Delete>
                <csw:Constraint version="1.1.0">
                    <ogc:Filter>
                        <ogc:Or>
                                @Value(where_clause)
                         </ogc:Or>
                    </ogc:Filter>
                </csw:Constraint>
            </csw:Delete>
        </csw:Transaction>
    -> XMLTemplater [ROOT]
AttributeCreator_5
    ATTR_TABLE:
      SET_TO xml (varchar(200)) = <csw:Transaction xmlns:csw="http://www.opengis.net/cat/csw/2.0.2" xmlns:ogc="http://www.opengis.net/ogc" xmlns:apiso="http://www.opengis.net/cat/csw/apiso/1.0" xmlns:xsi="http://www.w3.org/2001/XMLSchema-instance" service="CSW" version="2.0.2" xsi:schemaLocation="http://www.opengis.net/cat/csw/2.0.2 http://schemas.opengis.net/csw/2.0.2/CSW-publication.xsd">
            <csw:Delete>
                <csw:Constraint version="1.1.0">
                    <ogc:Filter>
               @Value(where_clause)
                    </ogc:Filter>
                </csw:Constraint>
            </csw:Delete>
        </csw:Transaction>
    -> XMLTemplater [ROOT]
Note: Creates Header for '_xml_data' attribute and outputs as '_xml_data_header'
XMLTemplater
    OUTPUT_XML_HEADER = Yes
    RESULT_ATTRIBUTE = _xml_data_header
    ROOT_QUERY_EXPR = @Value(xml)
    VISIBLE_QUERY_VALIDATE = Yes
    -> XMLFormatter_2
Note: Cleans up XML documents
XMLFormatter_2
    COLLAPSE_EMPTY_ELEMENT = No
    FORMAT_MODE = PRETTY_PRINT
    INDENT_SIZE = 1
    LIST_NAME = _xml_error
    NAMESPACE_CLEANUP = No
    OUTPUT_ENCODING = utf-8
    PARSER_CHOICE = LIBXML2
    REMOVE_ALL_COMMENT = No
    REMOVE_DTD = No
    REMOVE_EMPTY_ELEMENT = No
    REMOVE_XML_HEADER = no
    REPLACE_TABS_WITH_SPACES = no
    SCHEMALOC_CLEANUP = No
    TEXT_INDENT = no
    WHITESPACE_HANDLING = Preserve all whitespace
    XML_ATTR_TEXT = _xml_data_header
    XML_INPUT_TYPE = Attribute Specifying XML Text
    XML_OUTPUT_ATTR = xml
    XML_OUTPUT_TYPE = Attribute
    FORMATTING_CHOICE = Pretty-Print XML
    PASSED -> XMLValidator_2
Note: Validates XML syntax
XMLValidator_2
    LIMIT_ERRORS = No
    LIST_NAME = _xml_error
    VAL_MODE = SYNTAXONLY
    XML_ATTR_TEXT = xml
    XML_INPUT_TYPE = Attribute Specifying XML Text
    VAL_MODE_1 = Syntax
    PASSED -> StatisticsCalculator
Note: Calculer le nombre de transaction par groupe
StatisticsCalculator
    ATTR_ACCUM_MODE = None
    CALCULATION_MODE = NUMERIC
    FEAT_STATS = MD_Metadata.fileIdentifier.CharacterString,NUMERIC_MODE,,,COUNT,,,,,,,,,,
    PREPEND_ATTR_NAME_OBS = No
    STATISTIC_SUFFIX_RENAME_MAP = COUNT,nombre_transaction
    COMPLETE -> PyCSW_POST_4
Note: Posts Delete Records XML for each UUID in the CSW not found in the current data search, removing the obsolete record
PyCSW_POST_4: PythonCaller
    NEW_ATTRIBUTES = query_response buffer
    PYTHONSOURCE:
      import fme
      import fmeobjects
      #import urllib3
      import requests

      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):

          def __init__(self):
              pass

              self.csw_url = fme.macroValues['CSW_URL']

          def input(self,feature):
              self.xml_str = feature.getAttribute('xml')
              self.xml_str = self.xml_str.encode('utf-8')

              request_str = self.post_xml()

              feature.setAttribute('query_response', request_str)

              self.pyoutput(feature)

          def post_xml(self):
              headers = {'Content-Type': 'text/xml; charset=utf-8'} # set what your server accepts

              return requests.post(self.csw_url, data=self.xml_str, headers=headers, verify=False).text

          def close(self):
              pass
    PYTHONSYMBOL = FeatureProcessor
    -> AttributeKeeper_2
    -> XMLFormatter
XMLFlattener_Output: Inspector [off]
Terminator
    MESSAGE = Translation Terminated
AttributeKeeper_2
    CREATE_BULK_MODE_FEATURES = NO
    KEEP_ATTRS = nombre_transaction
    -> Sampler
Sampler
    MODE = ORIGINAL
    RATE = 5
    SAMPLE_TYPE_MULTIPLIER = 1
    SAMPLE_MODE = No
    SAMPLE_TYPE_LONG = Every Nth Feature
    SAMPLED -> Counter
Counter
    CNT_ATTR = _count
    SCOPE = Local
    START = 1
    -> AttributeCreator_10
AttributeCreator_10
    ATTR_TABLE = SET_TO nb_record (varchar(200)) = @Evaluate(@Value(_count)*5)
    -> Logger
Logger
    LOG_FEATURE = NONE
    MAXFEATS = 1000
    MESSAGE = Pycsw transaction - Delete (@Value(nb_record)/@Value(nombre_transaction))
    SEVERITY = INFO

Bookmark: Extraction du transaction repport
XMLFormatter
    COLLAPSE_EMPTY_ELEMENT = No
    FORMAT_MODE = PRETTY_PRINT
    INDENT_SIZE = 1
    LIST_NAME = _xml_error
    NAMESPACE_CLEANUP = No
    OUTPUT_ENCODING = utf-8
    PARSER_CHOICE = Libxml2
    REMOVE_ALL_COMMENT = Yes
    REMOVE_DTD = No
    REMOVE_EMPTY_ELEMENT = No
    REMOVE_XML_HEADER = no
    REPLACE_TABS_WITH_SPACES = no
    SCHEMALOC_CLEANUP = No
    TEXT_INDENT = no
    WHITESPACE_HANDLING = Preserve all whitespace
    XML_ATTR_TEXT = query_response
    XML_INPUT_TYPE = Attribute Specifying XML Text
    XML_OUTPUT_ATTR = query_response
    XML_OUTPUT_TYPE = Attribute
    FORMATTING_CHOICE = Pretty-Print XML
    PASSED -> XMLFlattener
Note: Si pas capable de flattener le transaction repport, c'est une exception et ça va dans failed
XMLFlattener
    ATTRIBUTE_XML = query_response
    DISABLE_EXTERNAL_ENTITY_PROCESSING = Yes
    EMBEDDED_EXPRESSIONS = csw:TransactionResponse
    ENTITY_RESOLVER = Yes
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    IGNORE_DATASET_EXTERNAL_DTD = No
    XML_SOURCE_TYPE = xml_attr
    -> XMLFlattener_Output
    <REJECTED> -> Terminator
