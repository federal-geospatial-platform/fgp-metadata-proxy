FME workspace NB_FGP_XML_BUILDER_REWORK.fmw

Parameters:
- ACTIVATE_TRANSLATION = No
- FORCED_PYCSW_URL =
- IN_FFS_TESTING_FILE =
- IN_CSV_LOOKUPTABLES_DIR = C:/Data/PT_Harvester/Lookup_tables   # Lookup Tables Directory
- IN_GMD_XML_TEMPLATE_DIR = C:/Data/PT_Harvester/XML_TEMPLATE
- LOGFILES_FOLDER = C:/Data/PT_Harvester/NB/LOG   # folder for log files
- LOCAL_SOURCE_METADATA_DELTA_FINDER = Yes
- LOCAL_WRITER = Yes
- OUT_XLS_NOTIFICATION_DIR = C:/Data/PT_Harvester/NB/XLS
- OUT_XML_FAILED_DIR = C:/Data/PT_Harvester/NB/XML_FAILED
- OUT_XML_LOCAL_DIR = C:/Data/PT_Harvester/NB/XML_LOCAL
- OUT_XML_PASSED_DIR = C:/Data/PT_Harvester/NB/XML_PASSED
- P-T_ABBR = NB
- PYCSW_OVERWRITE = NO
- SocrataDiscoveryAPIURL = https://api.us.socrata.com/api/catalog/v1?   # Socrata Discovery API URL
- TEXT = gnb.socrata.com   # SOCRATA_DOMAIN enter the socrata domain (without http or https)
- USE_PYCSW = no   # Use PYCSW
- READ_FFS = No   # Read FFS for Unit Test
- FME_SHAREDRESOURCE_DATA = C:/Data/PT_Harvester   # FME Server Resource Data

Writers:
- CSV2_1: CSV2 to $(LOGFILES_FOLDER)
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(OUT_XLS_NOTIFICATION_DIR)

HTTPCaller [off]
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://gnb.socrata.com/api/views
    TRANSFER_TIMEOUT_LENGTH = 90
    USE_COOKIES = No
    VERIFY_SSL_CERTIFICATES = No
    -> JSONFlattener
JSONFlattener [off]
    ERROR_LIST_ATTR = _json_error
    JSON_DOCUMENT = @Value(_response_body)
    NEW_ATTRIBUTES = array{}.id
    READ_FROM_FILE = NO
    RECURSIVE = Yes
    -> ListExploder
ListExploder [off]
    ATTR_ACCUM_MODE = Merge List Attributes
    ATTR_CONFLICT_RES = Use List Attribute Values
    INDEX_ATTR = _element_index
    LIST_ATTR = array{}
    ELEMENTS -> AttributeKeeper_2
AttributeKeeper_2 [off]
    KEEP_ATTRS = id
    -> HTTPCaller_2
Recorder [off]
    COMPRESSION_LEVEL = 6
    CREATE_SPATIAL_INDEX = No
    MODE = RECORD_PASS_THROUGH
    RECFILE = C:\Data\PT_Harvester\NB\source_feb12_view.ffs
    STORE_SCANNED_METADATA = No
    STORE_SCANNED_SCHEMA = No
FeatureReader [off]
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
Tester_9
    BOOL_OP = OR
    COMPOSITE_TEST = 1
    TEST_CLAUSE = TEST @Value(assetType) = href
    TEST_MODE = TEST
    PASSED -> Recorder_2
    FAILED -> NB_advancedViewResourceMapper
Recorder_2
    COMPRESSION_LEVEL = 6
    CREATE_SPATIAL_INDEX = No
    MODE = RECORD_PASS_THROUGH
    RECFILE = C:\Data\nbffs2.ffs
    STORE_SCANNED_METADATA = No
    STORE_SCANNED_SCHEMA = No
    RECORDED -> NB_HrefResourcesExtractor [AttributeExposer_Input]
NB_HrefResourcesExtractor
    -> NB_HrefResourceManager
No_iso_topic_for_dataset (writer CSV2_1)
    attributes: title string, title_fr string, id string, geostatus string, url string, format string
Note: NB_LINKBUILDER_GEO
LOOKUP_TABLES_READER_8
    CSV_ENCODING = utf-8
    CSV_PATH = $(IN_CSV_LOOKUPTABLES_DIR)
    FEATURE_TYPE = NB_LINKBUILDER_GEO
    PT = NB
    -> SOCRATA_RESOURCE_MAPPER [linkbuilder_geo]
Note: NB_LINKBUILDER_NONGEO
LOOKUP_TABLES_READER_9
    CSV_ENCODING = utf-8
    CSV_PATH = $(IN_CSV_LOOKUPTABLES_DIR)
    FEATURE_TYPE = NB_LINKBUILDER_NONGEO
    PT = NB
    -> SOCRATA_RESOURCE_MAPPER [LinkBuilderNonGeo]
Note: NB_HrefLinkParts
LOOKUP_TABLES_READER_21
    CSV_ENCODING = utf-8
    CSV_PATH = $(IN_CSV_LOOKUPTABLES_DIR)
    FEATURE_TYPE = NB_HrefLinkParts
    PT = NB
    -> NB_HrefResourceManager [fileparts]
NB_HrefResourceManager
    -> PythonCaller_3
Note: New Script, Merge Resources from esri, advanced views and resources
PythonCaller_3
    NEW_ATTRIBUTES = resources{}.name resources{}.url resources{}.format resources{}.name_fr
    PYTHONSOURCE:
      import fme
      import fmeobjects
      logger = fmeobjects.FMELogFile()
      # Template Function interface:
      # When using this function, make sure its name is set as the value of
      # the 'Class or Function to Process Features' transformer parameter
      def processFeature(feature):
          resourcesFormat = feature.getAttribute('resources{}.format')
          resourcesURL = feature.getAttribute('resources{}.url')
          resourcesName = feature.getAttribute('resources{}.name')
          resourcesNameFr = feature.getAttribute('resources{}.name_fr')

          if resourcesFormat is None and resourcesURL is None and resourcesName is None and resourcesNameFr is None:
              resourcesFormat= []
              resourcesURL = []
              resourcesName = []
              resourcesNameFr = []

          esriResourcesName = feature.getAttribute('esriresources{}.name')
          esriResourcesNameFr = feature.getAttribute('esriresources{}.name_fr')
          esriResourcesURL = feature.getAttribute('esriresources{}.url')
          esriResourcesFormat = feature.getAttribute('esriresources{}.format')

          if esriResourcesFormat is None and esriResourcesURL is None and esriResourcesName is None and esriResourcesNameFr is None:
              esriResourcesFormat= []
              esriResourcesURL = []
              esriResourcesName = []
              esriResourcesNameFr = []

          advancedViewResourcesName = feature.getAttribute('advancedViewResources{}.name')
          advancedViewResourcesNameFr = feature.getAttribute('advancedViewResources{}.name_fr')
          advancedViewResourcesURL = feature.getAttribute('advancedViewResources{}.url')
          advancedViewResourcesFormat = feature.getAttribute('advancedViewResources{}.format')

          if advancedViewResourcesFormat is None and advancedViewResourcesURL is None and advancedViewResourcesName is None and advancedViewResourcesNameFr is None:
              advancedViewResourcesFormat= []
              advancedViewResourcesURL = []
              advancedViewResourcesName = []
              advancedViewResourcesNameFr = []

          hrefResourcesName = feature.getAttribute('hrefResources{}.name')
          hrefResourcesNameFr = feature.getAttribute('hrefResources{}.name_fr')
          hrefResourcesURL = feature.getAttribute('hrefResources{}.url')
          hrefResourcesFormat = feature.getAttribute('hrefResources{}.format')

          if hrefResourcesFormat is None and hrefResourcesURL is None and hrefResourcesName is None and hrefResourcesNameFr is None:
              hrefResourcesFormat = []
              hrefResourcesURL = []
              hrefResourcesName = []
              hrefResourcesNameFr = []


          names = resourcesName + esriResourcesName + advancedViewResourcesName + hrefResourcesName
          names_fr = resourcesNameFr + esriResourcesNameFr + advancedViewResourcesNameFr + hrefResourcesNameFr
          formats = resourcesFormat + esriResourcesFormat + advancedViewResourcesFormat + hrefResourcesFormat
          urls = resourcesURL + esriResourcesURL + advancedViewResourcesURL + hrefResourcesURL
          length = len(names)
          count = 0

          for i in range(length):
              feature.setAttribute("resources{%s}.name" %count,names[i])
              feature.setAttribute("resources{%s}.name_fr" %count,names_fr[i])
              feature.setAttribute("resources{%s}.format" %count, formats[i])
              feature.setAttribute("resources{%s}.url" %count,urls[i])
              count += 1
    PYTHONSYMBOL = processFeature
    -> METADATA_VALUE_MAPPER [DATA_INPUT]
EMPTY_FORMAT_MAPPER
AttributeExposer_2
    ATTR_LIST = p-t_entity
    -> Tester_2
Note: USE PYCSW?
Tester_2
    BOOL_OP = OR
    COMPOSITE_TEST = 1
    TEST_CLAUSE = TEST $(USE_PYCSW) = yes
    TEST_MODE = TEST
    PASSED -> PYCSW_URL_MAPPER
    FAILED -> AttributeCreator_3
AttributeCreator_3
    ATTR_TABLE = SET_TO csw_url = www..com
    -> Tester_5
Note: PyCSW_config
LOOKUP_TABLES_READER_17
    CSV_ENCODING = utf-8
    CSV_PATH = $(IN_CSV_LOOKUPTABLES_DIR)
    FEATURE_TYPE = PyCSW_config
    PT = NB
    -> Tester_4
Note: USE PYCSW?
Tester_4
    BOOL_OP = OR
    COMPOSITE_TEST = 1
    TEST_CLAUSE = TEST $(USE_PYCSW) = yes
    TEST_MODE = TEST
    PASSED -> PYCSW_URL_MAPPER [PYCSW_CONFIG]
Tester_5
    BOOL_OP = AND
    COMPOSITE_TEST = 1 AND 2
    TEST_CLAUSE:
      TEST notes_fr ATTRIBUTE_HAS_A_VALUE ""
      TEST title_fr ATTRIBUTE_HAS_A_VALUE ""
    TEST_MODE = TEST
    PASSED -> AWS_TRANSLATE_3
    FAILED -> AWS_TRANSLATE_2
Translation_errors (writer CSV2_1)
    attributes: id string, _timestamp string
Note: Config_NB
LOOKUP_TABLES_READER_11
    CSV_ENCODING = utf-8
    CSV_PATH = $(IN_CSV_LOOKUPTABLES_DIR)
    FEATURE_TYPE = Config_NB
    PT = NB
    -> XML_PUBLISHER [CONFIG_FILE]
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer

Bookmark: COMMENT
SocrataAPICaller [off]
    SocrataAppToken = FL3Cxsebg0Vf6JQ0CnbMujHkQ
    Socrata_Domain = gnb.socrata.com
    UNIT_TEST = No

Bookmark: Initial Setup and Read from Socrata
Creator_3
    GEOMTYPE = Geometry Object
    NUM = 1
    CREATED -> DateTimeStamper
DateTimeStamper
    DATETIME_ATTR = _toto
    STAMP_TYPE = date
    TIMEZONE = local
    -> VariableSetter
VariableSetter
    SCOPE = Global
    VALUE = @Value(_toto)
    VARNAME = _timestamp
    -> AttributeCreator_4
AttributeCreator_4
    ATTR_TABLE = SET_TO socrataDomainURL = gnb.socrata.com
    -> Tester_6
Tester_6
    BOOL_OP = OR
    COMPOSITE_TEST = 1
    TEST_CLAUSE = TEST $(READ_FFS) = No
    TEST_MODE = TEST
    PASSED -> SocrataReader_APIViews
    FAILED -> FeatureReader_2 [INITIATOR]
Note: new CT
SocrataReader_APIViews
    -> LICENSE_FILTER
FeatureReader_2
    ATTR_ACCUM_MODE = Only Use Result
    COMBINE_GEOM = Use Result
    DATASET = C:\Data\PT_Harvester\NB\source_feb12_view.ffs
    FFS_USE_SEARCH_ENVELOPE = NO
    FORMAT = FFS
    INTERACT = <No Spatial Filter>
    OUTPUT_FEATURES_DISPLAY = Schema and Data Features
    <OTHER> -> LICENSE_FILTER
Note: Can you adjust the way you are reading data. / There are 270 records avalaible on https://gnb.socrata.com/en/browse but this reader gives only 156. Can we are 270 records and split geo vs non geo after / Why the parameter unit test ?
LOOKUP_TABLES_READER_19
    CSV_ENCODING = utf-8
    CSV_PATH = $(IN_CSV_LOOKUPTABLES_DIR)
    FEATURE_TYPE = License_NB
    PT = NB
    -> LICENSE_FILTER [LOOKUP_TABLE_INPUT]
LICENSE_FILTER
    LICENSE_ATT = @Value(licenseId)
    LICENSE_FILTER_PASSED -> AttributeCreator_5
AttributeCreator_5
    ATTR_TABLE:
      SET_TO resource.id = @Value(id)
      SET_TO resource.type = @Value(assetType)
    -> NB_MetadataMerger
Note: I changed the output of the advanced views resources list to output to its own separate list. format and name are handled in later CT
NB_MetadataMerger
    -> NB_DateTimeConversion
    UnmergedAdvancedView -> unmergedAdvancedView (writer CSV2_1)
Note: Had to specify a different Date time input format
NB_DateTimeConversion
    -> NB_Resource_Type_Filter
    error_datetime_output -> Error_Datetime (writer CSV2_1)
Error_Datetime (writer CSV2_1)
    attributes: resource.id string, resource.type string, socrataDomainURL string, id string, _response_body string, _http_status_code string, licenseId string, assetType string, modifyingViewUid string, url string, format string, _seriesID string, advancedViewResources__.url string, advancedViewResources__.format string, publicationDate string, createdAt string, rowsUpdatedAt string, fme_rejection_code string
unmergedAdvancedView (writer CSV2_1)
    attributes: url string, format string, _seriesID string
Note: NB_GeoDataTypes
LOOKUP_TABLES_READER_2
    CSV_ENCODING = utf-8
    CSV_PATH = $(IN_CSV_LOOKUPTABLES_DIR)
    FEATURE_TYPE = NB_GeoDataTypes
    PT = NB
    -> NB_Resource_Type_Filter [Geospatial_Datatypes_Lookup_Table]
Note: NB_Remove
LOOKUP_TABLES_READER
    CSV_ENCODING = utf-8
    CSV_PATH = $(IN_CSV_LOOKUPTABLES_DIR)
    FEATURE_TYPE = NB_Remove
    PT = NB
    -> NB_Resource_Type_Filter [Dataset_Removal_Table]
Note: NB_ExternalLinkFileFormats
LOOKUP_TABLES_READER_20
    CSV_ENCODING = utf-8
    CSV_PATH = $(IN_CSV_LOOKUPTABLES_DIR)
    FEATURE_TYPE = NB_ExternalLinkFileFormats
    PT = NB
    -> NB_Resource_Type_Filter [External_Link_Geo_File_Types]
Note: New CT, filters datasets by type and creates new data layers list, changed name from trueids to dataLayers{}
NB_Resource_Type_Filter
    Geospatial_Assets -> UNIQUE_ID_CREATOR
UNIQUE_ID_CREATOR
    UNIQUE_ATT = resource.id
    -> DEFAULT_ATTRIBUTE_MAPPER
Note: Default_NB
LOOKUP_TABLES_READER_7
    CSV_ENCODING = utf-8
    CSV_PATH = $(IN_CSV_LOOKUPTABLES_DIR)
    FEATURE_TYPE = Default_NB
    PT = NB
    -> DEFAULT_ATTRIBUTE_MAPPER [LOOKUP_TABLE_INPUT]
DEFAULT_ATTRIBUTE_MAPPER
    -> FeatureMerger [REQUESTOR]
Note: SpatialType_NB
LOOKUP_TABLES_READER_22
    CSV_ENCODING = utf-8
    CSV_PATH = $(IN_CSV_LOOKUPTABLES_DIR)
    FEATURE_TYPE = SpatialType_NB
    PT = NB
    -> AttributeExposer_5
AttributeExposer_5
    ATTR_LIST = spatial_representation_type_en,orig_id
    -> FeatureMerger [SUPPLIER]
Note: simple spatial rep type
FeatureMerger
    ATTR_ACCUM_MODE = Merge Supplier
    ATTR_CONFLICT_RES = Use Supplier
    IGNORE_NULLS = No
    JOIN_KEYS = @Value(resource.id) @Value(orig_id) AUTO
    MERGE_TYPE = Attributes Only
    PROCESS_DUPS = NO
    REJECT_NULL_MISSING_KEYS = No
    SUPPLIERS_FIRST = No
    MERGED -> Tester_7
Tester_7
    BOOL_OP = OR
    COMPOSITE_TEST = 1
    TEST_CLAUSE = TEST @Value(assetType) = href
    TEST_MODE = TEST
    PASSED -> NB_FrenchEnglishTitleDescSeparator [Feature_Input]
    FAILED -> NB_BoundingBoxExtractor [feature_input]
Note: only changed variable names
NB_BoundingBoxExtractor
    SocrataAppToken = FL3Cxsebg0Vf6JQ0CnbMujHkQ
    Socrata_Domain = $(SOCRATA_DOMAIN)
    feature_output -> NB_FrenchEnglishTitleDescSeparator [Feature_Input]
Note: NB_SlashCountSeparator
LOOKUP_TABLES_READER_18
    CSV_ENCODING = utf-8
    CSV_PATH = $(IN_CSV_LOOKUPTABLES_DIR)
    FEATURE_TYPE = NB_SlashCountSeparator
    PT = NB
    -> NB_FrenchEnglishTitleDescSeparator [SlashLocationSheet]
Note: only changed attribute names
NB_FrenchEnglishTitleDescSeparator
    Feature_Output -> AttributeExposer_3
    MULTIPLE_UNCAUGHT_SLASH_IN_DESC -> NB_MULTIPLE_SLASH_IN_DESCRIPTION (writer CSV2_1)
NB_MULTIPLE_SLASH_IN_DESCRIPTION (writer CSV2_1)
    attributes: Socrata_id string, link string, description string, datetime string
NB_TAGS_NOT_IN_LOOKUP_TABLE (writer CSV2_1)
Note: NB_Keywords
LOOKUP_TABLES_READER_3
    CSV_ENCODING = utf-8
    CSV_PATH = $(IN_CSV_LOOKUPTABLES_DIR)
    FEATURE_TYPE = NB_Keywords
    PT = NB
    -> NB_FRENCH_TAG_SEPARATOR [TAG_LOOKUP_TABLE]
Note: only changed attribute names
NB_FRENCH_TAG_SEPARATOR
Note: Sector_NB
LOOKUP_TABLES_READER_4
    CSV_ENCODING = utf-8
    CSV_PATH = $(IN_CSV_LOOKUPTABLES_DIR)
    FEATURE_TYPE = Sector_NB
    PT = NB
    -> NB_ORGANIZATION_MAPPER [Sector_Lookup_table]
Note: only changed attribute names
NB_ORGANIZATION_MAPPER
    No_Organization_Value -> NB_NO_ORGANIZATION_VALUE (writer CSV2_1)
    feature_output -> NB_ISOTOPIC_ASSIGNER
    No_Organization_Match -> NB_NO_ORGANIZATION_MATCH (writer CSV2_1)
NB_NO_ORGANIZATION_VALUE (writer CSV2_1)
    attributes: Socrata_ID string, Link string, datetime string
NB_NO_ORGANIZATION_MATCH (writer CSV2_1)
    attributes: Socrata_id string, link string, organization_value string, datetime string
Note: NB_TOPICS_DATASET
LOOKUP_TABLES_READER_5
    CSV_ENCODING = utf-8
    CSV_PATH = $(IN_CSV_LOOKUPTABLES_DIR)
    FEATURE_TYPE = NB_TOPICS_DATASET
    PT = NB
    -> NB_ISOTOPIC_ASSIGNER [NB_TOPICS_DATASET]
Note: NB_TOPICS_GENERIC
LOOKUP_TABLES_READER_6
    CSV_ENCODING = utf-8
    CSV_PATH = $(IN_CSV_LOOKUPTABLES_DIR)
    FEATURE_TYPE = NB_TOPICS_GENERIC
    PT = NB
    -> NB_ISOTOPIC_ASSIGNER [TOPICS_GENERIC]
Note: only changed attribute names
NB_ISOTOPIC_ASSIGNER
    FEATURE_OUTPUT -> Tester_9
    No_dataset_isotopic -> No_iso_topic_for_dataset (writer CSV2_1)

Bookmark: Attachment Handling
AttributeExposer_4
    ATTR_LIST = metadata.attachments{}.assetId,metadata.attachments{}.filename,metadata.attachments{}.name,metadata.attachments.filename,category
    -> ListElementCounter
ListElementCounter
    CNT_ATTR = _element_count
    LIST_NAME = metadata.attachments{}
    -> PythonCaller
PythonCaller
    PYTHONSOURCE:
      import fme
      import fmeobjects
      # Template Function interface:
      # When using this function, make sure its name is set as the value of
      # the 'Class or Function to Process Features' transformer parameter
      def processFeature(feature):

          i=-1
          for i in range(int(feature.getAttribute('_element_count'))):

              root=r'https://gnb.socrata.com/api/views'
              socrata_id=feature.getAttribute('id')
              res_id=feature.getAttribute('metadata.attachments{%i}.assetId'%(i))
              file_name=feature.getAttribute('metadata.attachments{%i}.filename'%(i))

              url=r'%s/%s/files/%s?download=true&filename=%s'%(root,socrata_id,res_id,file_name)
              feature.setAttribute('attachmentResources{%i}.url'%(i),url)
              feature.setAttribute('attachmentResources{%i}.name'%(i),feature.getAttribute('metadata.attachments{%i}.name'%(i)))
    PYTHONSYMBOL = processFeature

Bookmark: COMMENT
Note: Can you adjust the way you are reading data. / There are 270 records avalaible on https://gnb.socrata.com/en/browse but this reader gives only 156. Can we are 270 records and split geo vs non geo after / Why the parameter unit test ?
HTTPCaller_2 [off]
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://gnb.socrata.com/api/views/@Value(id)
    TRANSFER_TIMEOUT_LENGTH = 90
    USE_COOKIES = No
    VERIFY_SSL_CERTIFICATES = No
    -> JSONFlattener_2
JSONFlattener_2 [off]
    ERROR_LIST_ATTR = _json_error
    JSON_DOCUMENT = @Value(_response_body)
    READ_FROM_FILE = NO
    RECURSIVE = Yes
    -> Recorder

Bookmark: temporary tag handling
AttributeExposer_3
    ATTR_LIST = default_domain_tag
    -> ListRenamer
ListRenamer
    LEAVE_ORIG = No
    LIST_ACTION = Rename
    LIST_COMPONENT_NAMES = tags{},tags{}.display_name{}
    LIST_NAME = tags{}
    -> Tester_8
Tester_8
    BOOL_OP = OR
    COMPOSITE_TEST = 1
    TEST_CLAUSE = TEST tags{0}.display_name ATTRIBUTE_HAS_A_VALUE ""
    TEST_MODE = TEST
    PASSED -> Junction
    FAILED -> AttributeCreator_6
AttributeCreator_6
    ATTR_TABLE = SET_TO tags_old{0} = @Value(default_domain_tag)
    -> Junction
Junction
    -> NB_ORGANIZATION_MAPPER [feature_input]

Bookmark: Resource Mapping
Note: new CT, assigns resource values for advanced views in the same format as the other resources
NB_advancedViewResourceMapper: advancedViewResourceMapper
    -> SOCRATA_RESOURCE_MAPPER
Note: only changed attribute names
SOCRATA_RESOURCE_MAPPER
    Socrata_Domain = gnb.socrata.com
    no_geospatial_column_in_trueid -> no_geospatial_column_in_trueid (writer CSV2_1)
    -> NB_ESRIMAPPER
no_geospatial_column_in_trueid (writer CSV2_1)
    attributes: isotopic string, sector string, sector_fr string, title string, title_fr string, record_last_modified string, record_publish_date string, record_create_date string, results string, _element_index string, resource.type string, resource.id string, permalink string, geomidx string, fme_rejection_code string, datatypes_concat string, _http_status_code string, link string, resource.description string, resource.name string, resource.attribution string, classification.domain_metadata_0_.value string, geomcol string, geomtype string, trueid string, GeoAPIEndpoint string, features string, south_bound_latitudes string, north_bound_latitudes string, west_bound_longitudes string,
      east_bound_longitudes string, north_bound_latitude string, minnorth string, maxsouth string, south_bound_latitude string, maxwest string, west_bound_longitude string, east_bound_longitude string, mineast string, slashuuid string, notes string, notes_fr string, name_ct string, organization_raw string, api_value string, dataid string, lang_sep_pos string, classification.domain_category string, uuidjoinkey string, display_name string, tagname string, tag_validity string, isotopicidconcat string, True_Ids_0_.geomcol string, True_Ids_0_.geomtype string, True_Ids_0_.trueid string
Note: NB_ESRISERVICES
LOOKUP_TABLES_READER_10
    CSV_ENCODING = utf-8
    CSV_PATH = $(IN_CSV_LOOKUPTABLES_DIR)
    FEATURE_TYPE = NB_ESRISERVICES
    PT = NB
    -> NB_ESRIMAPPER [ESRI_LOOKUP]
Note: only changed attribute names
NB_ESRIMAPPER
    Invalid_ESRI_URL -> invalid_esri_url (writer CSV2_1)
    -> ListDuplicateRemover
invalid_esri_url (writer CSV2_1)
    attributes: esrirestlink string, title string, title_fr string, EsriLink string, Layertype string, _element_index string, ESRIJSONR string, _http_status_code string, _error string, fme_rejection_code string
Note: remove duplicate spatial references
ListDuplicateRemover
    SRC_LIST = spatialref{}.projection_name
    -> PythonCaller_3

Bookmark: Metadata Value Mapping
Note: Role
LOOKUP_TABLES_READER_12
    CSV_ENCODING = utf-8
    CSV_PATH = $(IN_CSV_LOOKUPTABLES_DIR)
    FEATURE_TYPE = Role
    PT = NB
    -> METADATA_VALUE_MAPPER [LOOKUP_TABLE_INPUT]
METADATA_VALUE_MAPPER
    ATT_TO_MAP = contacts{}.role
    CODE_REFRESH = YES
    ENGLISH_REFRESH = YES
    ERROR_NOT_MAPPED = YES
    FRENCH_REFRESH = YES
    -> METADATA_VALUE_MAPPER_2 [DATA_INPUT]
Note: Update
LOOKUP_TABLES_READER_13
    CSV_ENCODING = utf-8
    CSV_PATH = $(IN_CSV_LOOKUPTABLES_DIR)
    FEATURE_TYPE = Update
    PT = NB
    -> METADATA_VALUE_MAPPER_2 [LOOKUP_TABLE_INPUT]
METADATA_VALUE_MAPPER_2
    ATT_TO_MAP = update_frequency
    CODE_REFRESH = YES
    ENGLISH_REFRESH = YES
    ERROR_NOT_MAPPED = YES
    FRENCH_REFRESH = YES
    -> METADATA_VALUE_MAPPER_3 [DATA_INPUT]
Note: Progress
LOOKUP_TABLES_READER_14
    CSV_ENCODING = utf-8
    CSV_PATH = $(IN_CSV_LOOKUPTABLES_DIR)
    FEATURE_TYPE = Progress
    PT = NB
    -> METADATA_VALUE_MAPPER_3 [LOOKUP_TABLE_INPUT]
METADATA_VALUE_MAPPER_3
    ATT_TO_MAP = progress_code
    CODE_REFRESH = YES
    ENGLISH_REFRESH = YES
    ERROR_NOT_MAPPED = YES
    FRENCH_REFRESH = YES
    -> METADATA_VALUE_MAPPER_4 [DATA_INPUT]
Note: SpatialRepresentation
LOOKUP_TABLES_READER_15
    CSV_ENCODING = utf-8
    CSV_PATH = $(IN_CSV_LOOKUPTABLES_DIR)
    FEATURE_TYPE = SpatialRepresentation
    PT = NB
    -> METADATA_VALUE_MAPPER_4 [LOOKUP_TABLE_INPUT]
METADATA_VALUE_MAPPER_4
    ATT_TO_MAP = spatial_representation_type_en
    CODE_REFRESH = YES
    ENGLISH_REFRESH = YES
    ERROR_NOT_MAPPED = YES
    FRENCH_REFRESH = YES
    -> METADATA_FORMAT_MAPPER [DATA_INPUT]
Note: Format
LOOKUP_TABLES_READER_16
    CSV_ENCODING = utf-8
    CSV_PATH = $(IN_CSV_LOOKUPTABLES_DIR)
    FEATURE_TYPE = Format
    PT = NB
    -> METADATA_FORMAT_MAPPER [LOOKUP_TABLE_INPUT]
METADATA_FORMAT_MAPPER
    ATT_TO_MAP = resources{}.format
    ERROR_NOT_MAPPED = YES
    REAL_VALUE_REFRESH = YES
    RES_TYPE_EN_REFRESH = YES
    RES_TYPE_FR_REFRESH = YES
    -> METADATA_VALUE_MAPPER_ERROR_MANAGER
METADATA_VALUE_MAPPER_ERROR_MANAGER
    ERROR_OUTPUT -> ATTRIBUTE_MAPPING_ERRORS (writer XLSXW_1)
    DATA_OUTPUT -> AttributeRemover_6
ATTRIBUTE_MAPPING_ERRORS (writer XLSXW_1)
    attributes: id string(200), error string(200), _element_index string(200)
Note: Removing error list
AttributeRemover_6
    LIST_ATTRS = mapping_errors{}
    -> DistributionListGenerator
Note: same as before
Note: extract the distributionlist from resources.format
DistributionListGenerator
    -> RESOURCE_NAME_UNDERSCORE_REMOVER

Bookmark: Remove all underscores from resources{}.name attributes
RESOURCE_NAME_UNDERSCORE_REMOVER
    DATA_OUTPUT -> REMOVE_BROKEN_URL_WMS_ESRI_REST

Bookmark: Drop Broken Web Services
REMOVE_BROKEN_URL_WMS_ESRI_REST
    -> WMS_REST_LANGUAGE_FORMATTER
    FAULTY_URL_OUTPUT -> VariableRetriever_2
VariableRetriever_2
    SCOPE = Global
    VALUE_ATTR = _timestamp
    VARNAME = _timestamp
    -> MAP_SERVICE_URL_ERRORMAP (writer CSV2_1)
MAP_SERVICE_URL_ERRORMAP (writer CSV2_1)
    attributes: id string, format string, url string, _url_failure_message string, _timestamp string

Bookmark: HNAP RULES
WMS_REST_LANGUAGE_FORMATTER
    -> DUPLICATE_SERVICE_REMOVER
DUPLICATE_SERVICE_REMOVER
    -> AttributeExposer_2

Bookmark: New Bookmark
PYCSW_URL_MAPPER
    FORCED_PYCSW_URL = $(FORCED_PYCSW_URL)
    PROVIDER = $(P-T_ABBR)
    -> METADATA_DELTA_FINDER
Note: Searches existing PyCSW for new, updated or obsolete data
METADATA_DELTA_FINDER
    ABSTRACT_ATT_NEW = notes
    ABSTRACT_ATT_REF = MD_Metadata.identificationInfo.MD_DataIdentification.abstract.CharacterString
    CSW_FILTER = @Value(p-t_entity); @Value(p-t_entity)
    CUSTOM_CSW_CKAN_URL = @Value(csw_url)
    DATESTAMP_ATT_NEW = record_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    -> AttributeExposer
Note: Exposes PyCSW_Transaction attribute
AttributeExposer
    ATTR_LIST = PyCSW_Transaction
    -> AttributeFilter
Note: Filters items by PyCSW transaction type
AttributeFilter
    ATTR_NAME = PyCSW_Transaction
    ATTR_VALUES = <Empty>,<Missing>,<Null>,<Unfiltered>,No change,Update,Insert,Delete
    <EMPTY> -> Terminator
    <MISSING> -> Terminator
    <NULL> -> Terminator
    <UNFILTERED> -> Terminator
    No change -> Tester
    Update -> Tester_5
    Insert -> Tester_5
    Delete -> AttributeKeeper
Terminator
    MESSAGE = ERROR: Unknown _event value from Metadata_Delta
Note: Selects items with no change for publishing, overwriting all existing data
Tester
    BOOL_OP = OR
    COMPOSITE_TEST = 1
    TEST_CLAUSE = TEST $(PYCSW_OVERWRITE) = YES
    TEST_MODE = TEST
    PASSED -> AttributeCreator
    FAILED -> StatisticsCalculator
Note: Reset to update
AttributeCreator
    ATTR_TABLE = SET_TO PyCSW_Transaction = Update
    -> Tester_5
Note: Retains ID for list of deleted items
AttributeKeeper
    KEEP_ATTRS = id
    -> VariableRetriever_9
VariableRetriever_9
    SCOPE = Global
    VALUE_ATTR = _timestamp
    VARNAME = _timestamp
    -> DELETEDRECORDS (writer CSV2_1)
DELETEDRECORDS (writer CSV2_1)
    attributes: id string, _timestamp string
Creator_2
    GEOMTYPE = Geometry Object
    NUM = 1
    CREATED -> Tester_3
Note: USE PYCSW?
Tester_3
    BOOL_OP = OR
    COMPOSITE_TEST = 1
    TEST_CLAUSE = TEST $(USE_PYCSW) = yes
    TEST_MODE = TEST
    PASSED -> StatisticsCalculator
StatisticsCalculator
    COMPUTE_HISTOGRAM = NO
    COUNT_ATTR = _count
    PREPEND_ATTR_NAME_CHOICE = For multiple results only
    STATS_ATTRS = id
    SUMMARY -> AttributeCreator_2
AttributeCreator_2
    ATTR_TABLE = SET_TO _real_count = @Evaluate(@Value(_count)-1)
    -> StatisticsCalculator_Summary
StatisticsCalculator_Summary: Logger
    LOG_FEATURE = NONE
    MAXFEATS = 20
    MESSAGE:
      ************************
      **** Unchanged Report ****
      ************************

      @Value(_real_count) features were unchanged

      ************************
      ************************
      ************************
    SEVERITY = INFO

Bookmark: AWS Translation
AWS_TRANSLATE_2
    ACTIVATE_TRANSLATION = $(ACTIVATE_TRANSLATION)
    ATTR_2_Translate = notes,title,sector
    ATTR_LIST_2_Translate = resources{}.name
    MODE = English-->French
    -> AWS_TRANSLATE_3
    TRANSLATION_PROBLEM -> VariableRetriever_5
VariableRetriever_5
    SCOPE = Global
    VALUE_ATTR = _timestamp
    VARNAME = _timestamp
    -> Translation_errors (writer CSV2_1)

Bookmark: AWS Translation
AWS_TRANSLATE_3
    ACTIVATE_TRANSLATION = $(ACTIVATE_TRANSLATION)
    ATTR_LIST_2_Translate = tags{}.display_name
    MODE = English-->French
    -> XML_PUBLISHER
    TRANSLATION_PROBLEM -> VariableRetriever_3
VariableRetriever_3
    SCOPE = Global
    VALUE_ATTR = _timestamp
    VARNAME = _timestamp
    -> Translation_errors (writer CSV2_1)

Bookmark: XML CREATION AND WRITING
XML_PUBLISHER
    LOCAL_WRITER = $(LOCAL_WRITER)
    TEMPLATE_GMD_CITEDRESPONSIBLEPARTY = $(IN_GMD_XML_TEMPLATE_DIR)/GMD_CITEDRESPONSIBLEPARTY.xml
    TEMPLATE_GMD_CONTACT = $(IN_GMD_XML_TEMPLATE_DIR)/GMD_CONTACT.xml
    TEMPLATE_GMD_DISTRIBUTIONFORMAT = $(IN_GMD_XML_TEMPLATE_DIR)/GMD_DISTRIBUTIONFORMAT.xml
    TEMPLATE_GMD_DISTRIBUTOR = $(IN_GMD_XML_TEMPLATE_DIR)/GMD_DISTRIBUTOR.xml
    TEMPLATE_GMD_KEYWORDS = $(IN_GMD_XML_TEMPLATE_DIR)/GMD_KEYWORDS.xml
    TEMPLATE_GMD_MDMETADATA = $(IN_GMD_XML_TEMPLATE_DIR)/GMD_MDMETADATA.xml
    TEMPLATE_GMD_REFERENCESYSTEMINFO = $(IN_GMD_XML_TEMPLATE_DIR)/GMD_REFERENCESYSTEMINFO.xml
    TEMPLATE_GMD_RESOURCEMAINTENANCE = $(IN_GMD_XML_TEMPLATE_DIR)/GMD_RESOURCEMAINTENANCE.xml
    TEMPLATE_GMD_TOPICCATEGORY = $(IN_GMD_XML_TEMPLATE_DIR)/GMD_TOPICCATEGORY.xml
    TEMPLATE_GMD_TRANSFEROPTIONS = $(IN_GMD_XML_TEMPLATE_DIR)/GMD_TRANSFEROPTIONS.xml
    LOCAL -> text_line (writer TEXTLINE_3)
    INSERT_PASSED -> text_line (writer TEXTLINE_1)
    INSERT_FAILED -> text_line (writer TEXTLINE_2)
    UPDATE_PASSED -> text_line (writer TEXTLINE_1)
    UPDATE_FAILED -> text_line (writer TEXTLINE_2)

Bookmark: COMMENT
Note: Please have a lookt to the way we implemented other provice. To be able to have a global unit, please add the option to read FFS instead of callling provinicial Portal

Bookmark: COMMENTS
Note: PLease adjuster Workbench parameters name. Try to have something similair to QC or Ontario / Please use the FME_SHAREDRESOURCE_DATA as beginning path for output

Bookmark: Comment
Note: General comment: Add annotations to transformer

Bookmark: Comment
Note: Lost of data / 156 as input, / 44+ 87+22 as output (153) / What's HREF_ouput

FME custom transformer NB_HrefResourcesExtractor

AttributeExposer_Input (input)
    -> AttributeExposer
AttributeExposer
    ATTR_LIST = resource.id,metadata.additionalAccessPoints{}
    -> AttributeExploder
AttributeExploder
    ATTR_NAME_LABEL = attName
    ATTR_VALUE_LABEL = attVal
    EXPLODING_TYPE = List
    KEEP_ATTRIBUTES = Yes
    KEEP_GEOMETRY = No
    LIST_NAME = attList
    -> AttributeKeeper
    -> AttributeRemover
AttributeRemover
    LIST_ATTRS = attList{}
    -> FeatureMerger_3 [REQUESTOR]
AttributeKeeper
    KEEP_ATTRS = resource.id
    KEEP_LIST = attList{}
    -> ListExploder
ListExploder
    ATTR_ACCUM_MODE = Merge List Attributes
    ATTR_CONFLICT_RES = Use List Attribute Values
    INDEX_ATTR = _element_index
    LIST_ATTR = attList{}
    ELEMENTS -> StringSearcher
StringSearcher
    CASE = no
    MATCHED_RESULT_ATTR = _first_match
    REGEXP = metadata.accessPoints
    STRING_TO_SEARCH = @Value(attName)
    MATCHED -> AttributeCreator
    NOT_MATCHED -> StringSearcher_2
AttributeCreator
    ATTR_TABLE = SET_TO hrefUrlAccessPoint = @Value(attVal)
    -> AttributeKeeper_3
AttributeKeeper_3
    KEEP_ATTRS = hrefUrlAccessPoint,resource.id
    -> FeatureMerger_3 [SUPPLIER]
StringSearcher_2
    CASE = no
    MATCHED_RESULT_ATTR = _first_match
    REGEXP = metadata.additionalAccessPoints\{[0-9]*\}.urls
    STRING_TO_SEARCH = @Value(attName)
    MATCHED -> AttributeCreator_2
AttributeCreator_2
    ATTR_TABLE = SET_TO hrefUrlAccessPoint = @Value(attVal)
    -> AttributeKeeper_5
AttributeKeeper_5
    KEEP_ATTRS = hrefUrlAccessPoint,resource.id
    -> FeatureMerger_3 [SUPPLIER]
FeatureMerger_3
    ATTR_ACCUM_MODE = Merge Supplier
    ATTR_CONFLICT_RES = Use Requestor
    IGNORE_NULLS = No
    JOIN_KEYS = @Value(resource.id) @Value(resource.id) AUTO
    LIST_ATTRS_TO_INCLUDE = hrefUrlAccessPoint
    LIST_NAME = additionalAccessPointsList
    MERGE_TYPE = Attributes Only
    PROCESS_DUPS = NO
    REJECT_NULL_MISSING_KEYS = No
    SUPPLIERS_FIRST = No
    MERGED -> AttributeRemover_2
AttributeRemover_2
    REMOVE_ATTRS = _element_index,urlIdx,hrefAdditionalUrlAccessPoint,hrefUrlAccessPoint,additionalAccessPointDescription,additionalAccessPointTitle
    -> Output (output)
Output (output)

FME custom transformer NB_ISOTOPIC_ASSIGNER

input (input)
    -> AttributeExposer
AttributeExposer
    ATTR_LIST = resource.id,category
    -> FeatureMerger_8 [REQUESTOR]
Note: Can you adjust attribute management to be able to use CT METADATA_VALUE_MAPPER / Create the iso_topic list, merge lookup talbe and use the CT.
No_dataset_isotopic (output)

Bookmark: COMMENT
NB_TOPICS_DATASET (input)
    -> AttributeExposer_5
AttributeExposer_5
    ATTR_LIST = original_value,real_value_english
    -> ListBuilder_2
    -> METADATA_VALUE_MAPPER_ONE2MANY_2 [LOOKUP_TABLE_INPUT]

Bookmark: Assign Isotopics
ListBuilder_2
    LIST_ATTRS_TO_INCLUDE = original_value
    LIST_NAME = idtopiclist
    -> AttributeKeeper_4
AttributeKeeper_4
    KEEP_LIST = idtopiclist{}.original_value
    -> FeatureMerger_8 [SUPPLIER]
FeatureMerger_8
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = 1 1 AUTO
    MERGE_TYPE = Attributes Only
    PROCESS_DUPS = YES
    REJECT_NULL_MISSING_KEYS = No
    SUPPLIERS_FIRST = No
    MERGED -> ListSearcher
ListSearcher
    ATTR_VALUE = @Value(resource.id)
    INDEX_ATTR = _list_index
    LIST_ATTR = idtopiclist{}.original_value
    MATCHTYPE = FIRST_MATCHED_ENCODED
    FOUND -> AttributeCreator
    NOT_FOUND -> Tester_9
AttributeCreator
    ATTR_TABLE = SET_TO isotopic = @Value(resource.id)
    -> METADATA_VALUE_MAPPER_ONE2MANY_2 [DATA_INPUT]
METADATA_VALUE_MAPPER_ONE2MANY_2
    ATT_TO_MAP = isotopic
    CODE_REFRESH = NO
    ENGLISH_REFRESH = YES
    ERROR_NOT_MAPPED = YES
    FRENCH_REFRESH = NO
    -> AttributeCreator_4
AttributeCreator_4
    ATTR_TABLE = SET_TO isotopic_assignment_method = dataset_specific
    -> AttributeRemover
Tester_9
    BOOL_OP = OR
    COMPOSITE_TEST = 1
    TEST_CLAUSE = TEST category ATTRIBUTE_HAS_A_VALUE ""
    TEST_MODE = TEST
    PASSED -> AttributeCreator_2
    FAILED -> No_dataset_isotopic (output)
AttributeCreator_2
    ATTR_TABLE = SET_TO isotopic = @Value(category)
    -> METADATA_VALUE_MAPPER_ONE2MANY [DATA_INPUT]
TOPICS_GENERIC (input)
    -> AttributeExposer_6
AttributeExposer_6
    ATTR_LIST = original_value,real_value_english
    -> METADATA_VALUE_MAPPER_ONE2MANY [LOOKUP_TABLE_INPUT]
METADATA_VALUE_MAPPER_ONE2MANY
    ATT_TO_MAP = isotopic
    CODE_REFRESH = NO
    ENGLISH_REFRESH = YES
    ERROR_NOT_MAPPED = YES
    FRENCH_REFRESH = NO
    -> AttributeCreator_3
AttributeCreator_3
    ATTR_TABLE = SET_TO isotopic_assignment_method = generic
    -> AttributeRemover
AttributeRemover
    LIST_ATTRS = idtopiclist{}
    REMOVE_ATTRS = isotopic
    -> FEATURE_OUTPUT (output)
FEATURE_OUTPUT (output)

FME custom transformer NB_FRENCH_TAG_SEPARATOR

feature_input (input)
    -> AttributeExposer
Note: Attribute cleanup
AttributeExposer
    ATTR_LIST = tags{},category,resource.id,link2,default_domain_tag
    -> ListRenamer
ListExploder_2
    ATTR_ACCUM_MODE = Merge List Attributes
    ATTR_CONFLICT_RES = Use List Attribute Values
    INDEX_ATTR = _element_index
    LIST_ATTR = tags{}
    ELEMENTS -> Tester
    <REJECTED> -> Terminator_4
Tester
    BOOL_OP = OR
    COMPOSITE_TEST = 1
    TEST_CLAUSE = TEST @Value(TAG_IN_LOOKUP) = 0
    TEST_MODE = TEST
    PASSED -> AttributeKeeper_2
AttributeKeeper_2
    KEEP_ATTRS = display_name,resource.id
    -> TAG_NOT_FOUND (output)
TAG_NOT_FOUND (output)
Terminator_4
    MESSAGE = Translation Terminated
AttributeRemover_2
    REMOVE_ATTRS = display_name,tag_validity,uuidjoinkey,_element_index,tagname
    -> feature_output (output)
feature_output (output)

Bookmark: Remove French Tags from Tag List
ListRenamer
    LEAVE_ORIG = No
    LIST_ACTION = Rename
    LIST_COMPONENT_NAMES = tags{},tags_old{}
    LIST_NAME = tags{}
    -> UUIDGenerator
UUIDGenerator
    UUID_ATTR = uuidjoinkey
    -> AttributeKeeper
    -> AttributeRemover
AttributeRemover
    LIST_ATTRS = classification.domain_tags{}
    -> FeatureMerger_4 [REQUESTOR]
AttributeKeeper
    KEEP_ATTRS = default_domain_tag,uuidjoinkey,resource.id
    KEEP_LIST = tags_old{}
    -> Tester_4
    -> AttributeKeeper_Output
Tester_4
    BOOL_OP = OR
    COMPOSITE_TEST = 1
    TEST_CLAUSE = TEST tags_old{0} ATTRIBUTE_HAS_A_VALUE ""
    TEST_MODE = TEST
    PASSED -> ListExploder
    FAILED -> AttributeCreator_5
AttributeCreator_5
    ATTR_TABLE = SET_TO tags_old{0} = @Value(default_domain_tag)
    -> ListExploder
ListExploder
    ATTR_ACCUM_MODE = Merge List Attributes
    ATTR_CONFLICT_RES = Use List Attribute Values
    INDEX_ATTR = _element_index
    LIST_ATTR = tags_old{}
    ELEMENTS -> AttributeRenamer
    <REJECTED> -> Terminator
AttributeRenamer
    ATTR_TABLE:
      RENAME_SET_DEFAULT tags_old > display_name
      RENAME_SET_DEFAULT resource.id > resourceid
    -> FeatureMerger_3 [REQUESTOR]
Terminator
    MESSAGE = Translation Terminated
AttributeKeeper_Output: Inspector
TAG_LOOKUP_TABLE (input)
    -> AttributeExposer_4
AttributeExposer_4
    ATTR_LIST = tagname,tag_validity
    -> FeatureMerger_3 [SUPPLIER]
FeatureMerger_3
    ATTR_ACCUM_MODE = Merge Supplier
    ATTR_CONFLICT_RES = Use Requestor
    IGNORE_NULLS = No
    JOIN_KEYS = @Value(display_name) @Value(tagname) AUTO
    MERGE_TYPE = Attributes Only
    PROCESS_DUPS = NO
    REJECT_NULL_MISSING_KEYS = No
    SUPPLIERS_FIRST = No
    MERGED -> Tester_7
    UNMERGED_REQUESTOR -> AttributeCreator
    <REJECTED> -> Terminator_2
Tester_7
    BOOL_OP = OR
    COMPOSITE_TEST = 1
    TEST_CLAUSE = TEST @Value(tag_validity) = valid
    TEST_MODE = TEST
    PASSED -> AttributeCreator_2
Note: Attribute cleanup
AttributeCreator_2
    ATTR_TABLE = SET_TO TAG_IN_LOOKUP = 1
    -> AttributeRemover_3
AttributeCreator
    ATTR_TABLE = SET_TO TAG_IN_LOOKUP = 0
    -> AttributeRemover_3
AttributeRemover_3
    REMOVE_ATTRS = resourceid
    -> FeatureMerger_4 [SUPPLIER]
FeatureMerger_4
    ATTR_ACCUM_MODE = Merge Supplier
    ATTR_CONFLICT_RES = Use Requestor
    IGNORE_NULLS = No
    JOIN_KEYS = @Value(uuidjoinkey) @Value(uuidjoinkey) AUTO
    LIST_ATTRS_TO_INCLUDE = display_name TAG_IN_LOOKUP
    LIST_NAME = tags
    MERGE_TYPE = Attributes Only
    PROCESS_DUPS = NO
    REJECT_NULL_MISSING_KEYS = No
    SUPPLIERS_FIRST = No
    MERGED -> ListSearcher
    <REJECTED> -> Terminator_3
ListSearcher
    ATTR_VALUE = 0
    INDEX_ATTR = tagidx
    LIST_ATTR = tags{}.TAG_IN_LOOKUP
    MATCHTYPE = FIRST_MATCHED_ENCODED
    FOUND -> ListExploder_2
    NOT_FOUND -> AttributeRemover_2
Terminator_3
    MESSAGE = Translation Terminated
Terminator_2
    MESSAGE = Translation Terminated

Bookmark: COMMENTS
Note: Please add terminator to rejected ports

FME custom transformer NB_BoundingBoxExtractor

Parameters:
- Socrata_Domain =   # Enter the Socrata Domain (without https)
- SocrataAppToken = FL3Cxsebg0Vf6JQ0CnbMujHkQ   # Socrata App Token

feature_input (input)
    -> AttributeExposer_2
Note: gets the bounding box geojson from the socrata api, enters the json coordinate array into python where list comprehension is used to get the minimum and maximum lat and long
AttributeExposer_2
    ATTR_LIST = dataLayers{},dataLayers{}.layerid,dataLayers{}.geomcol,dataLayers{}.name,dataLayers{}.geomtype
    -> UUIDGenerator_2
Note: cleanup
AttributeRemover_6
    LIST_ATTRS = dataLayers{}.east_bound_longitudes dataLayers{}.north_bound_latitudes dataLayers{}.south_bound_latitudes dataLayers{}.west_bound_longitudes
    REMOVE_ATTRS = coordinatestring,bbox_json,uuidjoinkey
    -> feature_output (output)
feature_output (output)

Bookmark: Extract Bounding Box
UUIDGenerator_2
    UUID_ATTR = uuidjoinkey
    -> FeatureMerger_2 [REQUESTOR]
    -> AttributeKeeper_2
AttributeKeeper_2
    KEEP_ATTRS = uuidjoinkey
    KEEP_LIST = dataLayers{}
    -> ListExploder_2
ListExploder_2
    ATTR_ACCUM_MODE = Merge List Attributes
    ATTR_CONFLICT_RES = Use List Attribute Values
    INDEX_ATTR = _element_index
    LIST_ATTR = dataLayers{}
    ELEMENTS -> StringConcatenator
    <REJECTED> -> Terminator_2
StringConcatenator
    ACTION = Create New Attribute
    PARM_LINE = https://gnb.socrata.com/resource/@Value(layerid).geojson
    VAL_ATTR = GeoAPIEndpoint
    -> HTTPCaller_2
HTTPCaller_2
    CONNECTION_TIMEOUT_LENGTH = 60
    CUSTOM_HEADERS = X-App-Token;$(SocrataAppToken)
    ERROR_ATTR = _error
    FOLLOW_REDIRECTS = Yes
    HTTP_METHOD = GET
    SAVE_FILE = Attribute
    STATUS_CODE_ATTR = _http_status_code
    TARGET_ATTR = bbox_json
    TARGET_ATTR_ENCODING = auto-detect
    TARGET_URL = @Value(GeoAPIEndpoint)?$select=extent(@Value(geomcol))
    TRANSFER_TIMEOUT_LENGTH = 90
    USE_COOKIES = No
    VERIFY_SSL_CERTIFICATES = No
    -> AttributeRemover
    <REJECTED> -> Terminator
AttributeRemover
    REMOVE_ATTRS = _http_status_code
    -> JSONFlattener_2
JSONFlattener_2
    ERROR_LIST_ATTR = _json_error
    JSON_DOCUMENT = @Value(bbox_json)
    NEW_ATTRIBUTES = features
    READ_FROM_FILE = NO
    RECURSIVE = No
    -> JSONExtractor
    <REJECTED> -> Terminator_3
JSONExtractor
    EXTRACT_QUERY_TABLE = coordinatestring json["features"][0]["geometry"]["coordinates"][0][0]
    JSON_DOCUMENT = @Value(bbox_json)
    READ_FROM_FILE = NO
    EVALUATED -> PythonCaller
    <REJECTED> -> Terminator_4
Note: extracts the minimum and maximum longitude and latitude values of the bounding box. doing this with transformers is extremely convoluted. with python it is fast and efficient.
PythonCaller
    NEW_ATTRIBUTES = south_bound_latitudes north_bound_latitudes west_bound_longitudes east_bound_longitudes
    PYTHONSOURCE:
      import fme, fmeobjects, json
      # Template Function interface:
      # When using this function, make sure its name is set as the value of
      # the 'Class or Function to Process Features' transformer parameter
      def processFeature(feature):
          list = feature.getAttribute('coordinatestring')
          actualList = json.loads(list)
          longitudes = [float(x[0]) for x in actualList]
          latitudes = [float(x[1]) for x in actualList]
          feature.setAttribute('south_bound_latitudes',min(latitudes))
          feature.setAttribute('north_bound_latitudes',max(latitudes))
          feature.setAttribute('west_bound_longitudes',min(longitudes))
          feature.setAttribute('east_bound_longitudes',max(longitudes))
    PYTHONSYMBOL = processFeature
    -> FeatureMerger_2 [SUPPLIER]
FeatureMerger_2
    ATTR_ACCUM_MODE = Merge Supplier
    ATTR_CONFLICT_RES = Use Requestor
    IGNORE_NULLS = No
    JOIN_KEYS = @Value(uuidjoinkey) @Value(uuidjoinkey) AUTO
    LIST_ATTRS_TO_INCLUDE = east_bound_longitudes geomcol geomtype name north_bound_latitudes south_bound_latitudes west_bound_longitudes layerid
    LIST_NAME = dataLayers
    MERGE_TYPE = Attributes Only
    PROCESS_DUPS = NO
    REJECT_NULL_MISSING_KEYS = No
    SUPPLIERS_FIRST = No
    MERGED -> ListRangeExtractor
Terminator_4
    MESSAGE = Translation Terminated
Terminator_3
    MESSAGE = Translation Terminated
Terminator
    MESSAGE = Translation Terminated
Terminator_2
    MESSAGE = Translation Terminated

Bookmark: Consolidates longitude and latitude lists for if a dataset has multiple layers
ListRangeExtractor
    MAX = north_bound_latitude
    MIN = minnorth
    SRC_LIST = dataLayers{}.north_bound_latitudes
    -> ListRangeExtractor_2
ListRangeExtractor_2
    MAX = maxsouth
    MIN = south_bound_latitude
    SRC_LIST = dataLayers{}.south_bound_latitudes
    -> ListRangeExtractor_3
ListRangeExtractor_3
    MAX = maxwest
    MIN = west_bound_longitude
    SRC_LIST = dataLayers{}.west_bound_longitudes
    -> ListRangeExtractor_4
ListRangeExtractor_4
    MAX = east_bound_longitude
    MIN = mineast
    SRC_LIST = dataLayers{}.east_bound_longitudes
    -> AttributeRemover_6

Bookmark: COMMENTS
Note: Please add terminator to rejected ports when needed

FME custom transformer NB_DateTimeConversion

Input (input)
    -> AttributeExposer
AttributeExposer
    ATTR_LIST = publicationDate,createdAt,rowsUpdatedAt
    -> DateTimeConverter
Output (output)
error_datetime_output (output)

Bookmark: DateTime Conversion
Note: Formats all date fields to ISO yyyy-mm-dd
DateTimeConverter
    DATETIME_ATTR = publicationDate createdAt rowsUpdatedAt
    IN_FORMAT = %s$
    OUT_FORMAT = %Y-%m-%d
    PASSTHROUGH = NO
    REPAIR_INPUT = YES
    TEST_INPUT = 1611946240
    -> AttributeRenamer_2
    <REJECTED> -> error_datetime_output (output)
AttributeRenamer_2
    ATTR_TABLE:
      RENAME_SET_DEFAULT rowsUpdatedAt > record_last_modified
      RENAME_SET_DEFAULT publicationDate > record_publish_date
      RENAME_SET_DEFAULT createdAt > record_create_date
    -> Output (output)

FME custom transformer SocrataAPICaller

Parameters:
- Socrata_Domain = gnb.socrata.com   # Enter the Socrata Domain (without https)
- SocrataAppToken = FL3Cxsebg0Vf6JQ0CnbMujHkQ   # Socrata App Token
- UNIT_TEST = No   # Unit Test Mode

Note: To be more robust, instead of hardcoding 1000 max records, can you loop with resultSetSize value in the request and the offset in the query. / Loop it 10 by 10 / http://api.us.socrata.com/api/catalog/v1?only=datasets&domains=gnb.socrata.com&limit=10&offset=0 / http://api.us.socrata.com/api/catalog/v1?only=datasets&domains=gnb.socrata.com&limit=10&offset=10 / http://api.us.socrata.com/api/catalog/v1?only=datasets&domains=gnb.socrata.com&limit=10&offset=20
Note: Set Verrify SSL certificate to No / Add something to catch rejected elements / Don't have to publish socrata domain has a parameter. Can be hardcoded
feature_input (input)
    -> AttributeCreator_4
Note: What's that ?? / IF this used only inside SocrataAPI Caller, please set those attributes inside the CT
AttributeCreator_4
    ATTR_TABLE:
      SET_TO iteration = 0
      SET_TO currentDatasetCount = 0
    -> AttributeExposer_2
Note: clone it x number of times
AttributeExposer_2
    ATTR_LIST = _creation_instance,_toto,currentDatasetCount,iteration
    -> Tester
Note: Removes Datasets without geometry datatypes in resources.columns_datatype{},
Tester_2_Failed: Inspector
Note: lookup any new geospatial column types
Note: ListeConcatentor + tester +listsearcher might be replaced by a listsearcher using a regex (I think)... / Also Can you create a sheet for datatype in excel. If new datatypes are coming, we need to update the sheet.
Note: cleanup
AttributeRemover_7
    LIST_ATTRS = columns{}
    REMOVE_ATTRS = _element_index,datatypes_concat,_http_status_code,results
    -> Geospatial_Feature_Output (output)
Geospatial_Feature_Output (output)
Note: cleanup
AttributeRemover_4
    LIST_ATTRS = columns{}
    REMOVE_ATTRS = results,_element_index,joinuuid,_http_status_code,datatypes_concat
    -> Non_Geopatial_Dataset_Output (output)
Non_Geopatial_Dataset_Output (output)

Bookmark: Initial Query, Flattening and Filtering
Note: Bypass API GET request for unit testing
Tester
    BOOL_OP = OR
    COMPOSITE_TEST = 1
    TEST_CLAUSE = TEST $(UNIT_TEST) = Yes
    TEST_MODE = TEST
    PASSED -> AttributeExposer_4
    FAILED -> HTTPCaller_5
Note: Please add terminator to rejected ports
HTTPCaller_5
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = http://api.us.socrata.com/api/catalog/v1/domains?domains=$(Socrata_Domain)&derived=false&only=datasets,maps
    TRANSFER_TIMEOUT_LENGTH = 90
    USE_COOKIES = No
    VERIFY_SSL_CERTIFICATES = No
    -> JSONFlattener
    <REJECTED> -> Terminator_2
JSONFlattener
    ERROR_LIST_ATTR = _json_error
    JSON_DOCUMENT = @Value(_response_body)
    READ_FROM_FILE = NO
    RECURSIVE = Yes
    -> AttributeExposer_9
    <REJECTED> -> Terminator
AttributeExposer_9
    ATTR_LIST = results{0}.count
    -> AttributeRenamer_3
AttributeRenamer_3
    ATTR_TABLE = RENAME_SET_DEFAULT results{0}.count > maxDatasetCount
    -> AttributeExposer_8
AttributeExposer_8
    ATTR_LIST = currentDatasetCount,maxDatasetCount,iteration
    -> Cloner
Note: Please add terminator to rejected ports
Cloner
    COPIES = @ceil(@Value(maxDatasetCount)/10)
    COPYATT = iteration
    COPY -> AttributeCreator
    <REJECTED> -> Terminator_3
AttributeCreator
    ATTR_TABLE = SET_TO currentDatasetCount = @Evaluate(@Value(iteration)*10)
    -> HTTPCaller
AttributeRemover_8
    REMOVE_ATTRS = iteration,currentDatasetCount,_http_status_code,_response_body,maxDatasetCount
    -> JSONFlattener_3
ListExploder_3
    ATTR_ACCUM_MODE = Only Use List Attributes
    INDEX_ATTR = _element_index
    LIST_ATTR = results{}
    ELEMENTS -> BulkAttributeRenamer
    <REJECTED> -> BulkAttributeRenamer
BulkAttributeRenamer
    ATTRCHOICE = All Attributes
    CASE_DISP = NO
    MODE_CHOICE = RENAME
    PATTERN_ACTION_DISP = REMOVEPREFIX
    REPLACE_STR = results.
    -> AttributeExposer_4
AttributeExposer_4
    ATTR_LIST = resource.type,resource.id,permalink
    -> FeatureMerger_4 [REQUESTOR]
Terminator_5
    MESSAGE = Translation Terminated
Terminator_4
    MESSAGE = Translation Terminated
Note: initial call, filters for datasets only in the domain of $(Socrata_Domain)
Terminator_3
    MESSAGE = Translation Terminated
Terminator
    MESSAGE = Translation Terminated
Terminator_2
    MESSAGE = Translation Terminated
Note: Can be replace by json flattner+listexploder. / Might be little bit faster.... / Also add something to catch rejected port
Geospatial_Datatypes_Lookup_Table (input)
    -> AttributeExposer_6
AttributeExposer_6
    ATTR_LIST = datatype
    -> ListBuilder
ListBuilder
    LIST_ATTRS_TO_INCLUDE = datatype
    LIST_NAME = _list
    -> ListConcatenator
ListConcatenator
    DROP_EMPTY_PARTS = No
    LIST_ATTR = _list{}.datatype
    SEP = |
    VAL_ATTR = datatypes_concat
    -> AttributeKeeper_3
AttributeKeeper_3
    KEEP_ATTRS = datatypes_concat
    -> FeatureMerger_4 [SUPPLIER]
Terminator_6
    MESSAGE = Translation Terminated
Dataset_Removal_Table (input)
    -> AttributeExposer_3
AttributeExposer_3
    ATTR_LIST = dataid
    -> FeatureMerger_5 [SUPPLIER]

Bookmark: COMMENTS
Note: Please add terminator to rejected ports
HTTPCaller
    CONNECTION_TIMEOUT_LENGTH = 60
    CUSTOM_HEADERS = X-App-Token;$(SocrataAppToken)
    ERROR_ATTR = _error
    FOLLOW_REDIRECTS = Yes
    HTTP_METHOD = GET
    SAVE_FILE = Attribute
    STATUS_CODE_ATTR = _http_status_code
    TARGET_ATTR = currentResponse
    TARGET_ATTR_ENCODING = auto-detect
    TARGET_URL = http://api.us.socrata.com/api/catalog/v1?only=datasets,maps&domains=$(Socrata_Domain)&limit=10&offset=@Value(currentDatasetCount)&derived=false
    TRANSFER_TIMEOUT_LENGTH = 90
    USE_COOKIES = No
    VERIFY_SSL_CERTIFICATES = No
    -> AttributeRemover_8
    <REJECTED> -> Terminator_4

Bookmark: COMMENTS
Note: Please add terminator to rejected ports
JSONFlattener_3
    ERROR_LIST_ATTR = _json_error
    JSON_DOCUMENT = @Value(currentResponse)
    NEW_ATTRIBUTES = results{}
    READ_FROM_FILE = NO
    RECURSIVE = Yes
    -> ListExploder_3
    <REJECTED> -> Terminator_5

Bookmark: COMMENTS
Note: Please add terminators. It's unconditinnal merge so no feature should outputted in the unmerged requestor, unusedSupplier and rejected port
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> FeatureMerger_5 [REQUESTOR]
    UNMERGED_REQUESTOR -> Terminator_6
    UNUSED_SUPPLIER -> Terminator_6
    <REJECTED> -> Terminator_6

Bookmark: Geospatial Dataset Filtering
FeatureMerger_5
    ATTR_ACCUM_MODE = Merge Supplier
    ATTR_CONFLICT_RES = Use Requestor
    IGNORE_NULLS = No
    JOIN_KEYS = @Value(resource.id) @Value(dataid) AUTO
    MERGE_TYPE = Attributes Only
    PROCESS_DUPS = NO
    REJECT_NULL_MISSING_KEYS = No
    SUPPLIERS_FIRST = No
    UNMERGED_REQUESTOR -> Tester_2
Tester_2
    BOOL_OP = OR
    COMPOSITE_TEST = 1
    TEST_CLAUSE = CASE_INSENSITIVE_TEST @Value(resource.type) != map
    TEST_MODE = CASE_INSENSITIVE_TEST
    PASSED -> AttributeExposer
    FAILED -> HTTPCaller_6
    FAILED -> Tester_2_Failed
AttributeExposer
    ATTR_LIST = resource.columns_datatype{},resource.columns_field_name{}
    -> UUIDGenerator_3
UUIDGenerator_3
    UUID_ATTR = joinuuid
    -> FeatureMerger_3 [REQUESTOR]
    -> AttributeKeeper_4
AttributeKeeper_4
    KEEP_ATTRS = joinuuid
    KEEP_LIST = resource.columns_datatype{}
    -> ListExploder_4
StringCaseChanger
    ATTRCHOICE = Selected Attributes
    ATTRLIST = resource.columns_datatype
    CHANGE_TYPE = lowercase
    -> AttributeRenamer
AttributeRenamer
    ATTR_TABLE = RENAME_SET_DEFAULT resource.columns_datatype > datatype_lower
    -> AttributeRemover_9
Note: Please add terminator to ports were data should not go
AttributeRemover_9
    REMOVE_ATTRS = colDataTypeIdx
    -> FeatureMerger_3 [SUPPLIER]
ListSearcher
    ATTR_VALUE = (@Value(datatypes_concat))
    INDEX_ATTR = geomidx
    LIST_ATTR = columns{}.datatype_lower
    MATCHTYPE = REGULAR_EXPRESSION_ENCODED
    FOUND -> AttributeRemover_10
    NOT_FOUND -> AttributeRemover_4
AttributeRemover_10
    REMOVE_ATTRS = datatypes_concat,fme_rejection_code,joinuuid,datatype_lower
    -> AttributeExposer_7
AttributeExposer_7
    ATTR_LIST = resource.columns_field_name{},resource.id
    -> AttributeCreator_2
AttributeCreator_2
    ATTR_TABLE:
      SET_TO True_Ids{0}.geomcol = @Value(resource.columns_field_name{@Value(geomidx)})
      SET_TO True_Ids{0}.geomtype = @Value(columns{@Value(geomidx)}.datatype_lower)
      SET_TO True_Ids{0}.trueid = @Value(resource.id)
    -> AttributeRemover_7

Bookmark: COMMENT
Note: What to do with rejected elements
ListExploder_4
    ATTR_ACCUM_MODE = Merge List Attributes
    ATTR_CONFLICT_RES = Use List Attribute Values
    INDEX_ATTR = colDataTypeIdx
    LIST_ATTR = resource.columns_datatype{}
    ELEMENTS -> StringCaseChanger

Bookmark: COMMENTS
FeatureMerger_3
    ATTR_ACCUM_MODE = Merge Supplier
    ATTR_CONFLICT_RES = Use Requestor
    IGNORE_NULLS = No
    JOIN_KEYS = @Value(joinuuid) @Value(joinuuid) AUTO
    LIST_ATTRS_TO_INCLUDE = datatype_lower
    LIST_NAME = columns
    MERGE_TYPE = Attributes Only
    PROCESS_DUPS = NO
    REJECT_NULL_MISSING_KEYS = No
    SUPPLIERS_FIRST = No
    MERGED -> ListSearcher

Bookmark: Comment
Note: What to do with the rejected ones
Note: SSL certificate validation = no
HTTPCaller_6
    CONNECTION_TIMEOUT_LENGTH = 60
    ERROR_ATTR = _error
    FOLLOW_REDIRECTS = Yes
    HTTP_METHOD = GET
    SAVE_FILE = Attribute
    STATUS_CODE_ATTR = _http_status_code
    TARGET_ATTR = HTTPGET
    TARGET_ATTR_ENCODING = auto-detect
    TARGET_URL = https://gnb.socrata.com/api/views/@Value(resource.id).json
    TRANSFER_TIMEOUT_LENGTH = 90
    USE_COOKIES = No
    VERIFY_SSL_CERTIFICATES = No
    -> UUIDGenerator_4

Bookmark: Get Layers from Maps Datasets
UUIDGenerator_4
    UUID_ATTR = _uuid
    -> AttributeKeeper_5
    -> AttributeRemover_2
AttributeRemover_2
    REMOVE_ATTRS = HTTPGET
    -> FeatureMerger_6 [REQUESTOR]
AttributeKeeper_5
    KEEP_ATTRS = datatypes_concat,HTTPGET,_uuid
    -> JSONFlattener_4
AttributeExposer_11
    ATTR_LIST = columns{}.name,columns{}.dataTypeName
    -> PythonCaller_3
PythonCaller_3
    PYTHONSOURCE:
      import fme
      import fmeobjects
      # Template Function interface:
      # When using this function, make sure its name is set as the value of
      # the 'Class or Function to Process Features' transformer parameter
      def processFeature(feature):
          _list = feature.getAttribute('columns{}.dataTypeName')
          _outlist =  [x.lower() for x in _list]
          for i in range (len(_outlist)):
              feature.setAttribute('columns{{{}}}.dataTypeName'.format(i),_outlist[i])

      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = FeatureProcessor
    -> ListSearcher_2
ListSearcher_2
    ATTR_VALUE = (@Value(datatypes_concat))
    INDEX_ATTR = geomidx
    LIST_ATTR = columns{}.dataTypeName
    MATCHTYPE = REGULAR_EXPRESSION_ENCODED
    FOUND -> AttributeCreator_5
    NOT_FOUND -> AttributeRemover_4
AttributeCreator_5
    ATTR_TABLE:
      SET_TO geomcol = @Value(columns{@Value(geomidx)}.name)
      SET_TO geomtype = @Value(columns{@Value(geomidx)}.dataTypeName)
      SET_TO trueid = @Value(childViews)
    -> AttributeKeeper_8
AttributeKeeper_8
    KEEP_ATTRS = trueid,_uuid,geomtype,geomcol
    -> FeatureMerger_6 [SUPPLIER]
AttributeRemover_11
    REMOVE_ATTRS = geomcol,trueid,geomtype,_uuid
    -> AttributeRemover_7

Bookmark: COMMENT
JSONFlattener_4
    ERROR_LIST_ATTR = _json_error
    JSON_DOCUMENT = @Value(HTTPGET)
    READ_FROM_FILE = NO
    RECURSIVE = Yes
    -> AttributeExposer_10
Note: What to do with rejected ones
AttributeExposer_10
    ATTR_LIST = childViews{}
    -> ListExploder_5
ListExploder_5
    ATTR_ACCUM_MODE = Merge List Attributes
    ATTR_CONFLICT_RES = Use List Attribute Values
    INDEX_ATTR = _element_index
    LIST_ATTR = childViews{}
    ELEMENTS -> HTTPCaller_7
HTTPCaller_7
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body2
    TARGET_ATTR_ENCODING = auto-detect
    TARGET_URL = https://gnb.socrata.com/api/views/@Value(childViews).json
    TRANSFER_TIMEOUT_LENGTH = 90
    USE_COOKIES = No
    VERIFY_SSL_CERTIFICATES = No
    -> JSONFlattener_5
JSONFlattener_5
    ERROR_LIST_ATTR = _json_error
    JSON_DOCUMENT = @Value(_response_body2)
    READ_FROM_FILE = NO
    RECURSIVE = Yes
    -> AttributeExposer_11

Bookmark: Comment
Note: Please add terminator to ports were data should not go
FeatureMerger_6
    ATTR_ACCUM_MODE = Merge Supplier
    ATTR_CONFLICT_RES = Use Requestor
    IGNORE_NULLS = No
    JOIN_KEYS = @Value(_uuid) @Value(_uuid) AUTO
    LIST_ATTRS_TO_INCLUDE = geomcol geomtype trueid
    LIST_NAME = True_Ids
    MERGE_TYPE = Attributes Only
    PROCESS_DUPS = NO
    REJECT_NULL_MISSING_KEYS = No
    SUPPLIERS_FIRST = No
    MERGED -> AttributeRemover_11

Bookmark: COMMENT
Note: If the goal of this transformer is to read NB data, please split in 2 transformers. One to read NB portal and the other to filter datasets

Bookmark: COMMENTS
Note: Please add terminator to rejected ports

Bookmark: Comment
Note: more logging for rejected ports

FME custom transformer NB_MetadataMerger

Input (input)
    -> AttributeExposer_2
Note: Exposing ID and resource.type
AttributeExposer_2
    ATTR_LIST = resource.type,id,modifyingViewUid
    -> Tester
    -> FeatureMerger [REQUESTOR]
    -> AttributeExploder
Note: Creating attributes to be part of resource{} list
AttributeCreator_6
    ATTR_TABLE:
      SET_TO url = https://gnb.socrata.com/datasets/@Value(id)
      SET_TO format = HTML
    -> AttributeKeeper_5
AttributeKeeper_5
    KEEP_ATTRS = name,url,protocol,format,resourceType_fr,_seriesID,resourceType_en
    -> FeatureMerger_2 [SUPPLIER]
DuplicateFilter_2
    INPUT_ORDERED_CHOICE = No
    KEYATTR = id
    UNIQUE -> FeatureMerger [SUPPLIER]
Note: Removing from original record those considaret as an Advanced View of a dataset
FeatureMerger
    ATTR_ACCUM_MODE = Merge Supplier
    ATTR_CONFLICT_RES = Use Requestor
    IGNORE_NULLS = No
    JOIN_KEYS = @Value(id) @Value(id) AUTO
    MERGE_TYPE = Attributes Only
    PROCESS_DUPS = NO
    REJECT_NULL_MISSING_KEYS = No
    SUPPLIERS_FIRST = No
    UNMERGED_REQUESTOR -> FeatureMerger_2 [REQUESTOR]
    UNUSED_SUPPLIER -> Terminator
    <REJECTED> -> Terminator
Note: Transfering additional view to original resource
FeatureMerger_2
    ATTR_ACCUM_MODE = Merge Supplier
    ATTR_CONFLICT_RES = Use Requestor
    IGNORE_NULLS = No
    JOIN_KEYS = @Value(id) @Value(_seriesID) AUTO
    LIST_ATTRS_TO_INCLUDE = format url
    LIST_NAME = advancedViewResources
    MERGE_TYPE = Attributes Only
    PROCESS_DUPS = NO
    REJECT_NULL_MISSING_KEYS = No
    SUPPLIERS_FIRST = No
    MERGED -> Output (output)
    UNMERGED_REQUESTOR -> Output (output)
    UNUSED_SUPPLIER -> UnmergedAdvancedView (output)
    <REJECTED> -> Terminator_2
Output (output)
UnmergedAdvancedView (output)
Terminator_2
    MESSAGE = Translation Terminated
Terminator
    MESSAGE = Translation Terminated

Bookmark: Searching for source dataset in JSON attributes
Tester
    BOOL_OP = OR
    COMPOSITE_TEST = 1
    TEST_CLAUSE = TEST @Value(modifyingViewUid) != ""
    TEST_MODE = TEST
    PASSED -> AttributeRenamer
AttributeRenamer
    ATTR_TABLE = RENAME_SET_DEFAULT modifyingViewUid > _seriesID
    -> DuplicateFilter
    -> DuplicateFilter_2
Note: Exploding attributes to avoid list parser / 1 feature per attribute
AttributeExploder
    ATTR_NAME_LABEL = _attr_name
    ATTR_VALUE_LABEL = _seriesID
    EXPLODING_TYPE = Features
    KEEP_ATTRIBUTES = Yes
    KEEP_GEOMETRY = No
    -> AttributeKeeper_4
Note: Cleanup
AttributeKeeper_4
    KEEP_ATTRS = _seriesID,id,resource.type,_attr_name
    -> StringReplacer
Note: RegEx to remove list / {} in attribute name
StringReplacer
    CASE = NO
    FIND_TEXT = {[0-9]+}
    NO_MATCH = _FME_NO_OP_
    REGEXP = YES
    SRC_ATTRS = _attr_name
    -> Tester_7
Note: Only feature regarding / series.dataSource.datasetUid
Tester_7
    BOOL_OP = OR
    COMPOSITE_TEST = 1
    TEST_CLAUSE = TEST @Value(_attr_name) = displayFormat.visualizationCanvasMetadata.vifs.series.dataSource.datasetUid
    TEST_MODE = TEST
    PASSED -> DuplicateFilter_2
    PASSED -> DuplicateFilter
Note: Removing duplicates / based on / ID, restype,series source
Note: 1 feature by ID
DuplicateFilter
    INPUT_ORDERED_CHOICE = No
    KEYATTR = _seriesID id resource.type
    UNIQUE -> AttributeCreator_6

FME custom transformer NB_HrefResourceManager

fileparts (input)
    -> AttributeExposer_2
AttributeExposer_2
    ATTR_LIST = linkpart,outputVal,namePart
    -> ListBuilder
ListBuilder
    LIST_ATTRS_TO_INCLUDE = linkpart outputVal namePart
    LIST_NAME = filepartsList
    -> AttributeKeeper
AttributeKeeper
    KEEP_LIST = filepartsList{}.linkpart filepartsList{}.namePart filepartsList{}.outputVal
    -> FeatureMerger [SUPPLIER]
Input (input)
    -> AttributeExposer
AttributeExposer
    ATTR_LIST = resource.id,primaryAccessPointsList{},additionalAccessPointsList{},title,title_fr
    -> FeatureMerger [REQUESTOR]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeKeeper_2
    MERGED -> FeatureMerger_2 [REQUESTOR]
AttributeKeeper_2
    KEEP_ATTRS = title,resource.id,title_fr
    KEEP_LIST = additionalAccessPointsList{} filepartsList{}.linkpart filepartsList{}.namePart filepartsList{}.outputVal
    -> ListExploder
ListExploder
    ATTR_ACCUM_MODE = Merge List Attributes
    ATTR_CONFLICT_RES = Use List Attribute Values
    INDEX_ATTR = _element_index
    LIST_ATTR = additionalAccessPointsList{}
    ELEMENTS -> AttributeExposer_3
AttributeExposer_3
    ATTR_LIST = hrefUrlAccessPoint
    -> StringSearcher
StringSearcher
    CASE = no
    MATCHED_RESULT_ATTR = _first_match
    REGEXP = maps.arcgis.com
    STRING_TO_SEARCH = @Value(hrefUrlAccessPoint)
    MATCHED -> AttributeCreator
    NOT_MATCHED -> StringSearcher_2
AttributeCreator
    ATTR_TABLE:
      SET_TO url = @Value(hrefUrlAccessPoint)
      SET_TO format = Web App
      SET_TO namePart = Web App
    -> Junction
StringSearcher_2
    CASE = no
    MATCHED_RESULT_ATTR = _first_match
    REGEXP = .html
    STRING_TO_SEARCH = @Value(hrefUrlAccessPoint)
    MATCHED -> AttributeCreator_2
    NOT_MATCHED -> PythonCaller
AttributeCreator_2
    ATTR_TABLE:
      SET_TO url = @Value(hrefUrlAccessPoint)
      SET_TO format = HTML
      SET_TO namePart = HTML
    -> Junction
PythonCaller
    NEW_ATTRIBUTES = url format namePart
    PYTHONSOURCE:
      import fme
      import fmeobjects
      # Template Function interface:
      # When using this function, make sure its name is set as the value of
      # the 'Class or Function to Process Features' transformer parameter
      def processFeature(feature):
          linkParts = feature.getAttribute('filepartsList{}.linkpart')
          outVals = feature.getAttribute('filepartsList{}.outputVal')
          nameParts = feature.getAttribute('filepartsList{}.namePart')
          print(len(linkParts))
          print(len(outVals))
          print(len(nameParts))
          url = feature.getAttribute('hrefUrlAccessPoint')
          print(url)
          format = 'other'
          namePart = 'Other'
          for part in linkParts:
              print(part)
              if part in url:
                  format = outVals[linkParts.index(part)]
                  namePart = nameParts[linkParts.index(part)]
          feature.setAttribute('url',url)
          feature.setAttribute('format',format)
          feature.setAttribute('namePart',namePart)


      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> Junction
Junction
    -> DuplicateFilter
DuplicateFilter
    INPUT_ORDERED_CHOICE = No
    KEYATTR = resource.id format url
    UNIQUE -> AttributeCreator_3
AttributeCreator_3
    ATTR_TABLE = SET_TO name = @Value(title) - @Value(namePart)
    -> Tester_2
Tester_2
    BOOL_OP = OR
    COMPOSITE_TEST = 1
    TEST_CLAUSE = TEST title_fr ATTRIBUTE_HAS_A_VALUE ""
    TEST_MODE = TEST
    PASSED -> AttributeCreator_5
    FAILED -> AttributeCreator_4
AttributeCreator_5
    ATTR_TABLE = SET_TO name_fr = @Value(title_fr) - @Value(namePart)
    -> FeatureMerger_2 [SUPPLIER]
AttributeCreator_4
    ATTR_TABLE = SET_TO name_fr = FME_NULL_VALUE
    -> FeatureMerger_2 [SUPPLIER]
FeatureMerger_2
    ATTR_ACCUM_MODE = Merge Supplier
    ATTR_CONFLICT_RES = Use Requestor
    IGNORE_NULLS = No
    JOIN_KEYS = @Value(resource.id) @Value(resource.id) AUTO
    LIST_ATTRS_TO_INCLUDE = format name name_fr url
    LIST_NAME = hrefResources
    MERGE_TYPE = Attributes Only
    PROCESS_DUPS = NO
    REJECT_NULL_MISSING_KEYS = No
    SUPPLIERS_FIRST = No
    MERGED -> AttributeRemover
AttributeRemover
    LIST_ATTRS = filepartsList{} primaryAccessPointsList{}
    REMOVE_ATTRS = _element_index,namePart,name_fr,name,_first_match,format
    -> Output (output)
Output (output)

FME custom transformer EMPTY_FORMAT_MAPPER

DATA_INPUT (input)
    -> AttributeExposer_2
AttributeExposer_2
    ATTR_LIST = resources{}.format,id,resources{}.url
    -> ListElementCounter
ListElementCounter
    CNT_ATTR = _element_count
    LIST_NAME = resources{}
    -> PythonCaller
PythonCaller
    NEW_ATTRIBUTES = assignation
    PYTHONSOURCE:
      import fme
      import fmeobjects
      # Template Function interface:
      # When using this function, make sure its name is set as the value of
      # the 'Class or Function to Process Features' transformer parameter
      def processFeature(feature):
          for i in range(int(feature.getAttribute('_element_count'))):

              format=feature.getAttribute('resources{%d}.format'%(i))
              if not format:
                  url=feature.getAttribute('resources{%d}.url'%(i))

                  if not url:
                      new_format='other'
                  else:
                      if r'service=wms' in url.lower():
                          new_format='WMS'
                          #feature.setAttribute('assignation',new_format)
                      elif r'mapserver' in url.lower():
                          new_format='ESRI REST'
                          #feature.setAttribute('assignation',new_format)
                      else:
                          try:
                              if len(url.split(r'/')[-1].split('.'))>1:
                                  if len(url.split(r'/')[-1].split('.')[-1])<10:
                                      new_format=url.split(r'/')[-1].split('.')[-1]
                                      #feature.setAttribute('assignation',new_format)
                                  else:
                                      new_format='other'
                                      #feature.setAttribute('assignation',new_format)

                              else:
                                  new_format='other'
                                  #feature.setAttribute('assignation',new_format)


                          except:
                              new_format='other'





                  feature.setAttribute('resources{%d}.format'%(i),new_format)
    PYTHONSYMBOL = processFeature
    -> DATA_OUTPUT (output)
DATA_OUTPUT (output)

FME custom transformer NB_Resource_Type_Filter

AttributeFilter
    ATTR_NAME = assetType
    ATTR_VALUES = <Empty>,<Missing>,<Null>,<Unfiltered>,map,dataset,href
    map -> Tester_2
    dataset -> Tester_2
    href -> FeatureMerger [REQUESTOR]
Tester_3
    BOOL_OP = OR
    COMPOSITE_TEST = 1
    TEST_CLAUSE = TEST @Value(geostatus) = Yes
    TEST_MODE = TEST
    PASSED -> Geospatial_Assets (output)
    FAILED -> nonGeoDataset_assets (output)
Note: geospatial dataset output
Geospatial_Assets (output)
Note: non-geospatial dataset output
nonGeoDataset_assets (output)

Bookmark: Attach List of Geospatial Data Types
Geospatial_Datatypes_Lookup_Table (input)
    -> AttributeExposer_6
AttributeExposer_6
    ATTR_LIST = datatype
    -> ListBuilder
ListBuilder
    LIST_ATTRS_TO_INCLUDE = datatype
    LIST_NAME = _list
    -> ListConcatenator
ListConcatenator
    DROP_EMPTY_PARTS = No
    LIST_ATTR = _list{}.datatype
    SEP = |
    VAL_ATTR = datatypes_concat
    -> AttributeKeeper_3
AttributeKeeper_3
    KEEP_ATTRS = datatypes_concat
    -> FeatureMerger_4 [SUPPLIER]
Input (input)
    -> AttributeExposer_4
AttributeExposer_4
    ATTR_LIST = assetType,resource.id,childViews{},category,metadata.additionalAccessPoints{}.description
    -> FeatureMerger_4 [REQUESTOR]
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> FeatureMerger_5 [REQUESTOR]
    UNMERGED_REQUESTOR -> Terminator_6
    UNUSED_SUPPLIER -> Terminator_6
    <REJECTED> -> Terminator_6
Terminator_6
    MESSAGE = Translation Terminated

Bookmark: Remove Datasets in NB_REMOVE
Dataset_Removal_Table (input)
    -> AttributeExposer_3
AttributeExposer_3
    ATTR_LIST = dataid
    -> FeatureMerger_5 [SUPPLIER]
FeatureMerger_5
    ATTR_ACCUM_MODE = Merge Supplier
    ATTR_CONFLICT_RES = Use Requestor
    IGNORE_NULLS = No
    JOIN_KEYS = @Value(resource.id) @Value(dataid) AUTO
    MERGE_TYPE = Attributes Only
    PROCESS_DUPS = NO
    REJECT_NULL_MISSING_KEYS = No
    SUPPLIERS_FIRST = No
    UNMERGED_REQUESTOR -> AttributeFilter

Bookmark: Map Processing
Tester_2
    BOOL_OP = OR
    COMPOSITE_TEST = 1
    TEST_CLAUSE = TEST childViews{0} ATTRIBUTE_HAS_A_VALUE ""
    TEST_MODE = TEST
    PASSED -> UUIDGenerator_4
    FAILED -> AttributeExposer_2
UUIDGenerator_4
    UUID_ATTR = _uuid
    -> AttributeKeeper_5
    -> FeatureMerger_6 [REQUESTOR]
AttributeKeeper_5
    KEEP_ATTRS = datatypes_concat,_uuid
    KEEP_LIST = childViews{}
    -> ListExploder_5
ListExploder_5
    ATTR_ACCUM_MODE = Merge List Attributes
    ATTR_CONFLICT_RES = Use List Attribute Values
    INDEX_ATTR = _element_index
    LIST_ATTR = childViews{}
    ELEMENTS -> HTTPCaller_7
HTTPCaller_7
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body2
    TARGET_ATTR_ENCODING = auto-detect
    TARGET_URL = https://gnb.socrata.com/api/views/@Value(childViews).json
    TRANSFER_TIMEOUT_LENGTH = 90
    USE_COOKIES = No
    VERIFY_SSL_CERTIFICATES = No
    -> JSONFlattener_5
JSONFlattener_5
    ERROR_LIST_ATTR = _json_error
    JSON_DOCUMENT = @Value(_response_body2)
    READ_FROM_FILE = NO
    RECURSIVE = Yes
    -> AttributeExposer_11
AttributeExposer_11
    ATTR_LIST = columns{}.fieldName,columns{}.dataTypeName,name
    -> PythonCaller_3
PythonCaller_3
    PYTHONSOURCE:
      import fme
      import fmeobjects
      # Template Function interface:
      # When using this function, make sure its name is set as the value of
      # the 'Class or Function to Process Features' transformer parameter
      def processFeature(feature):
          _list = feature.getAttribute('columns{}.dataTypeName')
          _outlist =  [x.lower() for x in _list]
          for i in range (len(_outlist)):
              feature.setAttribute('columns{{{}}}.dataTypeName'.format(i),_outlist[i])

      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = FeatureProcessor
    -> ListSearcher_2
ListSearcher_2
    ATTR_VALUE = (@Value(datatypes_concat))
    INDEX_ATTR = geomidx
    LIST_ATTR = columns{}.dataTypeName
    MATCHTYPE = REGULAR_EXPRESSION_ENCODED
    FOUND -> AttributeCreator_5
    NOT_FOUND -> AttributeCreator_3
AttributeCreator_5
    ATTR_TABLE:
      SET_TO geomcol = @Value(columns{@Value(geomidx)}.fieldName)
      SET_TO geomtype = @Value(columns{@Value(geomidx)}.dataTypeName)
      SET_TO layerid = @Value(childViews)
      SET_TO geostatus = Yes
    -> AttributeKeeper
AttributeCreator_3
    ATTR_TABLE = SET_TO geostatus = No
    -> AttributeKeeper
AttributeKeeper
    KEEP_ATTRS = layerid,name,geomtype,geostatus,geomcol,_uuid
    -> FeatureMerger_6 [SUPPLIER]
FeatureMerger_6
    ATTR_ACCUM_MODE = Merge Supplier
    ATTR_CONFLICT_RES = Use Requestor
    IGNORE_NULLS = No
    JOIN_KEYS = @Value(_uuid) @Value(_uuid) AUTO
    LIST_ATTRS_TO_INCLUDE = geomcol geomtype name layerid
    LIST_NAME = dataLayers
    MERGE_TYPE = Attributes Only
    PROCESS_DUPS = NO
    REJECT_NULL_MISSING_KEYS = No
    SUPPLIERS_FIRST = No
    MERGED -> Tester_3
AttributeExposer_2
    ATTR_LIST = columns{}.fieldName,columns{}.dataTypeName,name
    -> PythonCaller_2
PythonCaller_2
    PYTHONSOURCE:
      import fme
      import fmeobjects
      # Template Function interface:
      # When using this function, make sure its name is set as the value of
      # the 'Class or Function to Process Features' transformer parameter
      def processFeature(feature):
          _list = feature.getAttribute('columns{}.dataTypeName')
          _outlist =  [x.lower() for x in _list]
          for i in range (len(_outlist)):
              feature.setAttribute('columns{{{}}}.dataTypeName'.format(i),_outlist[i])

      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = FeatureProcessor
    -> ListSearcher_4
ListSearcher_4
    ATTR_VALUE = (@Value(datatypes_concat))
    INDEX_ATTR = geomidx
    LIST_ATTR = columns{}.dataTypeName
    MATCHTYPE = REGULAR_EXPRESSION_ENCODED
    FOUND -> AttributeCreator_6
    NOT_FOUND -> AttributeCreator_7
AttributeCreator_6
    ATTR_TABLE:
      SET_TO dataLayers{0}.geomcol = @Value(columns{@Value(geomidx)}.fieldName)
      SET_TO dataLayers{0}.geomtype = @Value(columns{@Value(geomidx)}.dataTypeName)
      SET_TO dataLayers{0}.layerid = @Value(resource.id)
      SET_TO dataLayers{0}.geostatus = Yes
      SET_TO geostatus = Yes
    -> Tester_3
AttributeCreator_7
    ATTR_TABLE = SET_TO geostatus = No
    -> Tester_3

Bookmark: HREF Handling
External_Link_Geo_File_Types (input)
    -> AttributeExposer
AttributeExposer
    ATTR_LIST = Filetype
    -> ListBuilder_2
ListBuilder_2
    LIST_ATTRS_TO_INCLUDE = Filetype
    LIST_NAME = filetypelist
    -> ListConcatenator_3
ListConcatenator_3
    DROP_EMPTY_PARTS = No
    LIST_ATTR = filetypelist{}.Filetype
    SEP = |
    VAL_ATTR = filetypes_concat
    -> AttributeKeeper_2
AttributeKeeper_2
    KEEP_ATTRS = filetypes_concat
    -> FeatureMerger [SUPPLIER]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Tester
Tester
    BOOL_OP = OR
    COMPOSITE_TEST = 1 OR 2
    TEST_CLAUSE:
      TEST @Value(category) = Geographic Data
      TEST @Value(category) = Lidar
    TEST_MODE = TEST
    PASSED -> AttributeCreator_2
    FAILED -> ListSearcher_3
ListSearcher_3
    ATTR_VALUE = (@Value(filetypes_concat))
    INDEX_ATTR = geomidx
    LIST_ATTR = metadata.additionalAccessPoints{}.description
    MATCHTYPE = REGULAR_EXPRESSION_ENCODED
    FOUND -> AttributeCreator_2
    NOT_FOUND -> AttributeCreator_4
AttributeCreator_2
    ATTR_TABLE = SET_TO geostatus = Yes
    -> Geospatial_Assets (output)
AttributeCreator_4
    ATTR_TABLE = SET_TO geostatus = No
    -> nonGeoDataset_assets (output)

FME custom transformer NB_ESRIMAPPER

Parameters:
- FME_PROCESS_GROUPS_ORDERED = No   # Process At End (Blocking),No%Process When Group Changes (Advanced),Yes Group By Mode

Input (input)
    -> AttributeExposer_2
AttributeExposer_2
    ATTR_LIST = resource.id,title,title_fr
    -> FeatureMerger [REQUESTOR]
ESRI_LOOKUP (input)
    -> AttributeExposer
AttributeExposer
    ATTR_LIST = EsriLink,idval,Layertype
    -> FeatureMerger [SUPPLIER]
FeatureMerger
    ATTR_ACCUM_MODE = Merge Supplier
    ATTR_CONFLICT_RES = Use Requestor
    IGNORE_NULLS = No
    JOIN_KEYS = @Value(resource.id) @Value(idval) AUTO
    LIST_ATTRS_TO_INCLUDE = EsriLink Layertype
    LIST_NAME = ESRILIST
    MERGE_TYPE = Attributes Only
    PROCESS_DUPS = NO
    REJECT_NULL_MISSING_KEYS = No
    SUPPLIERS_FIRST = No
    MERGED -> UUIDGenerator
    UNMERGED_REQUESTOR -> Output (output)
UUIDGenerator
    UUID_ATTR = joinuuidkey
    -> AttributeKeeper
    -> FeatureMerger_2 [REQUESTOR]
AttributeKeeper
    KEEP_ATTRS = title,joinuuidkey,title_fr
    KEEP_LIST = ESRILIST{}
    -> ListExploder
ListExploder
    ATTR_ACCUM_MODE = Merge List Attributes
    ATTR_CONFLICT_RES = Use List Attribute Values
    INDEX_ATTR = _element_index
    LIST_ATTR = ESRILIST{}
    ELEMENTS -> Tester
Tester
    BOOL_OP = OR
    COMPOSITE_TEST = 1
    TEST_CLAUSE = TEST @Value(Layertype) = multi
    TEST_MODE = TEST
    PASSED -> AttributeCreator_3
    FAILED -> AttributeCreator
AttributeCreator_3
    ATTR_TABLE = SET_TO esrirestlink = @Value(EsriLink)
    -> HTTPCaller
AttributeCreator
    ATTR_TABLE = SET_TO esrirestlink = @Value(EsriLink)
    -> PythonCaller
PythonCaller
    PYTHONSOURCE:
      import fme
      import fmeobjects
      # Template Function interface:
      # When using this function, make sure its name is set as the value of
      # the 'Class or Function to Process Features' transformer parameter
      def processFeature(feature):
          link = feature.getAttribute("esrirestlink")
          link = link.rsplit('/',1)[0]
          feature.setAttribute('esrirestlink',link)
      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> HTTPCaller
HTTPCaller
    CONNECTION_TIMEOUT_LENGTH = 60
    ERROR_ATTR = _error
    FOLLOW_REDIRECTS = Yes
    HTTP_METHOD = GET
    SAVE_FILE = Attribute
    STATUS_CODE_ATTR = _http_status_code
    TARGET_ATTR = ESRIJSONR
    TARGET_ATTR_ENCODING = auto-detect
    TARGET_URL = @Value(esrirestlink)?f=pjson
    TRANSFER_TIMEOUT_LENGTH = 90
    USE_COOKIES = No
    VERIFY_SSL_CERTIFICATES = No
    -> Tester_3
    <REJECTED> -> Invalid_ESRI_URL (output)
Tester_3
    BOOL_OP = OR
    COMPOSITE_TEST = 1
    TEST_CLAUSE = CASE_INSENSITIVE_TEST @Value(ESRIJSONR) CONTAINS   "message": "Invalid URL",
    TEST_MODE = CASE_INSENSITIVE_TEST
    PASSED -> Invalid_ESRI_URL (output)
    FAILED -> JSONFlattener
JSONFlattener
    ERROR_LIST_ATTR = _json_error
    JSON_DOCUMENT = @Value(ESRIJSONR)
    NEW_ATTRIBUTES = spatialReference.latestWkid
    READ_FROM_FILE = NO
    RECURSIVE = Yes
    -> AttributeKeeper_2
AttributeKeeper_2
    KEEP_ATTRS = title,joinuuidkey,spatialReference.latestWkid,EsriLink,_element_index,title_fr
    -> AttributeCreator_2
AttributeCreator_2
    ATTR_TABLE:
      SET_TO format = ESRI REST
      SET_TO url = @Value(EsriLink)
      SET_TO name = @Value(title) ESRI REST @Value(_element_index)
      SET_TO projection_name = EPSG:@Value(spatialReference.latestWkid)
      SET_TO projection_system = EPSG
      SET_TO projection_system_version = unknown
    -> Tester_2
Tester_2
    BOOL_OP = OR
    COMPOSITE_TEST = 1
    TEST_CLAUSE = TEST title_fr ATTRIBUTE_HAS_A_VALUE ""
    TEST_MODE = TEST
    PASSED -> AttributeCreator_4
    FAILED -> AttributeCreator_5
AttributeCreator_4
    ATTR_TABLE = SET_TO name_fr = @Value(title) ESRI REST @Value(_element_index)
    -> AttributeKeeper_3
    -> AttributeKeeper_4
AttributeCreator_5
    ATTR_TABLE = SET_TO name_fr = FME_NULL_VALUE
    -> AttributeKeeper_4
    -> AttributeKeeper_3
AttributeKeeper_3
    KEEP_ATTRS = format,joinuuidkey,url,name,name_fr
    -> FeatureMerger_2 [SUPPLIER]
FeatureMerger_2
    ATTR_ACCUM_MODE = Merge Supplier
    ATTR_CONFLICT_RES = Use Requestor
    IGNORE_NULLS = No
    JOIN_KEYS = @Value(joinuuidkey) @Value(joinuuidkey) AUTO
    LIST_ATTRS_TO_INCLUDE = format name url name_fr
    LIST_NAME = esriresources
    MERGE_TYPE = Attributes Only
    PROCESS_DUPS = NO
    REJECT_NULL_MISSING_KEYS = No
    SUPPLIERS_FIRST = No
    MERGED -> FeatureMerger_3 [REQUESTOR]
AttributeKeeper_4
    KEEP_ATTRS = projection_system_version,projection_name,joinuuidkey,projection_system
    -> FeatureMerger_3 [SUPPLIER]
FeatureMerger_3
    ATTR_ACCUM_MODE = Merge Supplier
    ATTR_CONFLICT_RES = Use Requestor
    IGNORE_NULLS = No
    JOIN_KEYS = @Value(joinuuidkey) @Value(joinuuidkey) AUTO
    LIST_ATTRS_TO_INCLUDE = projection_name projection_system projection_system_version
    LIST_NAME = esriprojectionlist
    MERGE_TYPE = Attributes Only
    PROCESS_DUPS = NO
    REJECT_NULL_MISSING_KEYS = No
    SUPPLIERS_FIRST = No
    MERGED -> PythonCaller_2
Note: Merge SpatialRef
PythonCaller_2
    NEW_ATTRIBUTES = spatialref{}.projection_name spatialref{}.projection_system spatialref{}.projection_system_version
    PYTHONSOURCE:
      import fme
      import fmeobjects
      logger = fmeobjects.FMELogFile()
      # Template Function interface:
      # When using this function, make sure its name is set as the value of
      # the 'Class or Function to Process Features' transformer parameter
      def processFeature(feature):
          spatialRefName = feature.getAttribute('spatialref{}.projection_name')
          spatialRefSystem = feature.getAttribute('spatialref{}.projection_system')
          spatialRefVersion = feature.getAttribute('spatialref{}.projection_system_version')
          esriSpatialRefName = feature.getAttribute('esriprojectionlist{}.projection_name')
          esriSpatialRefSystem = feature.getAttribute('esriprojectionlist{}.projection_system')
          esriSpatialRefVersion = feature.getAttribute('esriprojectionlist{}.projection_system_version')
          names = spatialRefName + esriSpatialRefName
          systems = spatialRefSystem + esriSpatialRefSystem
          versions = spatialRefVersion + esriSpatialRefVersion
          length = len(names)
          count = 0

          for i in range(length):
              feature.setAttribute("spatialref{%s}.projection_name" %count,names[i])
              feature.setAttribute("spatialref{%s}.projection_system" %count, systems[i])
              feature.setAttribute("spatialref{%s}.projection_system_version" %count,versions[i])
              count += 1
    PYTHONSYMBOL = processFeature
    -> AttributeRemover
AttributeRemover
    LIST_ATTRS = ESRILIST{} esriprojectionlist{}
    -> Output (output)
Output (output)
Invalid_ESRI_URL (output)

FME custom transformer DistributionListGenerator

Input (input)
    -> UUIDGenerator
UUIDGenerator
    UUID_ATTR = joinkeyuuid
    -> AttributeKeeper
    -> FeatureMerger [REQUESTOR]
AttributeKeeper
    KEEP_ATTRS = joinkeyuuid
    KEEP_LIST = resources{}.format
    -> ListExploder
ListExploder
    ATTR_ACCUM_MODE = Merge List Attributes
    ATTR_CONFLICT_RES = Use List Attribute Values
    INDEX_ATTR = _element_index
    LIST_ATTR = resources{}
    ELEMENTS -> AttributeRemover
AttributeRemover
    REMOVE_ATTRS = _element_index
    -> FeatureMerger [SUPPLIER]
FeatureMerger
    ATTR_ACCUM_MODE = Merge Supplier
    ATTR_CONFLICT_RES = Use Requestor
    IGNORE_NULLS = No
    JOIN_KEYS = @Value(joinkeyuuid) @Value(joinkeyuuid) AUTO
    LIST_ATTRS_TO_INCLUDE = format
    LIST_NAME = distributionList
    MERGE_TYPE = Attributes Only
    PROCESS_DUPS = NO
    REJECT_NULL_MISSING_KEYS = No
    SUPPLIERS_FIRST = No
    MERGED -> ListDuplicateRemover_2
Note: remove duplicate distribution formats
ListDuplicateRemover_2
    SRC_LIST = distributionList{}.format
    -> AttributeRemover_2
AttributeRemover_2
    REMOVE_ATTRS = joinkeyuuid
    -> Output (output)
Output (output)

FME custom transformer ListSlicer_2
Replaces an existing list with a list containing elements of the slicing range which is determined by the starting index and the number of elements.
If the source list was a structured one like "_list{}.foo", "_list{}.bar", all the members belonging to the same base name will be replaced.
Example
When the source list contains:
_list{0}.foo = '0'
_list{1}.foo = '1'
_list{2}.foo = '2'
_list{3}.foo = '3'
_list{4}.foo = '4'
_list{0}.bar = 'A'
_list{1}.bar = 'B'
_list{2}.bar = 'C'
_list{3}.bar = 'D'
_list{4}.bar = 'E'
After slicing with Starting Element Index = 1 and Number of Elements to Slice = 3, the list will be replaced with:
_list{0}.foo = '1'
_list{1}.foo = '2'
_list{2}.foo = '3'
_list{0}.bar = 'B'
_list{1}.bar = 'C'
_list{2}.bar = 'D'
Note: This transformer contains a Python script which was tested with both Python 2.7 interpreter and Python 3.6 interpreter.
Parameters
    Source List Attribute:
Select a source list attribute to be sliced.
    Starting Element Index:
Specify index of the element to start slicing. The index is always 0-based.
If specified index is less than 0, this transformer considers the starting index as 0.
    Number of Elements to Slice:
Specify the number of elements to be sliced.
If specified number is equal to 0, this transformer removes every element from the source list (i.e. removes the source list).
If specified number is less than 0, this transformer considers the number as 0.
    Null Elements Treatment:
Select how treat <null> elements in the slicing range.
"Replace with Empty String" - Every <null> element will be replaced with an empty string.
"Replace with New Value" - Every <null> element will be replaced with a value specified as New Value for Null parameter.
"Replace with Missing" - Every <null> element will be removed. The element will be missing in the resultant list.
"Leave Null" - Every <null> element will be left in the resultant list as <null>.
    New Value for Null:
Specify a value to be used for replacing <null> elements.
This parameter is used only if you selected "Replace with New Value" to Null Elements Treatment. Otherwise, it'll be just ignored.
    Missing Elements Treatment:
Select how treat <missing> elements in the slicing range.
"Replace with Empty String" - Every <missing> element will be replaced with an empty string.
"Replace with New Value" - Every <missing> element will be replaced with a value specified as New Value for Missing parameter.
"Replace with Null" - Every <missing> element will be replaced with <null>.
"Leave Missing" - Every <missing> element will be still missing in the resultant list.
    New Value for Missing:
Specify a value to be used for replacing <missing> elements.
This parameter is used only if you selected "Replace with New Value" to Missing Elements Treatment. Otherwise, it'll be just ignored.

Parameters:
- SRC_LIST =   # " " Source List Attribute
- START_INDEX = 0   # Starting Element Index
- NUM_ELEMENTS =   # Number of Elements to Slice
- NULL_TREATMENT = empty
- NEWVALUE_FOR_NULL =   # New Value for Null
- MISSING_TREATMENT = empty
- NEWVALUE_FOR_MISSING =   # New Value for Missing

Input (input)
    -> ParameterFetcher
ParameterFetcher
    ATTR_LIST = __listslicer.src_list {$(SRC_LIST)} __listslicer.start_index {$(START_INDEX)} __listslicer.num_elements {$(NUM_ELEMENTS)} __listslicer.null_treat {$(NULL_TREATMENT)} __listslicer.newvalue_for_null {$(NEWVALUE_FOR_NULL)} __listslicer.missing_treat {$(MISSING_TREATMENT)} __listslicer.newvalue_for_missing {$(NEWVALUE_FOR_MISSING)}
    -> PythonCaller
PythonCaller
    HIDE_ATTRIBUTES = __listslicer.src_list __listslicer.start_index __listslicer.num_elements __listslicer.null_treat __listslicer.newvalue_for_null __listslicer.missing_treat __listslicer.newvalue_for_missing
    PYTHONSOURCE:
      # 2014-07-27, Takashi Iijima, Original Implementation
      # 2014-08-02, Takashi Iijima, Resolved encoding issue on list name
      # 2018-06-14, Takashi Iijima, Updated to support both Python 2.7 and Python 3.x
      # 2020-04-30, Takashi Iijima, Changed default Python interpreter version to 3.x, saved with FME 2017.1.2.1

      import fmeobjects, re

      class ListSlicer(object):
          def __init__(self):
              import platform
              if platform.python_version_tuple()[0] == '2':
                  import locale
                  loc = locale.getdefaultlocale()
                  enc = loc[1] if loc else 'utf_8'
                  self.toStr = lambda s: s.encode(enc) if isinstance(s, unicode) else s
              else:
                  self.toStr = lambda s: s

          def input(self, feature):
              listName = self.toStr(feature.getAttribute('__listslicer.src_list'))
              prefix = listName[:-2]
              regexListElement = re.compile(r'^%s\{(\d+)\}(.*)$' % prefix)

              # Find maximum element index and collect suffixes of target list members.
              maxIndex = -1
              suffixes = set([])
              for name in [self.toStr(s) for s in feature.getAllAttributeNames()]:
                  m = regexListElement.match(name)
                  if m:
                      if maxIndex < int(m.group(1)):
                          maxIndex = int(m.group(1))
                      suffixes.add(self.toStr(m.group(2)))

              startIndex = int(feature.getAttribute('__listslicer.start_index'))
              if startIndex < 0:
                  startIndex = 0
              numElements = int(feature.getAttribute('__listslicer.num_elements'))
              if numElements < 0:
                  numElements = 0

              nullTreat = feature.getAttribute('__listslicer.null_treat')
              newValueToNull = feature.getAttribute('__listslicer.newvalue_for_null')

              missingTreat = feature.getAttribute('__listslicer.missing_treat')
              newValueToMissing = feature.getAttribute('__listslicer.newvalue_for_missing')

              for suffix in suffixes:
                  # Move elements from slicing range to head of the list.
                  for i in range(numElements):
                      srcName = '%s{%d}%s' % (prefix, startIndex + i, suffix)
                      destName = '%s{%d}%s' % (prefix, i, suffix)

                      isNull, isMissing, type = feature.getAttributeNullMissingAndType(srcName)
                      if isNull:
                          if nullTreat == 'empty':
                              feature.setAttribute(destName, '')
                          elif nullTreat == 'newvalue':
                              feature.setAttribute(destName, newValueToNull)
                          elif nullTreat == 'missing':
                              feature.removeAttribute(destName)
                          elif nullTreat == 'as_is':
                              feature.setAttributeNullWithType(destName, type)
                          else:
                              raise fmeobjects.FMEException('Debug error: Null Treatment')

                      elif isMissing:
                          if missingTreat == 'empty':
                              feature.setAttribute(destName, '')
                          elif missingTreat == 'newvalue':
                              feature.setAttribute(destName, newValueToMissing)
                          elif missingTreat == 'null':
                              feature.setAttributeNullWithType(destName, type)
                          elif missingTreat == 'as_is':
                              feature.removeAttribute(destName)
                          else:
                              raise fmeobjects.FMEException('Debug error: Missing Treatment')

                      else:
                          feature.setAttribute(destName, feature.getAttribute(srcName))

                  # Remove excess elements.
                  for i in range(numElements, maxIndex + 1):
                      feature.removeAttribute('%s{%d}%s' % (prefix, i, suffix))

              feature.removeAttrsWithPrefix('__listslicer.')
              self.pyoutput(feature)

          def close(self):
              pass
    PYTHONSYMBOL = ListSlicer
    -> Output (output)
Output (output)

FME custom transformer NB_FrenchEnglishTitleDescSeparator

Note: cleanup
AttributeRemover_5
    LIST_ATTRS = name_list{}
    REMOVE_ATTRS = slashuuid,name_ct
    -> Feature_Output (output)
Feature_Output (output)
Note: NB descriptions are bilingual within a single text field, separated by a slash. however, there may be slashes in the descriptions that do not separate languages. this reads from a lookup table which gets the index of the slash which separates languages, starting at 0, for any datasets which have more than one slash in their description. it then separates the french description into attribute notes_fr aand the french title into title_fr. it ALSO renames resource.name to title and reslurce.description to notes. datasets without french translations will be returned as null.
Terminator_3
    MESSAGE = Translation Terminated

Bookmark: Separate French Description Parts
Feature_Input (input)
    -> AttributeExposer
AttributeExposer
    ATTR_LIST = resource.id,description,name
    -> AttributeSplitter_2
AttributeSplitter_2
    ATTR_NAME = description
    DELIMITER = /
    DROP_EMPTY_PARTS = No
    LIST_NAME = desc_list
    TRIM_OPTION = Both
    -> ListElementCounter_2
ListElementCounter_2
    CNT_ATTR = slash_count
    LIST_NAME = desc_list{}
    -> Tester_6
Tester_6
    BOOL_OP = OR
    COMPOSITE_TEST = 1
    TEST_CLAUSE = TEST @Value(slash_count) <= 2
    TEST_MODE = TEST
    PASSED -> AttributeCreator_7
    FAILED -> FeatureMerger [REQUESTOR]
AttributeCreator_7
    ATTR_TABLE = SET_TO sepidx = 0
    -> UUIDGenerator_2
SlashLocationSheet (input)
    -> AttributeExposer_2
AttributeExposer_2
    ATTR_LIST = dataid,lang_sep_pos
    -> FeatureMerger [SUPPLIER]
FeatureMerger
    ATTR_ACCUM_MODE = Merge Supplier
    ATTR_CONFLICT_RES = Use Requestor
    IGNORE_NULLS = No
    JOIN_KEYS = @Value(resource.id) @Value(dataid) AUTO
    MERGE_TYPE = Attributes Only
    PROCESS_DUPS = NO
    REJECT_NULL_MISSING_KEYS = No
    SUPPLIERS_FIRST = No
    MERGED -> AttributeCreator_3
    UNMERGED_REQUESTOR -> MULTIPLE_UNCAUGHT_SLASH_IN_DESC (output)
    <REJECTED> -> Terminator_2
AttributeCreator_3
    ATTR_TABLE = SET_TO sepidx = @Value(lang_sep_pos)
    -> UUIDGenerator_2
UUIDGenerator_2
    UUID_ATTR = slashuuid
    -> AttributeKeeper_2
    -> AttributeRemover_2
AttributeRemover_2
    LIST_ATTRS = desc_list{}
    REMOVE_ATTRS = slash_count,sepidx,dataid,lang_sep_pos
    -> FeatureMerger_7 [REQUESTOR]
AttributeKeeper_2
    KEEP_ATTRS = slashuuid,sepidx
    KEEP_LIST = desc_list{}
    -> ListExploder_2
ListExploder_2
    ATTR_ACCUM_MODE = Merge List Attributes
    ATTR_CONFLICT_RES = Use List Attribute Values
    INDEX_ATTR = desc_idx
    LIST_ATTR = desc_list{}
    ELEMENTS -> Tester_3
    <REJECTED> -> Terminator
Tester_3
    BOOL_OP = OR
    COMPOSITE_TEST = 1
    TEST_CLAUSE = TEST @Value(desc_idx) <= @Value(sepidx)
    TEST_MODE = TEST
    PASSED -> ListBuilder
    FAILED -> ListBuilder_3
ListBuilder
    GROUP_BY = slashuuid
    LIST_ATTRS_TO_INCLUDE = desc_list
    LIST_NAME = desclist
    -> ListConcatenator
ListConcatenator
    DROP_EMPTY_PARTS = No
    LIST_ATTR = desclist{}.desc_list
    SEP = /
    VAL_ATTR = notes
    -> AttributeKeeper_3
ListBuilder_3
    GROUP_BY = slashuuid
    LIST_ATTRS_TO_INCLUDE = desc_list
    LIST_NAME = desclist_fr
    -> ListConcatenator_6
ListConcatenator_6
    DROP_EMPTY_PARTS = No
    LIST_ATTR = desclist_fr{}.desc_list
    SEP = /
    VAL_ATTR = notes_fr
    -> AttributeKeeper_3
AttributeKeeper_3
    KEEP_ATTRS = notes,notes_fr,slashuuid
    -> FeatureMerger_7 [SUPPLIER]
FeatureMerger_7
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(slashuuid) @Value(slashuuid) AUTO
    MERGE_TYPE = Attributes Only
    PROCESS_DUPS = YES
    REJECT_NULL_MISSING_KEYS = No
    SUPPLIERS_FIRST = No
    MERGED -> AttributeSplitter_3
    <REJECTED> -> Terminator_3
Terminator
    MESSAGE = Translation Terminated
MULTIPLE_UNCAUGHT_SLASH_IN_DESC (output)
Terminator_2
    MESSAGE = Translation Terminated

Bookmark: Remove French Title Parts
AttributeSplitter_3
    ATTR_NAME = name
    DELIMITER = /
    DROP_EMPTY_PARTS = No
    LIST_NAME = name_list
    TRIM_OPTION = Both
    -> ListElementCounter
ListElementCounter
    CNT_ATTR = name_ct
    LIST_NAME = name_list{}
    -> Tester_5
Tester_5
    BOOL_OP = OR
    COMPOSITE_TEST = 1
    TEST_CLAUSE = TEST @Value(name_ct) > 1
    TEST_MODE = TEST
    PASSED -> AttributeCreator_6
    FAILED -> AttributeCreator_8
AttributeCreator_6
    ATTR_TABLE:
      SET_TO title = @Value(name_list{0})
      SET_TO title_fr = @Value(name_list{1})
    -> AttributeRemover_5
AttributeCreator_8
    ATTR_TABLE:
      SET_TO title = @Value(name_list{0})
      SET_TO title_fr = FME_NULL_VALUE
    -> AttributeRemover_5

FME custom transformer advancedViewResourceMapper

Input (input)
    -> AttributeExposer
AttributeExposer
    ATTR_LIST = advancedViewResources{},title,title_fr
    -> UUIDGenerator
UUIDGenerator
    UUID_ATTR = adviewuuid
    -> Tester
Tester
    BOOL_OP = OR
    COMPOSITE_TEST = 1
    TEST_CLAUSE = TEST advancedViewResources{0}.url ATTRIBUTE_HAS_A_VALUE ""
    TEST_MODE = TEST
    PASSED -> AttributeRemover
    PASSED -> AttributeKeeper
    FAILED -> Output (output)
AttributeRemover
    LIST_ATTRS = advancedViewResources{}
    -> FeatureMerger [REQUESTOR]
AttributeKeeper
    KEEP_ATTRS = title,adviewuuid,title_fr
    KEEP_LIST = advancedViewResources{}
    -> ListExploder
ListExploder
    ATTR_ACCUM_MODE = Merge List Attributes
    ATTR_CONFLICT_RES = Use List Attribute Values
    INDEX_ATTR = _element_index
    LIST_ATTR = advancedViewResources{}
    ELEMENTS -> AttributeExposer_2
AttributeExposer_2
    ATTR_LIST = url,format
    -> AttributeCreator
AttributeCreator
    ATTR_TABLE = SET_TO name = @Value(title) - Advanced View
    -> Tester_2
Tester_2
    BOOL_OP = OR
    COMPOSITE_TEST = 1
    TEST_CLAUSE = TEST title_fr ATTRIBUTE_HAS_A_VALUE ""
    TEST_MODE = TEST
    PASSED -> AttributeCreator_4
    FAILED -> AttributeCreator_3
AttributeCreator_4
    ATTR_TABLE = SET_TO name_fr = @Value(title_fr) - vue avancée
    -> AttributeKeeper_2
AttributeCreator_3
    ATTR_TABLE = SET_TO name_fr = FME_NULL_VALUE
    -> AttributeKeeper_2
AttributeKeeper_2
    KEEP_ATTRS = name,format,url,name_fr,adviewuuid
    -> FeatureMerger [SUPPLIER]
FeatureMerger
    ATTR_ACCUM_MODE = Merge Supplier
    ATTR_CONFLICT_RES = Use Requestor
    IGNORE_NULLS = No
    JOIN_KEYS = @Value(adviewuuid) @Value(adviewuuid) AUTO
    LIST_ATTRS_TO_INCLUDE = format name name_fr url
    LIST_NAME = advancedViewResources
    MERGE_TYPE = Attributes Only
    PROCESS_DUPS = NO
    REJECT_NULL_MISSING_KEYS = No
    SUPPLIERS_FIRST = No
    MERGED -> Output (output)
Output (output)

FME custom transformer SOCRATA_RESOURCE_MAPPER

Parameters:
- Socrata_Domain = gnb.socrata.com   # Enter the Socrata Domain (without https)
- FME_PROCESS_GROUP_BY =   # "" Group By
- FME_PROCESS_GROUPS_ORDERED = No   # Process At End (Blocking),No%Process When Group Changes (Advanced),Yes Group By Mode

INPUT (input)
    -> AttributeExposer_2
AttributeExposer_2
    ATTR_LIST = resource.id,dataLayers{},title,title_fr,dataLayers{0}.geomcol,dataLayers{0}.geomtype,dataLayers{0}.layerid
    -> Tester_3
Tester_3
    BOOL_OP = OR
    COMPOSITE_TEST = 1 OR 2 OR 3
    TEST_CLAUSE:
      TEST dataLayers{0}.layerid ATTRIBUTE_IS_EMPTY ""
      TEST dataLayers{0}.layerid ATTRIBUTE_VALUE_NULL ""
      TEST dataLayers{0}.layerid ATTRIBUTE_IS_MISSING ""
    TEST_MODE = TEST
    PASSED -> Terminator
    FAILED -> Tester_4
Terminator
    MESSAGE = Missing ID value in trueids{}
Tester_4
    BOOL_OP = OR
    COMPOSITE_TEST = 1 OR 2 OR 3
    TEST_CLAUSE:
      TEST dataLayers{0}.geomcol ATTRIBUTE_VALUE_NULL ""
      TEST dataLayers{0}.geomcol ATTRIBUTE_IS_EMPTY ""
      TEST dataLayers{0}.geomcol ATTRIBUTE_IS_MISSING ""
    TEST_MODE = TEST
    PASSED -> no_geospatial_column_in_trueid (output)
    FAILED -> UUIDGenerator_2
no_geospatial_column_in_trueid (output)

Bookmark: NB_RESOURCES_MAPPER
UUIDGenerator_2
    UUID_ATTR = uuidjoinkey
    -> AttributeKeeper_2
    -> FeatureMerger_2 [REQUESTOR]
    -> AttributeKeeper_4
AttributeKeeper_4
    KEEP_ATTRS = uuidjoinkey,title,resource.id,title_fr
    -> FeatureMerger [REQUESTOR]
AttributeKeeper_2
    KEEP_ATTRS = uuidjoinkey,title,resource.id,title_fr
    KEEP_LIST = dataLayers{}
    -> ListElementCounter_2
ListElementCounter_2
    CNT_ATTR = trueIdLen
    LIST_NAME = dataLayers{}
    -> ListExploder_2
ListExploder_2
    ATTR_ACCUM_MODE = Merge List Attributes
    ATTR_CONFLICT_RES = Use List Attribute Values
    INDEX_ATTR = _element_index
    LIST_ATTR = dataLayers{}
    ELEMENTS -> AttributeExposer_3
AttributeExposer_3
    ATTR_LIST = _element_index,layerid
    -> FeatureMerger_4 [REQUESTOR]
LinkBuilderNonGeo (input)
    -> AttributeExposer_5
AttributeExposer_5
    ATTR_LIST = format,url,titlepart,include_idx
    -> FeatureMerger_4 [SUPPLIER]
FeatureMerger_4
    ATTR_ACCUM_MODE = Merge Supplier
    ATTR_CONFLICT_RES = Use Requestor
    IGNORE_NULLS = No
    JOIN_KEYS = 1 1 AUTO
    LIST_ATTRS_TO_INCLUDE = format include_idx titlepart url
    LIST_NAME = nongeoresources
    MERGE_TYPE = Attributes Only
    PROCESS_DUPS = NO
    REJECT_NULL_MISSING_KEYS = No
    SUPPLIERS_FIRST = No
    MERGED -> ListExploder
ListExploder
    ATTR_ACCUM_MODE = Merge List Attributes
    ATTR_CONFLICT_RES = Use List Attribute Values
    INDEX_ATTR = ignoreindex
    LIST_ATTR = nongeoresources{}
    ELEMENTS -> StringReplacer
StringReplacer
    CASE = NO
    FIND_TEXT = ($DOMAIN$)
    NO_MATCH = _FME_NO_OP_
    REGEXP = NO
    REPLACE_TEXT = $(Socrata_Domain)
    SRC_ATTRS = url
    -> StringReplacer_2
StringReplacer_2
    CASE = NO
    FIND_TEXT = ($trueid$)
    NO_MATCH = _FME_NO_OP_
    REGEXP = NO
    REPLACE_TEXT = @Value(layerid)
    SRC_ATTRS = url
    -> AttributeKeeper
linkbuilder_geo (input)
    -> AttributeExposer_7
AttributeExposer_7
    ATTR_LIST = format,url,titlepart,include_idx
    -> FeatureMerger [SUPPLIER]
FeatureMerger
    ATTR_ACCUM_MODE = Merge Supplier
    ATTR_CONFLICT_RES = Use Requestor
    IGNORE_NULLS = No
    JOIN_KEYS = 1 1 AUTO
    LIST_ATTRS_TO_INCLUDE = format include_idx titlepart url
    LIST_NAME = georesources
    MERGE_TYPE = Attributes Only
    PROCESS_DUPS = NO
    REJECT_NULL_MISSING_KEYS = No
    SUPPLIERS_FIRST = No
    MERGED -> ListExploder_5
ListExploder_5
    ATTR_ACCUM_MODE = Merge List Attributes
    ATTR_CONFLICT_RES = Use List Attribute Values
    INDEX_ATTR = _element_index
    LIST_ATTR = georesources{}
    ELEMENTS -> StringReplacer_4
StringReplacer_4
    CASE = NO
    FIND_TEXT = ($DOMAIN$)
    NO_MATCH = _FME_NO_OP_
    REGEXP = NO
    REPLACE_TEXT = $(Socrata_Domain)
    SRC_ATTRS = url
    -> StringReplacer_3
StringReplacer_3
    CASE = NO
    FIND_TEXT = ($ID$)
    NO_MATCH = _FME_NO_OP_
    REGEXP = NO
    REPLACE_TEXT = @Value(resource.id)
    SRC_ATTRS = url
    -> AttributeKeeper
AttributeKeeper
    KEEP_ATTRS = title,trueIdLen,titlepart,uuidjoinkey,title_fr,include_idx,layerid,_element_index,url,format
    -> Tester
Tester
    BOOL_OP = OR
    COMPOSITE_TEST = 1 OR 2
    TEST_CLAUSE:
      TEST @Value(include_idx) = 0
      TEST @Value(trueIdLen) = 1
    TEST_MODE = TEST
    PASSED -> AttributeCreator_10
    FAILED -> AttributeCreator_2
AttributeCreator_10
    ATTR_TABLE = SET_TO _element_index
    -> AttributeCreator_2
AttributeCreator_2
    ATTR_TABLE = SET_TO name = @Value(title) - @Value(titlepart) @Value(_element_index)
    -> Tester_2
Tester_2
    BOOL_OP = OR
    COMPOSITE_TEST = 1
    TEST_CLAUSE = TEST title_fr ATTRIBUTE_HAS_A_VALUE ""
    TEST_MODE = TEST
    PASSED -> AttributeCreator_4
    FAILED -> AttributeCreator_3
AttributeCreator_4
    ATTR_TABLE = SET_TO name_fr = @Value(title_fr) - @Value(titlepart) @Value(_element_index)
    -> AttributeKeeper_5
AttributeCreator_3
    ATTR_TABLE = SET_TO name_fr = FME_NULL_VALUE
    -> AttributeKeeper_5
AttributeKeeper_5
    KEEP_ATTRS = uuidjoinkey,format,url,name,name_fr
    -> FeatureMerger_2 [SUPPLIER]
FeatureMerger_2
    ATTR_ACCUM_MODE = Merge Supplier
    ATTR_CONFLICT_RES = Use Requestor
    IGNORE_NULLS = No
    JOIN_KEYS = @Value(uuidjoinkey) @Value(uuidjoinkey) AUTO
    LIST_ATTRS_TO_INCLUDE = format name url name_fr
    LIST_NAME = resources
    MERGE_TYPE = Attributes Only
    PROCESS_DUPS = NO
    REJECT_NULL_MISSING_KEYS = No
    SUPPLIERS_FIRST = No
    MERGED -> AttributeRemover_2
AttributeRemover_2
    REMOVE_ATTRS = name,uuidjoinkey,url,format
    -> AttributeCreator
AttributeCreator
    ATTR_TABLE:
      SET_TO spatialref{0}.projection_name = unknown
      SET_TO spatialref{0}.projection_system = unknown
      SET_TO spatialref{0}.projection_system_version = unknown
    -> AttributeExposer
AttributeExposer
    ATTR_LIST = resources{}
    -> OUTPUT (output)
OUTPUT (output)

Bookmark: COMMENT
Note: Good time to use python to create resource url. / Also, ul very simialire, might be useful to use excel file to store constant... / Also, instead of using attributes, might be useful to start creating resources{} list with format, url, description and protocol

FME custom transformer SocrataReader_APIViews

Input (input)
    -> AttributeExposer
AttributeExposer
    ATTR_LIST = socrataDomainURL
    -> HTTPCaller_3
HTTPCaller_3
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(socrataDomainURL)/api/views
    TRANSFER_TIMEOUT_LENGTH = 90
    USE_COOKIES = No
    VERIFY_SSL_CERTIFICATES = No
    -> JSONFlattener_3
    <REJECTED> -> Terminator
JSONFlattener_3
    ERROR_LIST_ATTR = _json_error
    JSON_DOCUMENT = @Value(_response_body)
    NEW_ATTRIBUTES = array{}.id
    READ_FROM_FILE = NO
    RECURSIVE = Yes
    -> ListExploder_2
    <REJECTED> -> Terminator_2
ListExploder_2
    ATTR_ACCUM_MODE = Merge List Attributes
    ATTR_CONFLICT_RES = Use List Attribute Values
    INDEX_ATTR = _element_index
    LIST_ATTR = array{}
    ELEMENTS -> AttributeKeeper_3
    <REJECTED> -> Terminator_3
AttributeKeeper_3
    KEEP_ATTRS = socrataDomainURL,id
    -> HTTPCaller_4
HTTPCaller_4
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(socrataDomainURL)/api/views/@Value(id)
    TRANSFER_TIMEOUT_LENGTH = 90
    USE_COOKIES = No
    VERIFY_SSL_CERTIFICATES = No
    -> JSONFlattener_4
    <REJECTED> -> Terminator_4
JSONFlattener_4
    ERROR_LIST_ATTR = _json_error
    JSON_DOCUMENT = @Value(_response_body)
    READ_FROM_FILE = NO
    RECURSIVE = Yes
    -> AttributeExposer_3
    <REJECTED> -> Terminator_5
AttributeExposer_3
    ATTR_LIST = licenseId,assetType
    -> NullAttributeMapper
NullAttributeMapper
    ATTRCHOICE = Selected Attributes
    ATTRLIST = licenseId
    NEW_VALUE = none
    NULL_TREATMENT = New Value
    SOURCE_ATTR_VAL = Null
    -> Output (output)
Output (output)
Terminator_5
    MESSAGE = Translation Terminated
Terminator_4
    MESSAGE = Translation Terminated
Terminator_3
    MESSAGE = Translation Terminated
Terminator_2
    MESSAGE = Translation Terminated
Terminator
    MESSAGE = Translation Terminated

FME custom transformer NB_ORGANIZATION_MAPPER

feature_input (input)
    -> AttributeExposer
Note: uses the classification.domain_metadata{0}.value entry if exists, otherwise uses attribution. removes french part of both. uses lookup table to standardize organization name
AttributeExposer
    ATTR_LIST = "metadata.custom_fields.Department / Ministère.Department / Ministère",attribution
    -> Tester_2
No_Organization_Match (output)

Bookmark: Get Organization Field
Tester_2
    BOOL_OP = OR
    COMPOSITE_TEST = 1 OR 2
    TEST_CLAUSE:
      TEST metadata.custom_fields.Department / Ministère.Department / Ministère ATTRIBUTE_IS_MISSING ""
      TEST metadata.custom_fields.Department / Ministère.Department / Ministère ATTRIBUTE_VALUE_NULL ""
    TEST_MODE = TEST
    PASSED -> Tester
    FAILED -> AttributeSplitter_5
Tester
    BOOL_OP = OR
    COMPOSITE_TEST = 1 OR 2
    TEST_CLAUSE:
      TEST attribution ATTRIBUTE_IS_MISSING ""
      TEST attribution ATTRIBUTE_VALUE_NULL ""
    TEST_MODE = TEST
    PASSED -> AttributeCreator_4
    FAILED -> AttributeSplitter_4
AttributeCreator_4
    ATTR_TABLE = SET_TO attribution = none_listed
    -> No_Organization_Value (output)
No_Organization_Value (output)
AttributeSplitter_4
    ATTR_NAME = attribution
    DELIMITER = /
    DROP_EMPTY_PARTS = No
    LIST_NAME = attribution_list
    TRIM_OPTION = Both
    -> FeatureMerger_2 [REQUESTOR]
AttributeSplitter_5
    ATTR_NAME = metadata.custom_fields.Department / Ministère.Department / Ministère
    DELIMITER = /
    DROP_EMPTY_PARTS = No
    LIST_NAME = attribution_list
    TRIM_OPTION = Both
    -> FeatureMerger_2 [REQUESTOR]
FeatureMerger_2
    ATTR_ACCUM_MODE = Merge Supplier
    ATTR_CONFLICT_RES = Use Requestor
    IGNORE_NULLS = No
    JOIN_KEYS = @Value(attribution_list{0}) @Value(api_value) AUTO
    MERGE_TYPE = Attributes Only
    PROCESS_DUPS = NO
    REJECT_NULL_MISSING_KEYS = No
    SUPPLIERS_FIRST = No
    MERGED -> AttributeRenamer_2
    UNMERGED_REQUESTOR -> No_Organization_Match (output)
AttributeRenamer_2
    ATTR_TABLE:
      RENAME_SET_DEFAULT organization_name > sector
      RENAME_SET_DEFAULT organization_name_fr > sector_fr
    -> AttributeRemover
AttributeRemover
    LIST_ATTRS = attribution_list{}
    REMOVE_ATTRS = api_value
    -> feature_output (output)
feature_output (output)

Bookmark: COMMENT
Sector_Lookup_table (input)
    -> AttributeExposer_3
Note: Attribute cleanup
AttributeExposer_3
    ATTR_LIST = api_value,organization_name,organization_name_fr
    -> FeatureMerger_2 [SUPPLIER]
