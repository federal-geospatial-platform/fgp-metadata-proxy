FME workspace NL_FGP_XML_BUILDER_DEV_01.fmw
Description: Description 
This workbench read and trasform all the metadata for the province of Québec (QC)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
P_T_ABBR: Two letter abbreviation code of the province or terrirtory (ex.: ON, QC, ...).
METADATA_OVERWRITE: Enable the overwite of the PyCSW.  Can take two values: Yes: Overwrite the contentof the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: C:\Data\PT_Harvester\QC\LOG\QC.log
OUT_JSON_LOCAL_DIR: Source directory to output JSON files. Defined as: C:\Data\PT_Harvester\QC\JSON_LOCAL
OUT_XLS_NOTIFICATION: Source directory to output excel files. Defined as: C:\Data\PT_Harvester\QC\XLS
OUT_XML_FAILED_DIR: Source directory to output failed XML files. Defined as: C:\Data\PT_Harvester\QC\XML_FAILED
OUT_XML_LOCAL_DIR: Source directory to output Local Source XML files. Defined as: C:\Data\PT_Harvester\QC\XML_LOCAL
OUT_XML_PASSED_DIR: Source directory to output passedXML files. Defined as: C:\Data\PT_Harvester\QC\XML_PASSED
SAMPLE_SIZE: Number of features to process. Zero (0) means process all the features. A number n greater than 0 means sample or process only the first n features.
URL_VALIDATION : Indicates to validate or not created URL. (Should be Yes for prod)

Parameters:
- ACTIVATE_GEO = Yes
- ACTIVATE_NON_GEO = Yes
- ACTIVATE_TRANSLATION = No
- CATALOGUE_READER_SELECT = No
- FORCED_PYCSW_URL =
- IN_FFS_TESTING_FILE =
- LOCAL_SOURCE_METADATA_DELTA_FINDER = Yes
- LOCAL_WRITER = Yes
- P-T_ABBR = NL
- METADATA_OVERWRITE = YES
- IN_OUT_WORKING_DIR = C:\Data\PT_Harvester
- SAMPLE_SIZE = 0
- URL_VALIDATION = No
- IN_CSV_LOOKUP_TABLES_DIR = $(IN_OUT_WORKING_DIR)\LOOKUP_TABLES   # DEFAULT_IN_CSV_LOOKUP_TABLES_DIR
- IN_GMD_XML_TEMPLATE_DIR = $(IN_OUT_WORKING_DIR)\XML_TEMPLATES
- IN_TBS_JSON_TEMPLATE_DIR = $(IN_OUT_WORKING_DIR)\JSON_TEMPLATES
- LOG_FILE = $(IN_OUT_WORKING_DIR)\$(P-T_ABBR)\LOG\$(P-T_ABBR).log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- FME_SHAREDRESOURCE_DATA = C:\Data   # FME Server Resource Data

Writers:
- XLSXW_1: XLSXW to $(OUT_XLS_NOTIFICATION_DIR)
- TEXTLINE_1: TEXTLINE to $(OUT_JSON_LOCAL_DIR)
- TEXTLINE_2: TEXTLINE to $(OUT_XML_PASSED_DIR)
- TEXTLINE_3: TEXTLINE to $(OUT_XML_FAILED_DIR)
- TEXTLINE_4: TEXTLINE to $(OUT_XML_LOCAL_DIR)

AttributeExposer_7
    ATTR_LIST = license_id
    -> LICENSE_FILTER_NG
LICENSE_FILTER_NG
    FEATURE_TYPE = License_NL
    IN_CSV_LOOKUP_TABLES_DIR = $(IN_CSV_LOOKUP_TABLES_DIR)
    LICENSE_ATT = @Value(license_id)
    P-T_ABBR = $(P-T_ABBR)
    LICENSE_FILTER_PASSED -> SECTOR_MAPPER_NG
    UNKNOWN_LICENSE -> LICENSE_ID_NOT_MAPPED (writer XLSXW_1)
SECTOR_MAPPER_NG
    FEATURE_TYPE = Sector_NL
    IN_CSV_LOOKUP_TABLES_DIR = $(IN_CSV_LOOKUP_TABLES_DIR)
    P-T_ABBR = $(P-T_ABBR)
    PUBLISHED_OUTPUT -> AttributeExposer
    UNMAPPED_OUTPUT -> SECTOR_NOT_MAPPED (writer XLSXW_1)
AttributeExposer
    ATTR_LIST = title
    -> UNIQUE_ID_CREATOR
UNIQUE_ID_CREATOR
    UNIQUE_ATT = @Value(title)
    -> AttributeExposer_3
    -> AttributeExposer_19 [off]
AttributeExposer_3
    ATTR_LIST = resources{}.format,id
    -> AttributeExposer_18
Junction
    -> ON_DATE_FORMATTER
    -> RESOURCES_VALIDATOR
Note: Writes XML to a local folder without publishing to PyCSW, and without the PyCSW transaction headers and footers
text_line (writer TEXTLINE_4)
    attributes: text_line_data buffer
Note: Writes XML published to the PyCSW to a local folder
text_line (writer TEXTLINE_2)
    attributes: text_line_data buffer
Note: Writes XML that failed to publish to the PyCSW to a local folder
text_line (writer TEXTLINE_3)
    attributes: text_line_data buffer
Junction_2
    -> AttributeExposer_2
text_line (writer TEXTLINE_1)
    attributes: text_line_data buffer
SECTOR_NOT_MAPPED (writer XLSXW_1)
    attributes: sector string(200), id string(200)
LICENSE_ID_NOT_MAPPED (writer XLSXW_1)
    attributes: license_id string(200), id string(200)

Bookmark: Reading NL Datasets and creating attributes
Creator
    GEOMTYPE = Geometry Object
    NUM = 1
    CREATED -> Tester_3
Tester_3
    BOOL_OP = OR
    COMPOSITE_TEST = 1
    TEST_CLAUSE = TEST $(CATALOGUE_READER_SELECT) = Yes
    TEST_MODE = TEST
    PASSED -> NL_CATALOGUE_READER
    FAILED -> FeatureReader [INITIATOR]
Note: Read pre-recorded NL catalogue data
FeatureReader
    ATTR_ACCUM_MODE = Only Use Result
    COMBINE_GEOM = Use Result
    DATASET = C:\DATA\FGP_GITHUB\fgp-metadata-proxy\FME_files\FME_Workspaces\NL_CATALOGUE_READER.ffs
    FFS_USE_SEARCH_ENVELOPE = NO
    FORMAT = FFS
    INTERACT = <No Spatial Filter>
    OUTPUT_FEATURES_DISPLAY = Schema and Data Features
    <OTHER> -> ATTRIBUTE_VALUE_TEXT_CLEANER_2
    <REJECTED> -> Terminator
Terminator
    MESSAGE = Translation Terminated
Note: Read NL catalogue
NL_CATALOGUE_READER
    URL_DATASET_GEO = https://opendata.gov.nl.ca/public/opendata/page/?page-id=datasets-spatial
    URL_DATASET_NON_GEO = https://opendata.gov.nl.ca/public/opendata/page/?page-id=datasets-tabular
    URL_ROOT = https://opendata.gov.nl.ca
    -> ATTRIBUTE_VALUE_TEXT_CLEANER_2
    -> Recorder [off]
    BROKEN_URL -> BROKEN_GEOHUB_URL (writer XLSXW_1)
Note: Clean all attribute from extra white spaces, \n, ...
ATTRIBUTE_VALUE_TEXT_CLEANER_2
    -> NL_ATTRIBUTE_EXTRACTOR
Note: Extract the metadata from the HTML tags
NL_ATTRIBUTE_EXTRACTOR
    -> ATTRIBUTE_MANAGER_NG
Note: Manage missing attributes
ATTRIBUTE_MANAGER_NG
    IN_YAML_TEXT:
      notes:
          action: attribute_not_null
          attr2set: title
      org_contact.fr:
          action: attribute_not_null
          attr2set: org_contact.en
      data_collection_start_date:
          action: text_not_null
          attr2set: UNKNOWN
      record_last_modified:
          action: attribute_not_null
          attr2set: record_create_date
      record_publish_date:
          action: attribute_not_null
          attr2set: record_create_date
      license_id:
          action: text_not_null
          attr2set: License is missing
      resources{}.language:
          action: text_overwrite
          attr2set: eng
      resources{}.protocol:
          action: text_overwrite
          attr2set: HTTPS
    -> AttributeExposer_5
AttributeExposer_5
    ATTR_LIST = data_collection_start_date
    -> EXTRACT_COLLECTION_START_END_DATE
Note: Set the collection start and end date
EXTRACT_COLLECTION_START_END_DATE
    CSV_PATH = $(IN_CSV_LOOKUP_TABLES_DIR)
    DATE_EXTENT = @Value(data_collection_start_date)
    FEATURE_TYPE = Manual_end_start_collection_date_NL
    PT = $(P-T_ABBR)
    -> DEFAULT_ATTRIBUTE_MAPPER_NG
    Unworking_extent -> Unworking_date_collection_extent (writer XLSXW_1)
Note: Sets default attribute values
DEFAULT_ATTRIBUTE_MAPPER_NG
    FEATURE_TYPE = Default_NL
    IN_CSV_LOOKUP_TABLES_DIR = $(IN_CSV_LOOKUP_TABLES_DIR)
    P-T_ABBR = $(P-T_ABBR)
    -> EMPTY_FORMAT_MAPPER [DATA_INPUT]
Note: Guest the format for empty ressources
EMPTY_FORMAT_MAPPER
    DATA_OUTPUT -> AttributeExposer_7 [off]
Unworking_date_collection_extent (writer XLSXW_1)
    attributes: unmatched_date_extent string(200)
BROKEN_GEOHUB_URL (writer XLSXW_1)
    attributes: _url_dataset_geo string(200), _url_root string(200)
Recorder
    COMPRESSION_LEVEL = 6
    CREATE_SPATIAL_INDEX = No
    MODE = RECORD_PASS_THROUGH
    RECFILE = C:\DATA\FGP_GITHUB\fgp-metadata-proxy\FME_files\FME_Workspaces\NL_CATALOGUE_READER.ffs
    STORE_SCANNED_METADATA = No
    STORE_SCANNED_SCHEMA = No

Bookmark: Add Geoportal Weblink
AttributeExposer_18
    ATTR_LIST = id
    -> GEOPORTAL_WEBLINK_ADDER_NG
Note: Ajout du lien vers la métadonnées en anglais
GEOPORTAL_WEBLINK_ADDER_NG
    FEATURE_TYPE = GeoportalWeblink_NL_en
    IN_CSV_LOOKUP_TABLES_DIR = $(IN_CSV_LOOKUP_TABLES_DIR)
    P-T_ABBR = $(P-T_ABBR)
    URL_VALIDATION = $(URL_VALIDATION)
    WEBLINK_WILDCARD = @Value(id)
    -> AttributeExposer_19
AttributeExposer_19
    ATTR_LIST = id
    -> GEOPORTAL_WEBLINK_ADDER_NG_2
Note: Ajout du lien vers la métadonnées en français
GEOPORTAL_WEBLINK_ADDER_NG_2
    FEATURE_TYPE = GeoportalWeblink_NL_fr
    IN_CSV_LOOKUP_TABLES_DIR = $(IN_CSV_LOOKUP_TABLES_DIR)
    P-T_ABBR = $(P-T_ABBR)
    URL_VALIDATION = $(URL_VALIDATION)
    WEBLINK_WILDCARD = @Value(id)
    -> AttributeExposer_11
AttributeExposer_11
    ATTR_LIST = resources{}
    -> ListElementCounter
ListElementCounter
    CNT_ATTR = _element_count
    LIST_NAME = resources{}
    -> PythonCaller_3
Note: Cération de lang_list / pour la sortie pour TBS
PythonCaller_3
    PYTHONSOURCE:
      import fme
      import fmeobjects
      # Template Function interface:
      # When using this function, make sure its name is set as the value of
      # the 'Class or Function to Process Features' transformer parameter
      def processFeature(feature):
          for i in range(int(feature.getAttribute('_element_count'))):
              langue=feature.getAttribute('resources{%i}.language'%(i))
              if not langue:
                  langue='english'
              feature.setAttribute('resources{%i}.language'%(i),langue)
              feature.setAttribute('resources{%i}.language_list'%(i),langue)
    PYTHONSYMBOL = processFeature
    -> GEO_NONE_GEO_SELECTOR

Bookmark: Spatail data filtering
Note: Filters geospatial data by referencing format, then by resources identified as having geographic markers
GEO_NONE_GEO_SELECTOR
    CSV_FILE_NAME = GeoSpatialValidation
    CSV_PATH = $(IN_CSV_LOOKUP_TABLES_DIR)
    CSV_PROVINCE = $(P-T_ABBR)
    YAML_DIRECTIVES:
      resources{}.format:
        domain: lookup_table_format
        spatial_type: overwrite
        not_found: log
        search_type: equals
    GEOSPATIAL -> SPATIAL_TYPE_MAPPER_NG [DATA_INPUT]
    NONE_GEOSPATIAL -> MANUAL_GEOSPATIAL_SETTER_NG [DATA_INPUT]
    LOG_ERROR -> GEOSPATIAL_FORMAT_NOT_MAPPED (writer XLSXW_1)
Note: Maps the spatial_representation_type of known geographic data, and geo data that could not be mapped to a specific spatial_representation_type is given value through lookup table where the type was researched manually
SPATIAL_TYPE_MAPPER_NG
    FEATURE_TYPE = UUID_Spatial_NL
    IN_CSV_LOOKUP_TABLES_DIR = $(IN_CSV_LOOKUP_TABLES_DIR)
    P-T_ABBR = $(P-T_ABBR)
    DATA_OUTPUT_FAILED -> SPATIAL_TYPE_NOT_MAPPED (writer XLSXW_1)
    DATA_OUTPUT_PASSED -> Junction_3
SPATIAL_TYPE_NOT_MAPPED (writer XLSXW_1)
GEOSPATIAL_FORMAT_NOT_MAPPED (writer XLSXW_1)
    attributes: resources__ string(200), _element_count number(20), _geo_none_geo_status string(200), id string(200), _not_found_err_msg string(200), format string(200)
Note: Additional filtering step required for ON data. Items identified as NON-GEOSPATIAL in GEOSPATIAL_DATA_VALIDATOR were analyzed manually and a lookup table was created to identify non-filtered geo data and create the spatial_representation_type
MANUAL_GEOSPATIAL_SETTER_NG
    FEATURE_TYPE = UnmappedGeoData_NL
    IN_CSV_LOOKUP_TABLES_DIR = $(IN_CSV_LOOKUP_TABLES_DIR)
    P-T_ABBR = $(P-T_ABBR)
    GEOSPATIAL -> Junction_3
    NON-GEOSPATIAL -> Tester_2
    UNMAPPED_DATA -> UNMAPPED_GEODATA_NL (writer XLSXW_1)
Junction_3
    -> Tester_7
UNMAPPED_GEODATA_NL (writer XLSXW_1)
    attributes: id string(200), notes string(200), title string(200), url string(200)

Bookmark: Activate Geo and Sample or full content
Tester_7
    BOOL_OP = OR
    COMPOSITE_TEST = 1
    TEST_CLAUSE = TEST @UpperCase($(ACTIVATE_GEO)) = YES
    TEST_MODE = TEST
    PASSED -> TestFilter
TestFilter
    DEFAULT_VALUE = SAMPLES FEATURES
    TEST_LIST = "BOOL_OP,OR,COMPOSITE_TEST,""""""1"""""",TEST_CLAUSE,TEST $(SAMPLE_SIZE) = 0",ALL FEATURES
    ALL FEATURES -> Junction
    SAMPLES FEATURES -> Sampler_3
Sampler_3
    RATE = $(SAMPLE_SIZE)
    SAMPLE_MODE = No
    SAMPLE_TYPE_LONG = First N Features
    SAMPLED -> Junction

Bookmark: Pre value map processing
Note: Extracts, sorts, fitlers and creates data values and addresses areas where date values are missing
ON_DATE_FORMATTER [off]
    -> RESOURCES_VALIDATOR
Note: Validates url, name and format on resources{} list items
RESOURCES_VALIDATOR
    -> METADATA_VALUE_MAPPER_NG [DATA_INPUT] [off]
    -> METADATA_VALUE_MAPPER_NG_3 [DATA_INPUT]

Bookmark: Attribute value mapper
METADATA_VALUE_MAPPER_NG [off]
    ATT_TO_MAP = resources{}.language
    CODE_REFRESH = NO
    ENGLISH_REFRESH = YES
    ERROR_NOT_MAPPED = YES
    FEATURE_TYPE = TransferLang_ON
    FRENCH_REFRESH = NO
    IN_CSV_LOOKUP_TABLES_DIR = $(IN_CSV_LOOKUP_TABLES_DIR)
    P-T_ABBR = $(P-T_ABBR)
    -> METADATA_VALUE_MAPPER_NG_3 [DATA_INPUT]
Note: Map Role to HNAP standards
Note: This section utilizes mulitple instances of the METADATA_VALUE_MAPPER to correct values to valid English values and to add the valid French equivalents and RI_CODES where applicable. It can be utilized for mulitple metadata items by accessing custom look up tables applicable to specific items. / Turn the error mapping options and the data items to be mapped on or off by clicking on the transformer and selecting yes/no. / - ERROR_NOT_MAPPED: enables mapping of data item values that cannot be found in the lookup tables. / - ENGLISH_REFRESH: enables updating of English attribute values. / - FRENCH_REFRESH: enables updating of French attribute values. / - CODE_REFRESH: enables updating of RI_CODE values. / Enter the attribute key name by clicking on the transformer and selecting the drop down menu next to the 'att_to_map' text box and selecting the 'Open text editor...' option. Explicitly enter the attribute key name in the text editor (ie: contacts{}.role). / IMPORTANT: Do not select the 'Attribute Value' option from the drop down menu to select the attribute key name.
METADATA_VALUE_MAPPER_NG_3
    ATT_TO_MAP = role
    CODE_REFRESH = YES
    ENGLISH_REFRESH = YES
    ERROR_NOT_MAPPED = YES
    FEATURE_TYPE = Role
    FRENCH_REFRESH = YES
    IN_CSV_LOOKUP_TABLES_DIR = $(IN_CSV_LOOKUP_TABLES_DIR)
    P-T_ABBR = $(P-T_ABBR)
    -> METADATA_VALUE_MAPPER_NG_4 [DATA_INPUT]
Note: Maps update cycle to HNAP standards
METADATA_VALUE_MAPPER_NG_4
    ATT_TO_MAP = update_frequency
    CODE_REFRESH = YES
    ENGLISH_REFRESH = YES
    ERROR_NOT_MAPPED = YES
    FEATURE_TYPE = Update
    FRENCH_REFRESH = YES
    IN_CSV_LOOKUP_TABLES_DIR = $(IN_CSV_LOOKUP_TABLES_DIR)
    P-T_ABBR = $(P-T_ABBR)
    -> METADATA_VALUE_MAPPER_NG_5 [DATA_INPUT]
Note: Maps progress code to HNAP standards
METADATA_VALUE_MAPPER_NG_5
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUP_TABLES_DIR)
    P-T_ABBR = $(P-T_ABBR)
    -> METADATA_VALUE_MAPPER_NG_6 [DATA_INPUT]
Note: Maps spatial rpresentation to HNAP standards
METADATA_VALUE_MAPPER_NG_6
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUP_TABLES_DIR)
    P-T_ABBR = $(P-T_ABBR)
    -> METADATA_VALUE_MAPPER_NG_7 [DATA_INPUT]
Note: Maps spatial_representation_type to HNAP standards8
METADATA_VALUE_MAPPER_NG_7
    ATT_TO_MAP = extracted_topic{}.value
    CODE_REFRESH = NO
    ENGLISH_REFRESH = YES
    ERROR_NOT_MAPPED = YES
    FEATURE_TYPE = Topic
    FRENCH_REFRESH = NO
    IN_CSV_LOOKUP_TABLES_DIR = $(IN_CSV_LOOKUP_TABLES_DIR)
    P-T_ABBR = $(P-T_ABBR)
    -> METADATA_FORMAT_MAPPER_NG [DATA_INPUT]

Bookmark: Format value mapper
Note: This section utilizes the METADATA_FORMAT_MAPPER to correct data format values to valid data format values and to associate and add the French and English 'Resource Type' attribute to each data format type. It accesses a custom look up table applicable to data formats. / Turn the error mapping options and the data items to be mapped on or off by clicking on the transformer and selecting yes/no. / - ERROR_NOT_MAPPED: enables mapping of data item values that cannot be found in the lookup tables. / - REAL_VALUE_REFRESH: enables updating of data format attribute values. / - RES_TYPE_FR_REFRESH: enables mapping of French resource types. / - RES_TYPE_EN_REFRESH: enables mapping of English resource types. / Enter the attribute key name by clicking on the transformer and selecting the drop down menu next to the 'att_to_map' text box and selecting the 'Open text editor...' option. Explicitly enter the attribute key name in the text editor (ie: resources{}.format). / IMPORTANT: Do not select the 'Attribute Value' option from the drop down menu to select the attribute key name.
METADATA_FORMAT_MAPPER_NG
    ATT_TO_MAP = resources{}.format
    ERROR_NOT_MAPPED = YES
    FEATURE_TYPE = Format
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    -> METADATA_VALUE_MAPPER_ERROR_MANAGER_2

Bookmark: Mapping error list creator
METADATA_VALUE_MAPPER_ERROR_MANAGER_2
    ERROR_OUTPUT -> ATTRIBUTE_MAPPING_ERRORS_GEO (writer XLSXW_1)
    DATA_OUTPUT -> REMOVE_BROKEN_URL_WMS_ESRI_REST
ATTRIBUTE_MAPPING_ERRORS_GEO (writer XLSXW_1)
    attributes: error string(200), id string(200), _element_index string(200)

Bookmark: Data cleanup. Dropping broken web services
Note: Tests WMS/ESRI_REST resource URL's and removes them where broken
REMOVE_BROKEN_URL_WMS_ESRI_REST
    -> WMS_REST_LANGUAGE_FORMATTER
    FAULTY_URL_OUTPUT -> MAP_SERVICE_URL_ERROR (writer XLSXW_1)
MAP_SERVICE_URL_ERROR (writer XLSXW_1)
    attributes: id auto(20), format string(8), url auto(20), _url_failure_message auto(20)

Bookmark: HNAP Rules- 1 web service per language.
Note: Formats WMS and ESRI REST resources to add French versions and formats French and English versions with valid supporting attributes
WMS_REST_LANGUAGE_FORMATTER
    -> DUPLICATE_SERVICE_REMOVER
Note: Removes duplicate WMS or ESRI REST resources where they exist, that would otherwise invalidate the dataset
DUPLICATE_SERVICE_REMOVER
    -> RESOURCE_NAME_UNDERSCORE_REMOVER

Bookmark: Data preparation for metadata section
Note: Removes all underscores from resources{}.name attributes. Long compounded names joined by underscores in this field can cause display formatting issues when published to the FGP.
RESOURCE_NAME_UNDERSCORE_REMOVER
    DATA_OUTPUT -> AttributeExposer_13
AttributeExposer_13
    ATTR_LIST = resources{}
    -> ListCopier
ListCopier
    DEST_LIST = distributionList
    SRC_LIST = resources{}
    -> GMD_SECTION_DATA_EXTRACTION
Note: Creates lists and removes duplicates for GMD_Section
GMD_SECTION_DATA_EXTRACTION
    -> MORE_INFO_MANAGER
Note: Tests the more_info{}.link list for valid attribute values and filters them out where missing
MORE_INFO_MANAGER
    -> PythonCaller

Bookmark: Pregenrate formating for ressources description
PythonCaller
    NEW_ATTRIBUTES = resources{}.description_temp
    PYTHONSOURCE:
      import fme
      import fmeobjects
      # Template Function interface:
      # When using this function, make sure its name is set as the value of
      # the 'Class or Function to Process Features' transformer parameter
      def processFeature(feature):


          for i in range(len(feature.getAttribute('resources{}.url'))):
              format=feature.getAttribute('resources{%i}.format'%(i))
              restype=feature.getAttribute('resources{%i}.format_resourceType_en'%(i))
              lang=feature.getAttribute('resources{%i}.language'%(i))

              feature.setAttribute('resources{%i}.description_temp'%(i),'%s;%s;%s'%(restype,format,lang))
    PYTHONSYMBOL = processFeature
    -> AttributeExposer_6

Bookmark: New Bookmark
AttributeExposer_6
    ATTR_LIST = search_criteria_pycsw,csw_url
    -> METADATA_DELTA_FINDER_NG
Note: Searches existing PyCSW for new, updated or obsolete dat
METADATA_DELTA_FINDER_NG
    ABSTRACT_ATT_NEW = notes
    ABSTRACT_ATT_REF = MD_Metadata.identificationInfo.MD_DataIdentification.abstract.CharacterString
    CSW_FILTER = @Value(search_criteria_pycsw)
    CUSTOM_CSW_CKAN_URL = @Value(csw_url)
    DATESTAMP_ATT_NEW = record_last_modified
    DATESTAMP_ATT_REF = MD_Metadata.dateStamp.Date
    ID_ATT_NEW = id
    ID_ATT_REF = MD_Metadata.fileIdentifier.CharacterString
    LOCAL_SOURCE = Yes
    LOCAL_SOURCE_DIR = $(OUT_XML_LOCAL_DIR)
    LOCAL_SOURCE_FORMAT = XML
    METADATA_OVERWRITE = $(METADATA_OVERWRITE)
    RES_FORMAT_ATT_NEW = resources{}.description_temp
    RES_FORMAT_ATT_REF = MD_Metadata.distributionInfo.MD_Distribution.transferOptions{}.MD_DigitalTransferOptions.onLine.CI_OnlineResource.description.CharacterString
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    Statistics -> StatisticsCalculator_Summary
    Update -> Junction_5
    Insert -> Junction_5
Note: Log statistics
StatisticsCalculator_Summary: Logger
    LOG_FEATURE = NONE
    MAXFEATS = 20
    MESSAGE:
      ************************
      **** Geo Unchanged Report ****
      ************************

      @Value(_real_count) features were unchanged

      ************************
      ************************
      ************************
    SEVERITY = INFO
Junction_5
    -> AWS_TRANSLATE_NG_2

Bookmark: Language Translation
Note: Translate geo features
AWS_TRANSLATE_NG_2
    ACTIVATE_TRANSLATION = $(ACTIVATE_TRANSLATION)
    ATTR_2_TRANSLATE = notes,title,sector
    ATTR_LIST_2_TRANSLATE = tags{}.display_name,resources{}.name
    MODE = English-->French
    -> XML_PUBLISHER_NG
    TRANSLATION_PROBLEM -> TRANSLATION_PROBLEM_GEO (writer XLSXW_1)
TRANSLATION_PROBLEM_GEO (writer XLSXW_1)
    attributes: _aws_activation string(200), _mode string(200), _attr2translate string(200), _attrlist2translate string(200), _translation_status string(200)

Bookmark: XML CREATION AND WRITING
Note: Excel config file to map ON attributes to those required by XML templates
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
XML_PUBLISHER_NG
    FEATURE_TYPE = Config_NL
    IN_CSV_LOOKUP_TABLES_DIR = $(IN_CSV_LOOKUP_TABLES_DIR)
    LOCAL_WRITER = $(LOCAL_WRITER)
    P-T_ABBR = $(P-T_ABBR)
    TEMPLATE_GMD_CITEDRESPONSIBLEPARTY = $(IN_GMD_XML_TEMPLATE_DIR)\GMD_CITEDRESPONSIBLEPARTY.xml
    TEMPLATE_GMD_CONTACT = $(IN_GMD_XML_TEMPLATE_DIR)\GMD_CONTACT.xml
    TEMPLATE_GMD_DISTRIBUTIONFORMAT = $(IN_GMD_XML_TEMPLATE_DIR)\GMD_DISTRIBUTIONFORMAT.xml
    TEMPLATE_GMD_DISTRIBUTOR = $(IN_GMD_XML_TEMPLATE_DIR)\GMD_DISTRIBUTOR.xml
    TEMPLATE_GMD_KEYWORDS = $(IN_GMD_XML_TEMPLATE_DIR)\GMD_KEYWORDS.xml
    TEMPLATE_GMD_MDMETADATA = $(IN_GMD_XML_TEMPLATE_DIR)\GMD_MDMETADATA.xml
    TEMPLATE_GMD_REFERENCESYSTEMINFO = $(IN_GMD_XML_TEMPLATE_DIR)\GMD_REFERENCESYSTEMINFO.xml
    TEMPLATE_GMD_RESOURCEMAINTENANCE = $(IN_GMD_XML_TEMPLATE_DIR)\GMD_RESOURCEMAINTENANCE.xml
    TEMPLATE_GMD_TOPICCATEGORY = $(IN_GMD_XML_TEMPLATE_DIR)\GMD_TOPICCATEGORY.xml
    TEMPLATE_GMD_TRANSFEROPTIONS = $(IN_GMD_XML_TEMPLATE_DIR)\GMD_TRANSFEROPTIONS.xml
    LOCAL -> text_line (writer TEXTLINE_4)
    INSERT_PASSED -> text_line (writer TEXTLINE_2)
    UPDATE_PASSED -> text_line (writer TEXTLINE_2)
    INSERT_FAILED -> text_line (writer TEXTLINE_3)
    UPDATE_FAILED -> text_line (writer TEXTLINE_3)

Bookmark: Activate None Geo and Sample or fulle content
Tester_2
    BOOL_OP = OR
    COMPOSITE_TEST = 1
    TEST_CLAUSE = TEST @UpperCase($(ACTIVATE_NON_GEO)) = YES
    TEST_MODE = TEST
    PASSED -> TestFilter_2
TestFilter_2
    DEFAULT_VALUE = SAMPLES FEATURES
    TEST_LIST = "BOOL_OP,OR,COMPOSITE_TEST,""""""1"""""",TEST_CLAUSE,TEST $(SAMPLE_SIZE) = 0",ALL FEATURES
    ALL FEATURES -> Junction_2
    SAMPLES FEATURES -> Sampler_4
Sampler_4
    RATE = $(SAMPLE_SIZE)
    SAMPLE_MODE = No
    SAMPLE_TYPE_LONG = First N Features
    SAMPLED -> Junction_2

Bookmark: Non-Geospatial Export
AttributeExposer_2
    ATTR_LIST = author,author_email,groups{}.name,id,license_id,metadata_created,metadata_modified,notes,organization.title,resources{}.id,resources{}.name,resources{}.url,tags{}.display_name,temporal,title,update_frequency
    -> ON_DATE_FORMATTER_2
    -> METADATA_VALUE_MAPPER_NG_2 [DATA_INPUT] [off]
Note: Extracts, sorts, fitlers and creates data values and addresses areas where date values are missing
ON_DATE_FORMATTER_2
    -> METADATA_VALUE_MAPPER_NG_2 [DATA_INPUT]
Note: Ajustement pour la langue des ressources
METADATA_VALUE_MAPPER_NG_2
    ATT_TO_MAP = resources{}.language_list
    CODE_REFRESH = NO
    ENGLISH_REFRESH = YES
    ERROR_NOT_MAPPED = YES
    FEATURE_TYPE = TransferLang_NL_TBS
    FRENCH_REFRESH = NO
    IN_CSV_LOOKUP_TABLES_DIR = $(IN_CSV_LOOKUP_TABLES_DIR)
    P-T_ABBR = $(P-T_ABBR)
    -> RESOURCES_VALIDATOR_2
Note: Validates url, name and format on resources{} list items
RESOURCES_VALIDATOR_2
    -> METADATA_VALUE_MAPPER_NG_8 [DATA_INPUT]
Note: Adjusting update frequency value
METADATA_VALUE_MAPPER_NG_8
    ATT_TO_MAP = update_frequency
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUP_TABLES_DIR)
    P-T_ABBR = $(P-T_ABBR)
    -> METADATA_FORMAT_MAPPER_NG_2 [DATA_INPUT]
Note: Format TBS
METADATA_FORMAT_MAPPER_NG_2
    ATT_TO_MAP = resources{}.format
    ERROR_NOT_MAPPED = YES
    FEATURE_TYPE = Format_TBS
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    -> AttributeExposer_9
METADATA_VALUE_MAPPER_ERROR_MANAGER
    ERROR_OUTPUT -> ATTRIBUTE_MAPPING_ERRORS_NON_GEO (writer XLSXW_1)
    DATA_OUTPUT -> RESOURCE_NAME_UNDERSCORE_REMOVER_2
Note: Removes all underscores from resources{}.name attributes. Long compounded names joined by underscores in this field can cause display formatting issues when published to the FGP.
RESOURCE_NAME_UNDERSCORE_REMOVER_2
    DATA_OUTPUT -> METADATA_DELTA_FINDER_NG_2
Note: Searches existing PyCSW for new, updated or obsolete dat
METADATA_DELTA_FINDER_NG_2
    ABSTRACT_ATT_NEW = notes
    ABSTRACT_ATT_REF = notes_translated.en
    DATESTAMP_ATT_NEW = record_last_modified
    DATESTAMP_ATT_REF = federated_date_modified
    ID_ATT_NEW = id
    ID_ATT_REF = id
    LOCAL_SOURCE = Yes
    LOCAL_SOURCE_DIR = $(OUT_JSON_LOCAL_DIR)
    LOCAL_SOURCE_FORMAT = JSON
    METADATA_OVERWRITE = $(METADATA_OVERWRITE)
    RES_FORMAT_ATT_NEW = resources{}.format
    RES_FORMAT_ATT_REF = resources{}.format
    RES_NAME_ATT_NEW = resources{}.format
    RES_NAME_ATT_REF = resources{}.format
    RES_URL_ATT_NEW = resources{}.url
    RES_URL_ATT_REF = resources{}.url
    TITLE_ATT_NEW = title
    TITLE_ATT_REF = title_translated.en
    Statistics -> StatisticsCalculator_Summary_2
    Update -> Junction_4
    Insert -> Junction_4
Note: Log statistics
StatisticsCalculator_Summary_2: Logger
    LOG_FEATURE = NONE
    MAXFEATS = 20
    MESSAGE:
      ************************
      **** None Geo Unchanged Report ****
      ************************

      @Value(_real_count) features were unchanged

      ************************
      ************************
      ************************
    SEVERITY = INFO
Junction_4
    -> AWS_TRANSLATE_NG
JSON_PUBLISHER_NG
    FEATURE_TYPE = JSON_CONFIG_NL
    IN_CSV_LOOKUP_TABLES_DIR = $(IN_CSV_LOOKUP_TABLES_DIR)
    JSON_RESOURCE_TEMPLATE = $(IN_TBS_JSON_TEMPLATE_DIR)\TBS_RESOURCES_TEMPLATE_NG.json
    JSON_ROOT_TEMPLATE = $(IN_TBS_JSON_TEMPLATE_DIR)\TBS_ROOT_TEMPLATE_NG.json
    Keywords_EN = tags{}.display_name
    Keywords_FR = tags{}.display_name_fr
    P-T_ABBR = $(P-T_ABBR)
    Subject_LIST = TBS_Subject{}.value
    Topic_LIST = TBS_Topic{}.value
    OUTPUT_LOCAL -> AttributeExposer_4
AttributeExposer_4
    ATTR_LIST = json_file,id
    -> AttributeCreator_6
AttributeCreator_6
    ATTR_TABLE = SET_TO text_line_data = @Value(json_file)
    -> text_line (writer TEXTLINE_1)
ATTRIBUTE_MAPPING_ERRORS_NON_GEO (writer XLSXW_1)
    attributes: error string(200), id string(200), _element_index string(200)

Bookmark: Generating TBS_SUBJECT list based on tags
AttributeExposer_9
    ATTR_LIST = resources{}.format_resourceType_en,extracted_topic{}.value
    -> ListCopier_2
Note: Copy tags in a temp list
ListCopier_2
    DEST_LIST = TBS_Subject
    SRC_LIST = extracted_topic{}
    -> METADATA_VALUE_MAPPER_NG_9 [DATA_INPUT]
Note: Subject TBS
METADATA_VALUE_MAPPER_NG_9
    ATT_TO_MAP = TBS_Subject{}.value
    CODE_REFRESH = NO
    ENGLISH_REFRESH = YES
    ERROR_NOT_MAPPED = YES
    FEATURE_TYPE = Topic_Subject_NL
    FRENCH_REFRESH = NO
    IN_CSV_LOOKUP_TABLES_DIR = $(IN_CSV_LOOKUP_TABLES_DIR)
    P-T_ABBR = $(P-T_ABBR)
    -> AttributeExposer_14
AttributeExposer_14
    ATTR_LIST = TBS_Subject{}.value
    -> ListDuplicateRemover
Note: Removeing duplicates on subject value
ListDuplicateRemover
    SRC_LIST = TBS_Subject{}.value
    -> AttributeExposer_20

Bookmark: Generating Tbs Topic based on tags
AttributeExposer_20
    ATTR_LIST = extracted_topic{}.value
    -> ListCopier_3
ListCopier_3
    DEST_LIST = TBS_Topic
    SRC_LIST = extracted_topic{}
    -> METADATA_VALUE_MAPPER_NG_10 [DATA_INPUT]
Note: Topic TBS
METADATA_VALUE_MAPPER_NG_10
    ATT_TO_MAP = TBS_Topic{}.value
    CODE_REFRESH = NO
    ENGLISH_REFRESH = YES
    ERROR_NOT_MAPPED = YES
    FEATURE_TYPE = Topic_Topic_NL
    FRENCH_REFRESH = NO
    IN_CSV_LOOKUP_TABLES_DIR = $(IN_CSV_LOOKUP_TABLES_DIR)
    P-T_ABBR = $(P-T_ABBR)
    -> AttributeExposer_15
AttributeExposer_15
    ATTR_LIST = TBS_Topic{}.value
    -> ListDuplicateRemover_2
ListDuplicateRemover_2
    SRC_LIST = TBS_Topic{}.value
    -> METADATA_VALUE_MAPPER_ERROR_MANAGER

Bookmark: Language translation
Note: Translate non geo features
AWS_TRANSLATE_NG
    ACTIVATE_TRANSLATION = $(ACTIVATE_TRANSLATION)
    ATTR_2_TRANSLATE = notes,title,sector
    ATTR_LIST_2_TRANSLATE = tags{}.display_name,resources{}.name
    MODE = English-->French
    -> JSON_PUBLISHER_NG
    TRANSLATION_PROBLEM -> TRANSLATION_PROBLEM_NONE_GEO (writer XLSXW_1)
TRANSLATION_PROBLEM_NONE_GEO (writer XLSXW_1)
    attributes: _aws_activation string(200), _mode string(200), _attr2translate string(200), _attrlist2translate string(200), _translation_status string(200)

FME custom transformer ON_TopicExtractor

Parameters:
- DEFAULT_TOPIC =

Topic (input)
    -> AttributeExposer_2
AttributeExposer_2
    ATTR_LIST = original_value
    -> AttributeCreator
AttributeCreator
    ATTR_TABLE:
      SET_TO _odre = 1
      SET_TO topic = @Value(original_value)
    -> Sorter
Input (input)
    -> AttributeExposer
AttributeExposer
    ATTR_LIST = keywords.en{}
    -> AttributeCreator_2
AttributeCreator_2
    ATTR_TABLE:
      SET_TO _odre = 2
      SET_TO DEFAULT_TOPIC = $(DEFAULT_TOPIC)
    -> Sorter
Sorter
    SORT_PARM = _odre NUMERIC ASCENDING
    SORTED -> PythonCaller
PythonCaller
    PYTHONSOURCE:
      import fme
      import fmeobjects
      # Template Function interface:
      # When using this function, make sure its name is set as the value of
      # the 'Class or Function to Process Features' transformer parameter


      # Template Class Interface:
      # When using this class, make sure its name is set as the value of
      # the 'Class or Function to Process Features' transformer parameter
      class FeatureProcessor(object):
          def __init__(self):
              self.topic=[]

          def input(self,feature):
              if int(feature.getAttribute('_odre'))==1:
                  #Ajouter le topic à la liste
                  self.topic.append(feature.getAttribute('topic'))

              else:

                 #Extraire le topic des keywords
                 extracted_topic=[feature.getAttribute('DEFAULT_TOPIC')]
                 feature_keywords=feature.getAttribute('keywords.en{}')

                 real_topic=False

                 for topics in self.topic:

                     if topics in feature_keywords:

                         if not real_topic:
                             #Reset de la liste pour vraie valeur
                             extracted_topic=[]
                             real_topic=True

                         extracted_topic.append(topics)

                 feature.setAttribute('extracted_topic{}.value',extracted_topic)




                 self.pyoutput(feature)
          def close(self):
              pass
    PYTHONSYMBOL = FeatureProcessor
    -> AttributeRemover
AttributeRemover
    REMOVE_ATTRS = _odre,DEFAULT_TOPIC
    -> ATTRIBUTE_UNEXPOSER
ATTRIBUTE_UNEXPOSER
    -> Output (output)
Output (output)

FME custom transformer NL_CATALOGUE_READER
Description
This Custom Transformer is used to read the metadata of the NewFoundLand & Labrador open data portal.  The portal is not offering a public APi to access the metdata information so, this custom transformer is reading all the XHTML code and flatten it in order to parse it and extract the needed metadata information.  The metadata extraction is done is two passes. The first passes to extrat the name and the url of each dataset.  A second pass is done to read the complete set of  metadata of each url (one url per dataset).
Note: There is no option to read only one record with a specific identifier.
Input Ports
Input: One feature to start the extraction of all the records from the NewFoundLand & Labrador open data portal.
Output Ports
Résultats: All the records read from the NewFoundLand & Labrador open data portal
Parameters
URL_ROOT: URL of the  NewFoundLand & Labrador open data portal.
URL_DATASET_GEO: URL prefix of the metadata of the geospatial datasets.
URL_DATASET_NON_GEO: URL prefix of the metadata of the non geospatial datasets.

Parameters:
- URL_ROOT = https://opendata.gov.nl.ca
- URL_DATASET_GEO = https://opendata.gov.nl.ca/public/opendata/page/?page-id=datasets-spatial
- URL_DATASET_NON_GEO = https://opendata.gov.nl.ca/public/opendata/page/?page-id=datasets-tabular

INPUT (input)
    -> AttributeCreator_2
OUTPUT (output)
BROKEN_URL (output)

Bookmark: Reading of the HTML cataloh of Newfoundland & Labrador
Note: Transform puplished parameters into attributes
AttributeCreator_2
    ATTR_TABLE:
      SET_TO _url_dataset_geo = $(URL_DATASET_GEO)
      SET_TO _url_dataset_non_geo = $(URL_DATASET_NON_GEO)
      SET_TO _url_root = $(URL_ROOT)
    -> PythonCaller
Note: Read the html code from NL web site
PythonCaller
    NEW_ATTRIBUTES = _html_geo_full _html_non_geo_full _url_error
    PYTHONSOURCE:
      import fme
      import fmeobjects
      from Python.NL_CATALOGUE_READER import catalogue_reader_primary
    PYTHONSYMBOL = catalogue_reader_primary
    -> TestFilter
Note: Test if primary reading is valid
TestFilter
    DEFAULT_VALUE = Invalid URL
    TEST_LIST = "BOOL_OP,OR,COMPOSITE_TEST,""""""1"""""",TEST_CLAUSE,TEST _url_error ATTRIBUTE_IS_MISSING """,Valid URL
    Valid URL -> XMLFlattener_2
    Valid URL -> XMLFlattener_4
    Invalid URL -> Junction
Note: Flatten the geospatial XHTML code
XMLFlattener_2
    ATTRIBUTE_XML = _html_geo_full
    EMBEDDED_EXPRESSIONS = <div id="Master_ContentPlaceHolder1_DataSets">
    FEATURE_TYPES_FORMAT_NAME = XML
    FLATTEN_OPTIONS = <structure separator="." map-empty-elements="yes" matched-prefix="attributes" matched-attributes="yes" cardinality="+{?}" structure-prefix="_html_p_" child-position-attribute="" except-expression="" ui-mode="basic" matched-ancestor-attributes=""/>
    XML_SOURCE_TYPE = Attribute with XML document
    -> PythonCaller_3
    <REJECTED> -> Terminator
Note: Read the HTML code for each of the dataset
PythonCaller_3
    NEW_ATTRIBUTES = _html_detail
    PYTHONSOURCE:
      import fme
      import fmeobjects
      from Python.NL_CATALOGUE_READER import CatalogueReaderSecondary
    PYTHONSYMBOL = CatalogueReaderSecondary
    -> Junction_2
Terminator
    MESSAGE = Translation Terminated. Unable to flatten the XHTML file.
Note: Flatten the non geospatial XHTML code
XMLFlattener_4
    ATTRIBUTE_XML = _html_non_geo_full
    EMBEDDED_EXPRESSIONS = <div id="Master_ContentPlaceHolder1_DataSets">
    FEATURE_TYPES_FORMAT_NAME = XML
    FLATTEN_OPTIONS = <structure separator="." map-empty-elements="yes" matched-prefix="attributes" matched-attributes="yes" cardinality="+{?}" structure-prefix="_html_p_" child-position-attribute="" except-expression="" ui-mode="basic" matched-ancestor-attributes=""/>
    XML_SOURCE_TYPE = Attribute with XML document
    -> PythonCaller_2
    <REJECTED> -> Terminator_3
Note: Read the HTML code for each of the dataset
PythonCaller_2
    NEW_ATTRIBUTES = _html_detail
    PYTHONSOURCE:
      import fme
      import fmeobjects
      from Python.NL_CATALOGUE_READER import CatalogueReaderSecondary
    PYTHONSYMBOL = CatalogueReaderSecondary
    -> Junction_2
Junction_2
    -> TestFilter_2
Note: Test if secondary reading is valid
TestFilter_2
    DEFAULT_VALUE = Invalid URL
    TEST_LIST = "BOOL_OP,OR,COMPOSITE_TEST,""""""1"""""",TEST_CLAUSE,TEST _url_error ATTRIBUTE_IS_MISSING """,Valid URL
    Valid URL -> XMLFlattener_3
    Invalid URL -> Junction
Note: Flatten the XHTML for each datasets
XMLFlattener_3
    ATTRIBUTE_XML = _html_detail
    EMBEDDED_EXPRESSIONS = <html>
    FEATURE_TYPES_FORMAT_NAME = XML
    FLATTEN_OPTIONS = <structure separator="." map-empty-elements="yes" matched-prefix="attributes" matched-attributes="yes" cardinality="+{?}" structure-prefix="_html_s_" child-position-attribute="" except-expression="" ui-mode="basic" matched-ancestor-attributes=""/>
    XML_SOURCE_TYPE = Attribute with XML document
    -> OUTPUT (output)
    <REJECTED> -> Terminator_2
Terminator_2
    MESSAGE = Translation Terminated. Unable to flatten the XHTML file.
Junction
    -> AttributeKeeper
Note: Only keep needed attributes for Excel file writing
AttributeKeeper
    KEEP_ATTRS = _url_dataset_geo,_url_root
    -> BROKEN_URL (output)
Terminator_3
    MESSAGE = Translation Terminated. Unable to flatten the non geospatial XHTML file.

FME custom transformer EXTRACT_COLLECTION_START_END_DATE
Description: 
Custom transformer utilisé pour extraire une étendue temporelle lorsque possible dans une chaine de caractère. Le custom a 3 actions possibles à poser.
Si la chaine de caractère est vide, on attribue la date de début à 0001-01-01. La date de fin est vide 
Si la chaine de caractère match une des expression régulière définies dans le code, le programme extrait la date de début et aussi de fin lorque présente 
Si la chaine de caractère ne matche pas l'expression régulière, il est possibile de définir manuellement les valeurs de début/fin grâce à une lookup table
Dans le cas où aucune des trois actions n'est possible, la feature ressort par le port unworking_extraction. Dans ce cas, on doit mettre à jour la lookup table ou bien ajouter une regex dans le code python.
Définifition de la lookup table: 
Input Ports
On utilise une lookup table selon template yaml suivant:
CSV_COLUMNS:
source_date_extent: [trim, no_null]
data_collection_start_date: [trim, no_null]
data_collection_end_date: [trim] 
#
CREATE_KEY_VALUE:
#
NO_DUPLICATE:
DUP_1: [source_date_extent]
#
CHECK_DOMAIN:
Output Ports
Lorsque l'extraction fonctionne, on ajoute les attributs data_collection_start_date et data_collection_end_date. Lorsque ça ne fonctionne pas, l'attribut unmatched_date_extent contient la chaine de caractère non matchée.

Parameters:
- CSV_PATH = C:\Data\PT_Harvester\LOOKUP_TABLES
- PT = NS
- DATE_EXTENT =
- FEATURE_TYPE =

LOOKUP_TABLES_READER_NG
    CSV_ENCODING = utf-8
    CSV_PATH = $(CSV_PATH)
    FEATURE_TYPE = $(FEATURE_TYPE)
    PT = $(PT)
    -> AttributeExposer_2
AttributeExposer_2
    ATTR_LIST = source_date_extent,data_collection_start_date,data_collection_end_date
    -> AttributeCreator_3
AttributeCreator_3
    ATTR_TABLE = SET_TO _ordre = 1
    -> Sorter
Input (input)
    -> AttributeCreator
AttributeCreator
    ATTR_TABLE = SET_TO _date_to_process = $(DATE_EXTENT)
    -> AttributeCreator_2
AttributeCreator_2
    ATTR_TABLE = SET_TO _ordre = 2
    -> Sorter
Sorter
    SORT_PARM = _ordre NUMERIC ASCENDING
    SORTED -> PythonCaller
PythonCaller
    NEW_ATTRIBUTES = data_collection_start_date data_collection_end_date unmatched_date_extent
    PYTHONSOURCE = from Python.EXTRACT_COLLECTION_START_END_DATE import collection_end_start_date_extractor
    PYTHONSYMBOL = collection_end_start_date_extractor
    -> AttributeRemover
AttributeRemover
    REMOVE_ATTRS = _date_to_process,_ordre
    -> TestFilter
Note: Extraction fonctionnelle
TestFilter
    DEFAULT_VALUE = Yes
    TEST_LIST = "BOOL_OP,OR,COMPOSITE_TEST,""""""1"""""",TEST_CLAUSE,TEST unmatched_date_extent ATTRIBUTE_HAS_A_VALUE """,No
    No -> ATTRIBUTE_UNEXPOSER
    Yes -> ATTRIBUTE_UNEXPOSER_2
ATTRIBUTE_UNEXPOSER_2
    -> Output (output)
Output (output)
ATTRIBUTE_UNEXPOSER
    -> AttributeExposer
AttributeExposer
    ATTR_LIST = unmatched_date_extent
    -> Unworking_extent (output)
Unworking_extent (output)

FME custom transformer JSON_PUBLISHER_NG
Description 
This custom transformer is translating the input CKAN metadata model into the JSON TBS model.  The rules on how to map the input CKAN features attributes into the TBS attributes are stored in the JSON configuration file. The JSON templates used to create the JSON file are supplied with the input parameters of the custom transformers.  The mapping into JSON file is done with FME JSON Templater transformer.
Input Ports 
Input: The input metadata records to translate into the JSON TBS model.
Output Ports 
OUTPUT_LOCAL: The output metdata records translated into the JSON TBS model.
Parameters 
JSON_ROOT_TEMPLATE: File system address containing the root section of the TBS model in JSON format.
JSON_RESOURCE_TEMPLATE: File system address containing the resources section of the TBS model in JSON format.

Parameters:
- JSON_ROOT_TEMPLATE =
- JSON_RESOURCE_TEMPLATE =
- Keywords_EN =   # Keywords list in English
- Keywords_FR =   # Keywords list in French
- Topic_LIST =   # Enter Topic list
- Subject_LIST =   # Enter Subject list
- FEATURE_TYPE =
- IN_CSV_LOOKUP_TABLES_DIR =
- P-T_ABBR =

Note: Read the CSV lookup table
LOOKUP_TABLES_READER_NG
    CSV_ENCODING = utf-8
    CSV_PATH = $(IN_CSV_LOOKUP_TABLES_DIR)
    FEATURE_TYPE = $(FEATURE_TYPE)
    PT = $(P-T_ABBR)
    -> AttributeExposer
AttributeExposer
    ATTR_LIST = TBS_ATTRIBUTES,FEATURE_ATTRIBUTES,SECTION
    -> AttributeSplitter_2
INPUT (input)
    -> AttributeCreator
AttributeCreator
    ATTR_TABLE = SET_TO CKAN_Transaction = Yes
    -> AttributeExposer_4
AttributeExposer_4
    ATTR_LIST = resources{},id
    -> FeatureMerger [REQUESTOR]
Sorter_2
    SORT_PARM = _order NUMERIC ASCENDING
    SORTED -> PythonCaller_2
Note: Python script utilizes attribute names and list attribute names created by the config file to convert metadata attribute keys to the HNAP_ATTRIBUTE Keys created from the config file. The HNAP_ATTRIBUTE keys are consumed by the XML Templates used to build the metadata XML file
PythonCaller_2
    PYTHONSOURCE:
      import fme
      import fmeobjects
      from Python.FME_utils import FME_utils

      # Template Class Interface:
      # When using this class, make sure its name is set as the value of
      # the 'Class or Function to Process Features' transformer parameter
      class FeatureProcessor(object):
          def __init__(self):
              #Creating dictionnairy
              #{key:[{a:b}{c:d},{a:e}{b:f}],key:[{a:b}{c:d},{a:e}{b:f}]}

              self.config={}
          def input(self,feature):
              #Config or metadata
              if int(feature.getAttribute('_order'))==1:
                 #Process config records
                 print (feature.getAttribute('_element_count'))
                 n2=[]
                 for i in range(feature.getAttribute('_element_count')):
                     n3={}
                     n3['TBS_ATTRIBUTES']=feature.getAttribute('_list{%s}.TBS_ATTRIBUTES'%(str(i)))
                     n3['FEATURE_ATTRIBUTES']=feature.getAttribute('_list{%s}.FEATURE_ATTRIBUTES'%(str(i)))
                     n3['LIST_NAME']=feature.getAttribute('extracted_list_name')


                     n2.append(n3)

                 self.config[feature.getAttribute('SECTION')]=n2

              else:

                  #Process metadata records
                  for keys in self.config:

                      if self.config[keys][0]['LIST_NAME']:

                          #Need to look in list to create multiple feature

                          # Only if metadatasection exists
                          max_index=FME_utils.max_index_attribute_list(feature,'%s{}'%(self.config[keys][0]['LIST_NAME']))
                          for index in range(max_index+1):
                              new_feature=fmeobjects.FMEFeature()
                              new_feature.setAttribute('SECTION',keys)

                              for i in self.config[keys]:
                                  new_att=i['TBS_ATTRIBUTES']

                                  if '{}' in i['FEATURE_ATTRIBUTES']:
                                      new_values=feature.getAttribute('%s{%s}.%s'%(i['FEATURE_ATTRIBUTES'].split('{}.')[0],str(index),i['FEATURE_ATTRIBUTES'].split('{}.')[1]))
                                  else:
                                      new_values=feature.getAttribute(i['FEATURE_ATTRIBUTES'])
                                  new_feature.setAttribute(new_att,new_values)

                              self.pyoutput(new_feature)

                      else:
                          #No list related to metasection, just need to parse regular attributes
                          new_feature=fmeobjects.FMEFeature()
                          new_feature.setAttribute('SECTION',keys)
                          for i in self.config[keys]:
                              new_att=i['TBS_ATTRIBUTES']
                              new_values=feature.getAttribute(i['FEATURE_ATTRIBUTES'])
                              new_feature.setAttribute(new_att,new_values)
                          self.pyoutput(new_feature)

          def close(self):
              pass
    PYTHONSYMBOL = FeatureProcessor
    -> AttributeFilter
OUTPUT_LOCAL (output)
Terminator_6
    MESSAGE = Translation Terminated

Bookmark: Adding PyCSW_Transaction, date_runtime, TBS_topic, TBS_subject, keywords_fr and keywords_fr attribute to ROOT +
Creator
    GEOMTYPE = Geometry Object
    NUM = 1
    CREATED -> AttributeCreator_8
    CREATED -> AttributeCreator_11
    CREATED -> AttributeCreator_5
    CREATED -> AttributeCreator_10
    CREATED -> AttributeCreator_9
    CREATED -> AttributeCreator_12
Note: CKAN Transaction
AttributeCreator_8
    ATTR_TABLE:
      SET_TO FEATURE_ATTRIBUTES = CKAN_Transaction
      SET_TO TBS_ATTRIBUTES = CKAN_Transaction
      SET_TO SECTION = ROOT
    -> AttributeExposer
Note: date_runtime
AttributeCreator_11
    ATTR_TABLE:
      SET_TO FEATURE_ATTRIBUTES = date_runtime
      SET_TO TBS_ATTRIBUTES = date_runtime
      SET_TO SECTION = ROOT
    -> AttributeExposer
Note: TBS_subject
AttributeCreator_5
    ATTR_TABLE:
      SET_TO FEATURE_ATTRIBUTES = TBS_subject
      SET_TO TBS_ATTRIBUTES = TBS_subject
      SET_TO SECTION = ROOT
    -> AttributeExposer
Note: TBS_topic
AttributeCreator_10
    ATTR_TABLE:
      SET_TO FEATURE_ATTRIBUTES = TBS_topic
      SET_TO TBS_ATTRIBUTES = TBS_topic
      SET_TO SECTION = ROOT
    -> AttributeExposer
Note: keywords_fr
AttributeCreator_9
    ATTR_TABLE:
      SET_TO FEATURE_ATTRIBUTES = keywords_fr
      SET_TO TBS_ATTRIBUTES = keywords_fr
      SET_TO SECTION = ROOT
    -> AttributeExposer
Note: keywords_en
AttributeCreator_12
    ATTR_TABLE:
      SET_TO FEATURE_ATTRIBUTES = keywords_en
      SET_TO TBS_ATTRIBUTES = keywords_en
      SET_TO SECTION = ROOT
    -> AttributeExposer

Bookmark: Searching for attribuite linked to more metadatasection
Note: From the lookup table, the METADATA_SECTION attribute for HNAP_ATTRIBUTES found in mulitple metadata sections is split into one attribute per METADATA_SECTION creating METADATA_SECTION{} list
AttributeSplitter_2
    ATTR_NAME = SECTION
    DELIMITER = ;
    DROP_EMPTY_PARTS = No
    LIST_NAME = SECTION
    TRIM_OPTION = Both
    -> ListExploder_9
Note: SECTION{} list is exploded to its individual parts
ListExploder_9
    ATTR_ACCUM_MODE = Merge List Attributes
    ATTR_CONFLICT_RES = Use List Attribute Values
    INDEX_ATTR = _element_index
    LIST_ATTR = SECTION{}
    ELEMENTS -> StringSearcher
    <REJECTED> -> Terminator_2
Terminator_2
    MESSAGE = Translation Terminated

Bookmark: Searching for list containing attributes. Need to generate multiple records from them
Note: Searches lookup table for FEATURE_ATTRIBUTES that are list attributes.
StringSearcher
    CASE = no
    MATCHED_RESULT_ATTR = _first_match
    REGEXP = {}
    STRING_TO_SEARCH = @Value(FEATURE_ATTRIBUTES)
    MATCHED -> AttributeSplitter_3
    NOT_MATCHED -> AttributeKeeper
Note: Splits list attributes using {} delimiter and creates _list{} list attribute from results
AttributeSplitter_3
    ATTR_NAME = FEATURE_ATTRIBUTES
    DELIMITER = {}
    DROP_EMPTY_PARTS = No
    LIST_NAME = _list
    TRIM_OPTION = Both
    -> AttributeCreator_7
Note: Extracts _list{0} attribute creating list_name attribute which is original FEATURE_ATTRIBUTE list name.
AttributeCreator_7
    ATTR_TABLE = SET_TO list_name = @Value(_list{0})
    -> AttributeKeeper
Note: Removes out of scope attributes
AttributeKeeper
    KEEP_ATTRS = TBS_ATTRIBUTES,FEATURE_ATTRIBUTES,SECTION,list_name
    -> ListBuilder_2

Bookmark: Grouo by metadatasection
Note: Builds _list{} list attributes from FEATURE_ATTRIBUTES, HNAP_ATTRIBUTES and list_name, grouped by METADATA_SECTION attributes
ListBuilder_2
    GROUPS_ORDERED = No
    GROUP_BY = SECTION
    LIST_ATTRS_TO_INCLUDE = FEATURE_ATTRIBUTES list_name TBS_ATTRIBUTES
    LIST_NAME = _list
    -> AttributeCreator_6
Note: Creates _order attribute with value of 1
AttributeCreator_6
    ATTR_TABLE = SET_TO _order = 1
    -> ListElementCounter_2
Note: Retreives _list{} element count for each METADATA_SECTION
ListElementCounter_2
    CNT_ATTR = _element_count
    LIST_NAME = _list{}
    -> ListSearcher

Bookmark: Extracting to identify list and random feature attributes
Note: Searches for _list{}.listname attribute in each METADATA_SECTION
ListSearcher
    INDEX_ATTR = _list_index
    LIST_ATTR = _list{}.list_name
    PREFIX = extracted_
    SEARCH_TYPE = First not matching
    FOUND -> AttributeCreator_2
    NOT_FOUND -> AttributeCreator_2
AttributeCreator_2
    ATTR_TABLE = SET_TO _order = 1
    -> Sorter_2

Bookmark: Adding date_runtime on incomming feature
Creator_2
    GEOMTYPE = Geometry Object
    NUM = 1
    CREATED -> DateTimeStamper
DateTimeStamper
    DATETIME_ATTR = date_runtime
    INCLUDE_OFFSET = NO
    STAMP_TYPE = datetime
    TIMEZONE = utc
    -> DateTimeConverter
DateTimeConverter
    DATETIME_ATTR = date_runtime
    OUT_FORMAT = ISO
    PASSTHROUGH = NO
    REPAIR_INPUT = YES
    -> AttributeKeeper_2
AttributeKeeper_2
    KEEP_ATTRS = date_runtime
    -> FeatureMerger [SUPPLIER]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> ListConcatenator_2
    UNMERGED_REQUESTOR -> Terminator_6
    <REJECTED> -> Terminator_6

Bookmark: Managing keywords, Topics and Subjects
ListConcatenator_2
    DROP_EMPTY_PARTS = No
    LIST_ATTR = $(Keywords_FR)
    SEP = ","
    VAL_ATTR = keywords_fr
    -> ListConcatenator
ListConcatenator
    DROP_EMPTY_PARTS = No
    LIST_ATTR = $(Keywords_EN)
    SEP = ","
    VAL_ATTR = keywords_en
    -> ListConcatenator_3
ListConcatenator_3
    DROP_EMPTY_PARTS = No
    LIST_ATTR = $(Subject_LIST)
    SEP = ","
    VAL_ATTR = TBS_subject
    -> ListConcatenator_4
ListConcatenator_4
    DROP_EMPTY_PARTS = No
    LIST_ATTR = $(Topic_LIST)
    SEP = ","
    VAL_ATTR = TBS_topic
    -> AttributeCreator_3
AttributeCreator_3
    ATTR_TABLE = SET_TO _order = 2
    -> Sorter_2

Bookmark: Création du fichier JSON
AttributeFilter
    ATTR_NAME = SECTION
    ATTR_VALUES = <Empty>,<Missing>,<Null>,<Unfiltered>,ROOT,RESOURCES
    <EMPTY> -> Terminator_4
    <MISSING> -> Terminator_4
    <NULL> -> Terminator_4
    <UNFILTERED> -> Terminator_4
    ROOT -> JSONTemplater [ROOT]
    RESOURCES -> JSONTemplater_2 [ROOT]
Terminator_4
    MESSAGE = ERROR: Unknown SECTION in JSON config file
Note: Creation du JSON pour le root
JSONTemplater
    CONSECUTIVE_GROUPS = No
    GROUP_BY = id
    RESULT_ATTRIBUTE = json_file
    ROOT_QUERY_FILE = $(JSON_ROOT_TEMPLATE)
    VISIBLE_QUERY_VALIDATE = Yes
    -> FeatureMerger_2 [REQUESTOR]
Note: Sorts config file and incoming data attributes so that config file attributes are ranked first.
Note: Creatio de JSON pour chaque ressources
Note: On n'utilise pas les sous -template du JSON template templater car augmente la complexsité quand il faut faire les find&replace pour avoir le bon texte formaté. / On fuisionne les ressources avec le root par la suite
JSONTemplater_2
    CONSECUTIVE_GROUPS = No
    GROUP_BY = id
    RESULT_ATTRIBUTE = json_file_resource
    ROOT_QUERY_FILE = $(JSON_RESOURCE_TEMPLATE)
    VISIBLE_QUERY_VALIDATE = Yes
    -> AttributeExposer_2
Note: Fusion des ressources de même id
ListBuilder
    GROUP_BY = id
    LIST_ATTRS_TO_INCLUDE = json_file_resource
    LIST_NAME = _list
    -> FeatureMerger_2 [SUPPLIER]
Note: Transfert des resources fuisionnées sur le root
FeatureMerger_2
    ATTR_ACCUM_MODE = Merge Supplier
    ATTR_CONFLICT_RES = Use Requestor
    IGNORE_NULLS = No
    JOIN_KEYS = @Value(id) @Value(id) AUTO
    MERGE_TYPE = Attributes Only
    PROCESS_DUPS = NO
    REJECT_NULL_MISSING_KEYS = No
    SUPPLIERS_FIRST = No
    MERGED -> ListConcatenator_5
    UNMERGED_REQUESTOR -> Terminator
    UNUSED_SUPPLIER -> Terminator
    <REJECTED> -> Terminator
Terminator
    MESSAGE = Translation Terminated

Bookmark: Find&Replace pour gérer la langue
AttributeExposer_2
    ATTR_LIST = resource_language
    -> StringReplacer_5
StringReplacer_5
    CASE = NO
    FIND_TEXT = "resource_language"
    NO_MATCH = _FME_NO_OP_
    REGEXP = NO
    REPLACE_TEXT = @Value(resource_language)
    SRC_ATTRS = json_file_resource
    -> ListBuilder

Bookmark: Transfert des ressources dans le JSON FILE
ListConcatenator_5
    DROP_EMPTY_PARTS = No
    LIST_ATTR = _list{}.json_file_resource
    SEP = ,
    VAL_ATTR = resources2replace
    -> StringReplacer_2
StringReplacer_2
    CASE = NO
    FIND_TEXT = "FME_RESOURCES_SUB_TEMPLATE"
    NO_MATCH = _FME_NO_OP_
    REGEXP = NO
    REPLACE_TEXT = @Value(resources2replace)
    SRC_ATTRS = json_file
    -> AttributeExposer_5

Bookmark: Text editing
AttributeExposer_5
    ATTR_LIST = metadata_contact_fr,metadata_contact_en,email
    -> PythonCaller_4
Note: Gestion de FME_CONTACT_INFORMATION_VALUES
PythonCaller_4
    PYTHONSOURCE:
      import fme
      import fmeobjects
      # Template Function interface:
      # When using this function, make sure its name is set as the value of
      # the 'Class or Function to Process Features' transformer parameter
      def processFeature(feature):
          json_file=feature.getAttribute('json_file')


          email=''
          contact_form_en=''
          contact_form_fr=''
          metadata_contact_fr=feature.getAttribute('metadata_contact_fr')
          metadata_contact_en=feature.getAttribute('metadata_contact_en')

          if feature.getAttribute('email'):
              email=r',\"electronic_mail_address\": \"%s\"'%(feature.getAttribute('email'))

          if feature.getAttribute('contact_form_en'):
              contact_form_en=r',\"contact_form\": \"%s\"'%(feature.getAttribute('contact_form_en'))
          if  feature.getAttribute('contact_form_fr'):
              contact_form_fr=r',\"contact_form\": \"%s\"'%(feature.getAttribute('contact_form_fr'))

          remplacement=r'"{\"fr\": {\"organization_name\": \"%s\"%s%s},\"en\": {\"organization_name\": \"%s\"%s%s}}"'%(metadata_contact_fr,email,contact_form_fr,metadata_contact_en,email,contact_form_en)

          json_new=json_file.replace(r'"FME_CONTACT_INFORMATION_VALUES"',remplacement)
          feature.setAttribute('json_file',json_new)
    PYTHONSYMBOL = processFeature
    -> StringReplacer_3
Note: Remplacement de la chaine de caractère pour keyword fr
StringReplacer_3
    CASE = NO
    FIND_TEXT = "FME_KEYWORDS_FR"
    NO_MATCH = _FME_NO_OP_
    REGEXP = NO
    REPLACE_TEXT = ["@Value(keywords_fr)"]
    SRC_ATTRS = json_file
    -> StringReplacer_4
Note: Remplacement de la chaine de caractère pour keyword en
StringReplacer_4
    CASE = NO
    FIND_TEXT = "FME_KEYWORDS_EN"
    NO_MATCH = _FME_NO_OP_
    REGEXP = NO
    REPLACE_TEXT = ["@Value(keywords_en)"]
    SRC_ATTRS = json_file
    -> StringReplacer_6
Note: Remplacement de la chaine de caractère pour tbs_subject
StringReplacer_6
    CASE = NO
    FIND_TEXT = "FME_SUBJECT_VALUES"
    NO_MATCH = _FME_NO_OP_
    REGEXP = NO
    REPLACE_TEXT = ["@Value(TBS_subject)"]
    SRC_ATTRS = json_file
    -> StringReplacer_7
Note: Remplacement de la chaine de caractère pour tbs_topic
StringReplacer_7
    CASE = NO
    FIND_TEXT = "FME_TOPIC_CATEGORY"
    NO_MATCH = _FME_NO_OP_
    REGEXP = NO
    REPLACE_TEXT = ["@Value(TBS_topic)"]
    SRC_ATTRS = json_file
    -> StringReplacer
Note: Nettoyage des listes vides
StringReplacer
    CASE = NO
    FIND_TEXT = [""]
    NO_MATCH = _FME_NO_OP_
    REGEXP = NO
    REPLACE_TEXT = [ ]
    SRC_ATTRS = json_file
    -> AttributeKeeper_3
AttributeKeeper_3
    KEEP_ATTRS = id,json_file
    -> OUTPUT_LOCAL (output)

FME custom transformer ON_DATE_FORMATTER

INPUT (input)
    -> AttributeExposer
Note: Exposes attributes required by this transformer
AttributeExposer
    ATTR_LIST = record_create_date,record_publish_date,record_last_modified,resources{}.created,resources{}.data_last_updated,resources{}.data_range_end,resources{}.data_range_start,id
    -> DateTimeConverter_3
Note: Converts date attributes to ISO yyyy-dd-mm format
DateTimeConverter_3
    DATETIME_ATTR = record_create_date record_last_modified record_publish_date
    OUT_FORMAT = %Y-%m-%d
    PASSTHROUGH = NO
    REPAIR_INPUT = YES
    -> UUIDGenerator_2
    <REJECTED> -> Cloner_6
Note: Creates unique ID for remerging attributes
UUIDGenerator_2
    UUID_ATTR = uuid_date
    -> AttributeKeeper_2
    -> FeatureMerger_5 [REQUESTOR]
Note: Retains unique ID and resources list
AttributeKeeper_2
    KEEP_ATTRS = uuid_date
    KEEP_LIST = resources{}
    -> ListExploder_2
Note: Explodes resources list
ListExploder_2
    ATTR_ACCUM_MODE = Merge List Attributes
    ATTR_CONFLICT_RES = Use List Attribute Values
    INDEX_ATTR = _element_index
    LIST_ATTR = resources{}
    ELEMENTS -> DateTimeConverter_4
Note: Converts selected dates extracted from resources list values to ISO yyyy-dd-mm format
DateTimeConverter_4
    DATETIME_ATTR = data_range_end data_last_updated created data_range_start
    OUT_FORMAT = %Y%m%d
    PASSTHROUGH = YES
    REPAIR_INPUT = YES
    -> ListBuilder_5
Note: Rebuilds resources list
ListBuilder_5
    GROUP_BY = uuid_date
    LIST_NAME = resources
    -> ListRangeExtractor
Note: Converts maximum value of resources{}date_range_end attributes to data_collection_end_date attribute
ListRangeExtractor
    MAX = data_collection_end_date
    MIN = _dump
    SRC_LIST = resources{}.data_range_end
    -> ListRangeExtractor_2
Note: Converts maximum value of resources{}date_range_start attributes to data_collection_start_date attribute
ListRangeExtractor_2
    MAX = _dump
    MIN = data_collection_start_date
    SRC_LIST = resources{}.data_range_start
    -> AttributeKeeper_3
Note: Retains only date attributes and discards all others
AttributeKeeper_3
    KEEP_ATTRS = data_collection_end_date,uuid_date,data_collection_start_date
    -> DateTimeConverter_5
Note: Converts data_collection_start_date and data_collection_end_date attributes to yyyy-mm-dd format
DateTimeConverter_5
    DATETIME_ATTR = data_collection_end_date data_collection_start_date
    OUT_FORMAT = %Y-%m-%d
    PASSTHROUGH = YES
    REPAIR_INPUT = YES
    -> FeatureMerger_5 [SUPPLIER]
Note: Remerges attributes
FeatureMerger_5
    ATTR_ACCUM_MODE = Merge Supplier
    ATTR_CONFLICT_RES = Use Supplier
    IGNORE_NULLS = No
    JOIN_KEYS = @Value(uuid_date) @Value(uuid_date) AUTO
    MERGE_TYPE = Attributes Only
    PROCESS_DUPS = NO
    REJECT_NULL_MISSING_KEYS = No
    SUPPLIERS_FIRST = No
    MERGED -> Tester
    <REJECTED> -> Cloner_5
Note: Tests data_collection_start_date for a value
Tester
    BOOL_OP = OR
    COMPOSITE_TEST = 1
    TEST_CLAUSE = TEST data_collection_start_date ATTRIBUTE_HAS_A_VALUE ""
    TEST_MODE = TEST
    PASSED -> Tester_2
    FAILED -> AttributeCreator_5
Note: Sets data_collection_start_date to 0001-01-01 where missing
AttributeCreator_5
    ATTR_TABLE = SET_TO data_collection_start_date = 0001-01-01
    -> Tester_2
Note: Tests record_publish_date for value
Tester_2
    BOOL_OP = OR
    COMPOSITE_TEST = 1
    TEST_CLAUSE = TEST record_publish_date ATTRIBUTE_HAS_A_VALUE ""
    TEST_MODE = TEST
    PASSED -> Tester_3
    FAILED -> DateTimeStamper
Note: Extracts current date
DateTimeStamper
    DATETIME_ATTR = _timestamp
    INCLUDE_OFFSET = NO
    STAMP_TYPE = datetime
    TIMEZONE = local
    -> DateTimeCalculator
Note: Calculate day eight days previous to set as record_publish_date where missing. This is to avoid constant recalculating of value when data is processed weekly. Should be changed if processing schedule changes to longer intervals
DateTimeCalculator
    MODE = DATETIMECALC_1_ADD_INTERVAL
    OPERATION_PARAMETERS = START_DATETIME]@Value(_timestamp)]OPERATOR]SUBTRACT]YEARS]0]MONTHS]0]DAYS]8]HOURS]0]MINUTES]0]SECONDS]0]RESULT_DATETIME]record_publish_date]FME_CONTROLLER_QUERY_FILE]transformers/dependencies/datetimecalculator/DATETIMECALC_1_ADD_INTERVAL.fme
    -> DateTimeConverter_2
    <REJECTED> -> Cloner
Note: Sets record_publish_date to ISO yyyy-dd-mm format
DateTimeConverter_2
    DATETIME_ATTR = record_publish_date
    OUT_FORMAT = %Y-%m-%d
    PASSTHROUGH = NO
    REPAIR_INPUT = YES
    -> Tester_3
    <REJECTED> -> Cloner_4
Note: Tests if record_last_modified has a value
Tester_3
    BOOL_OP = OR
    COMPOSITE_TEST = 1
    TEST_CLAUSE = TEST record_last_modified ATTRIBUTE_HAS_A_VALUE ""
    TEST_MODE = TEST
    PASSED -> AttributeCreator_8
    FAILED -> AttributeCreator_7
Note: Sets record_last_modified to record_publish_date where missing
AttributeCreator_7
    ATTR_TABLE = SET_TO record_last_modified = @Value(record_publish_date)
    -> AttributeCreator_8
Note: Sets record_create_date to record_publish_date
AttributeCreator_8
    ATTR_TABLE = SET_TO record_create_date = @Value(record_publish_date)
    -> AttributeRemover
Note: Removes out of scope attributes
AttributeRemover
    LIST_ATTRS = resources{}.created resources{}.data_last_updated resources{}.data_range_end resources{}.data_range_start
    REMOVE_ATTRS = uuid_date
    -> ATTRIBUTE_UNEXPOSER
ATTRIBUTE_UNEXPOSER
    -> OUTPUT (output)
OUTPUT (output)
Note: Crash avoidance
Cloner_4
    COPIES = 1
    COPYATT = _copynum
Note: Crash avoidance
Cloner
    COPIES = 1
    COPYATT = _copynum
Note: Crash prevention
Cloner_5
    COPIES = 1
    COPYATT = _copynum
Cloner_6
    COPIES = 1
    COPYATT = _copynum
