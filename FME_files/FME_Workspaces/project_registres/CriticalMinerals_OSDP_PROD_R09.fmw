FME workspace CriticalMinerals_OSDP_PROD_R09.fmw

Parameters:
- ENV = STAGING
- Last_CriticalMinerals_file =
- TEXT = 2025-02-20T00:04:24Z   # Date_Last_Update Date du timeStamp sur GCGEO (22b2db8a-dc12-47f2-9737-99d3da921751) YYYY-MM-DDThh:mm:ssZ
- Date_Published = 20210111   # "{}" Date de Publication sur GCGEO(22b2db8a-dc12-47f2-9737-99d3da921751) (AAAA-MM-JJ)
- Date_Start = 20240101   # "{}" Début du Time Period sur GCGEO (22b2db8a-dc12-47f2-9737-99d3da921751) (AAAA-MM-JJ)
- Date_End = 20241231   # "{}" Fin time Period sur GCGEO (22b2db8a-dc12-47f2-9737-99d3da921751) (AAAA-MM-JJ)

Creator
    GEOMTYPE = Geometry Object
    NUM = 1
    CREATED -> DateTimeStamper
    CREATED -> AttributeCreator_11
    CREATED -> FeatureReader_2 [INITIATOR]
    CREATED -> FeatureReader [INITIATOR]
FeatureReader_2
    ATTR_ACCUM_MODE = Only Use Result
    COMBINE_GEOM = Use Result
    DATASET = https://ftp.maps.canada.ca/pub/nrcan_rncan/Mining-industry_Industrie-miniere/critical_mineral-mineraux_critiques/critical_minerals.gdb.zip
    FILEGDB_QUERY_FEATURE_TYPES_FOR_MERGE_FILTERS = Yes
    FILEGDB_SIMPLE_DONUT_GEOMETRY = simple
    FILEGDB_STRIP_GUID_GLOBALID_BRACES = no
    FILEGDB_USE_SEARCH_ENVELOPE = NO
    FORMAT = FILEGDB
    INTERACT = <No Spatial Filter>
    OUTPUT_FEATURES_DISPLAY = Schema and Data Features
    <OTHER> -> AttributeExposer
    <REJECTED> -> Terminator
AttributeExposer
    ATTR_LIST = ActivityStatusEN,ActivityStatusFR,CommoditiesEN,CommoditiesFR,DevelopmentStageEN,DevelopmentStageFR,Latitude,Longitude,ID,OperationGroupEN,OperationGroupFR,OperatorOwnersEN,OperatorOwnersFR,PropertyNameEN,PropertyNameFR,ProvincesEN,ProvincesFR,Website
    -> AttributeCreator_5
AttributeRemover_2
    LIST_ATTRS = website_list{}
    REMOVE_ATTRS = Activity Status,Commodities,Commodités,Development Stage,Operation Group,Operator Owners,Property Name,Province/Territoire,Province/Territory,ID
    -> AttributeRounder
FeatureHolder
    -> DuplicateFilter
VariableRetriever_2
    SCOPE = Global
    VALUE_ATTR = _datestamp
    VARNAME = DateStamp
    -> VariableRetriever_3
VariableRetriever_3
    SCOPE = Global
    VALUE_ATTR = RecordKeeper.LastSyncTS
    VARNAME = DateLastSync
    -> FeatureWriter [Output]
FeatureWriter
    CSV2_DELIMITER = ,
    CSV2_ENCODING = utf-8
    CSV2_EXISTING_FILE_HANDLING = Yes
    CSV2_FIELD_QUALIFIER_CHARACTER = "
    CSV2_FIELD_QUALIFIER_ESCAPE_CHARACTER = "
    CSV2_QUALIFY_FIELD_NAMES = yes
    CSV2_QUALIFY_FIELD_VALUES = yes
    CSV2_ROW_TERMINATION = System
    CSV2_WRITE_BOM_FOR_UNICODE = Yes
    CSV2_WRITE_FIELD_NAMES = firstrow
    CSV2_WRITE_SCHEMA_FILE = NO
    DATASET = $(FME_SHAREDRESOURCE_DATA)\DDR\Conditioning_Data\Critical_Minerals\GeoDCAT
    DATASET_ATTR = _dataset
    FEATURE_TYPE_LIST_ATTR = _feature_type
    FORMAT = CSV2
    MORE_SUMMARY_ATTRS = _datestamp
    TOTAL_FEATURES_WRITTEN_ATTR = _total_features_written
    SUMMARY -> Execute_Python_3.7_Library
Note: Création du Last CriticalMinerals
Execute_Python_3.7_Library: 7_Library
    EXECUTION_TRACE = +Execute_Python_fileCopy
    Execution_Parameters:
      [
      {"parametersAreAttributeNames":False},
      {
        "source":"$(FME_SHAREDRESOURCE_DATA)\DDR\Conditioning_Data\Critical_Minerals\GeoDCAT\NRCAN-CRITICAL-MINERALS-@Value(_feature_type{0}._datestamp).csv",
        "destination":"$(FME_SHAREDRESOURCE_DATA)\DDR\Conditioning_Data\Critical_Minerals\Last_critical_minerals.csv"
      },
      ]
    Function_Name = fileCopy
    -> AttributeExposer_2
AttributeExposer_2
    ATTR_LIST = ddr_iam_role,osdp_bucket_owner_id,S3_file_upload.iam_role,S3_file_upload.bucket_owner_id,_feature_type{0}._datestamp
    -> AttributeCreator_13
Terminator
    MESSAGE:
      Translation Terminated

      Lecture du fichier source a échouée

Bookmark: Lire Last_CriticalMineral_File (pas les deleted records)
FeatureReader
    ATTRIBUTES = CSV,"Action,""Record Type"",""Contributor System"",""Contributor Org"",""Content Category"",""Publisher (EN)"",""Publisher (FR)"",PublishedFor,""Creator (EN)"",""Creator (FR)"",""Subject Area"",""Subject Topic"",Identifier.Bundle,Identifier.Artifact,""Identifier.Artifact (DOI)"",Identifier.Child,""Title (EN)"",""Title (FR)"",""Description (EN)"",""Description (FR)"",""Keywords (EN)"",""Keywords (FR)"",Date.LastUpdate,Date.Published,Date.Start,Date.End,Coverage.Geometry,Coverage.ProvinceCd,""Coverage.Placename (EN)"",""Coverage.Placename (FR)"",Coverage.Country,Coverage.Region,External.DatasetCategory,External.ProjectCategory,Rights.License,Rights.Disposition,UpdateFrequency,RecordKeeper.Organization,RecordKeeper.System,RecordKeeper.LastUserToModify,RecordKeeper.LastSyncTS,""Citation Total"",Citation.Format[1],""Citation.Value (EN)[1]"",""Citation.Value (FR)[1]"",""Resource Total"",Resource.Type[1],Resource.Format[1],Resource.ServiceProtocol[1],Resource.Language[1],""Resource.Name (EN)[1]"",""Resource.Name (FR)[1]"",""Resource.URL (EN)[1]"",""Resource.URL (FR)[1]"",Resource.Type[2],Resource.Format[2],Resource.ServiceProtocol[2],Resource.Language[2],""Resource.Name (EN)[2]"",""Resource.Name (FR)[2]"",""Resource.URL (EN)[2]"",""Resource.URL (FR)[2]"""
    ATTR_ACCUM_MODE = Only Use Result
    COMBINE_GEOM = Use Result
    CSV2_CASE_SENSITIVE_FIELD_NAMES = Yes
    CSV2_CHUNK_SIZE = 100000
    CSV2_DATA_START_LINE = 2
    CSV2_DELIMITER = ,
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 10000
    CSV2_SCAN_TYPES = Yes
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = $(Last_CriticalMinerals_file)
    FORMAT = CSV2
    INTERACT = <No Spatial Filter>
    OUTPUT_FEATURES_DISPLAY = Schema and Data Features
    SELECTED_PORTS = CSV
    CSV -> Tester_2
    <REJECTED> -> Terminator_4
Note: GARDE SEULEMENT ACTIVE RECORDS
Tester_2
    BOOL_OP = OR
    TEST_CLAUSE = TEST @Value(Action) = U
    TEST_MODE = TEST
    PASSED -> FeatureMerger [REQUESTOR]
Terminator_4
    MESSAGE:
      Translation Terminated

      Lecture du fichier existant a plantée

Bookmark: CRÉATION VARIABLE POUR DATE DE TRAITEMENT ET DATE DU TIMESTAMP DE LA MÉTADONNÉE
DateTimeStamper
    DATETIME_ATTR = _date
    INCLUDE_OFFSET = NO
    STAMP_TYPE = datetime
    TIMEZONE = utc
    -> SubstringExtractor_4
Note: Enlever fractions de secondes
SubstringExtractor_4
    END = 13
    RESULT_ATTR = _datetime
    SRC_STRING = @Value(_date)
    START = 0
    -> DateTimeConverter
    -> DateTimeConverter_4
DateTimeConverter_4
    DATETIME_ATTR = _datetime
    OUT_FORMAT = %Y%m%d%H%M%SZ
    PASSTHROUGH = NO
    REPAIR_INPUT = YES
    -> VariableSetter_3
Note: Date traitement pour nom du fichier
VariableSetter_3
    SCOPE = Global
    VALUE = @Value(_datetime)
    VARNAME = DateStamp
DateTimeConverter
    DATETIME_ATTR = _datetime
    OUT_FORMAT = %Y-%m-%dT%H:%M:%SZ
    PASSTHROUGH = NO
    REPAIR_INPUT = YES
    -> VariableSetter
Note: Date traitement pour / RecordKeeper.LastSyncTS
VariableSetter
    SCOPE = Global
    VALUE = @Value(_datetime)
    VARNAME = DateLastSync
AttributeCreator_11
    ATTR_TABLE = SET_TO Date_LastUpdate = $(Date_Last_Update)
    -> VariableSetter_2

Bookmark: ATTRIBUTS SIMPLES
AttributeCreator_5
    ATTR_TABLE:
      SET_TO Action = U
      SET_TO Record Type = 1
      SET_TO Contributor System = NRCAN-CRITICAL-MINERALS
      SET_TO Contributor Org = GC:NRCan-RNCan
      SET_TO Content Category = Project
      SET_TO Publisher (EN) = Natural Resources Canada
      SET_TO Publisher (FR) = Ressources naturelles Canada
      SET_TO PublishedFor = Author
      SET_TO Creator (EN) = Government of Canada, Natural Resources Canada, Lands and Minerals Sector
      SET_TO Creator (FR) = Gouvernement du Canada, Ressources naturelles Canada, Secteur des terres et des minéraux
      SET_TO Subject Area = Economy & Industry
      SET_TO Operation Group = @Value(OperationGroupEN)
      SET_TO Groupe d'exploitation = @Value(OperationGroupFR)
      SET_TO Property Name = @Value(PropertyNameEN)
      SET_TO Nom de la propriété = @Value(PropertyNameFR)
      SET_TO Operator Owners = @Value(OperatorOwnersEN)
      SET_TO Opérateurs propriétaires = @Value(OperatorOwnersFR)
      SET_TO Province/Territory = @Value(ProvincesEN)
      SET_TO Province/Territoire = @Value(ProvincesFR)
      SET_TO Commodities = @Value(CommoditiesEN)
      SET_TO Commodités = @Value(CommoditiesFR)
      SET_TO Development Stage = @Value(DevelopmentStageEN)
      SET_TO Stade de développement = @Value(DevelopmentStageFR)
      SET_TO Activity Status = @Value(ActivityStatusEN)
      SET_TO Statut des activités = @Value(ActivityStatusFR)
      SET_TO Coverage.Geometry = POINT(@Value(Longitude) @Value(Latitude))
      SET_TO Coverage.Country = CA
      SET_TO Coverage.Region
      SET_TO External.DatasetCategory
      SET_TO External.ProjectCategory
      SET_TO Rights.License = GC-OpenData
      SET_TO Rights.Disposition = Open
      SET_TO UpdateFrequency = P1Y
      SET_TO RecordKeeper.Organization = GC:NRCan-RNCan
      SET_TO RecordKeeper.System = NRCAN-OSDP
      SET_TO RecordKeeper.LastUserToModify = OSDP.NRCAN-CRITICAL-MINERALS.Project
      SET_TO Note Total = 0
      SET_TO Resource Total = FME_CONDITIONAL:DEFAULT_VALUE'1'BOOL_OP;OR;COMPOSITE_TEST;1;TEST @Value(Website) != Not available/Pas disponible'2'FME_NUM_CONDITIONS2___
      SET_TO Resource.Type[1] = Dataset
      SET_TO Resource.Format[1] = HTML
      SET_TO Resource.ServiceProtocol[1] = HTTPS
      SET_TO Resource.Language[1] = eng; fre
      SET_TO Resource.Name (EN)[1] = Critical minerals advanced projects, mines and processing facilities in Canada
      SET_TO Resource.Name (FR)[1] = Projets avancés, mines et installations de traitement de minéraux critiques du Canada
      SET_TO Resource.URL (EN)[1] = https://osdp-psdo.canada.ca/dp/en/search/metadata/NRCAN-FGP-1-22b2db8a-dc12-47f2-9737-99d3da921751
      SET_TO Resource.URL (FR)[1] = https://osdp-psdo.canada.ca/dp/fr/recherche/metadonnees/NRCAN-FGP-1-22b2db8a-dc12-47f2-9737-99d3da921751
      SET_TO Date.Published = $(Date_Published)
      SET_TO Date.LastUpdate = $(Date_Last_Update)
      SET_TO Date.Start = $(Date_Start)
      SET_TO Date.End = $(Date_End)
      SET_TO Identifier.Bundle
      SET_TO Identifier.Artifact (DOI)
      SET_TO Identifier.Child
    -> Tester

Bookmark: 1 ou 2 ressources dans le geoDCAT
Tester
    BOOL_OP = OR
    TEST_CLAUSE = TEST @Value(Resource Total) = 1
    TEST_MODE = TEST
    PASSED -> AttributeRemover_2
    FAILED -> AttributeSplitter
AttributeSplitter
    ATTR_NAME = Website
    DELIMITER = :
    DROP_EMPTY_PARTS = No
    LIST_NAME = website_list
    TRIM_OPTION = Both
    -> AttributeCreator
AttributeCreator
    ATTR_TABLE:
      SET_TO Resource.Type[2] = Website
      SET_TO Resource.Format[2] = HTML
      SET_TO Resource.ServiceProtocol[2] = @UpperCase(@Value(website_list{0}))
      SET_TO Resource.Language[2] = eng; fre
      SET_TO Resource.Name (EN)[2] = Operator Owner Website
      SET_TO Resource.Name (FR)[2] = Site Web de l'opérateur et du propriétaire
      SET_TO Resource.URL (EN)[2] = @Value(Website)
      SET_TO Resource.URL (FR)[2] = @Value(Website)
    -> AttributeRemover_2

Bookmark: arrondir lat/long 3 décimales
AttributeRounder
    PLACES = 3
    ROUND_TYPE = Nearest
    SRC_ATTRS = Latitude Longitude
    -> PythonCaller_2

Bookmark: Coverage.ProvinceCd et Placename
PythonCaller_2
    NEW_ATTRIBUTES = "Coverage.ProvinceCd "
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              PT={}
              PT['Alberta']='AB'
              PT['British Columbia']='BC'
              PT['Manitoba']='MB'
              PT['Nova Scotia']='NS'
              PT['New Brunswick']='NB'
              PT['Newfoundland and Labrador']='NL'
              PT['Northwest Territories']='NT'
              PT['Ontario']='ON'
              PT['Prince Edward Island']='PE'
              PT['Saskatchewan']='SK'
              PT['Quebec']='QC'
              PT['Nunavut']='NU'
              PT['Yukon']='YT'

              for keys in PT:
                  if keys in feature.getAttribute('ProvincesEN'):
                      feature.setAttribute('Coverage.ProvinceCd',feature.getAttribute('ProvincesEN').replace(keys,PT[keys]))



              self.pyoutput(feature)
          def close(self):
              pass
    PYTHONSYMBOL = FeatureProcessor
    -> AttributeCreator_10
AttributeCreator_10
    ATTR_TABLE:
      SET_TO Coverage.Placename (EN) = @Value(PropertyNameEN), @Value(ProvincesEN)
      SET_TO Coverage.Placename (FR) = @Value(PropertyNameFR), @Value(ProvincesFR)
    -> AttributeCreator_31

Bookmark: TITLE
Note: GÉNÉRATION / SECTIONS
AttributeCreator_31
    ATTR_TABLE:
      SET_TO Title_prefix(EN) = Critical Minerals:
      SET_TO Title_prefix(FR) = Minéraux critiques :
      SET_TO Title_location(EN) = @Value(PropertyNameEN), @Value(ProvincesEN)
      SET_TO Title_location(FR) = @Value(PropertyNameFR), @Value(ProvincesFR)
      SET_TO Title_type_part(EN) = FME_CONDITIONAL:DEFAULT_VALUE'@Value(OperationGroupEN)'BOOL_OP;OR;COMPOSITE_TEST;1;TEST @Value(OperationGroupEN) = Project'Advanced projects'BOOL_OP;AND;COMPOSITE_TEST;1;TEST @Value(OperationGroupEN) = Processing'Processing facilities'FME_NUM_CONDITIONS3___
      SET_TO Title_type_part(FR) = FME_CONDITIONAL:DEFAULT_VALUE'@Value(OperationGroupFR)'BOOL_OP;OR;COMPOSITE_TEST;1;TEST @Value(OperationGroupFR) = Projet'Projets avancés'BOOL_OP;AND;COMPOSITE_TEST;1;TEST @Value(OperationGroupFR) = Traitement'Installations de traitement primaire'FME_NUM_CONDITIONS3___
    -> AttributeCreator_32
AttributeCreator_32
    ATTR_TABLE:
      SET_TO Title (EN) = @Value(Title_prefix(EN)) @Value(Title_location(EN)) (@Value(Title_type_part(EN)))
      SET_TO Title (FR) = @Value(Title_prefix(FR)) @Value(Title_location(FR)) (@Value(Title_type_part(FR)))
    -> AttributeRemover
AttributeRemover
    REMOVE_ATTRS = Title_location(EN),Title_location(FR),Title_prefix(EN),Title_prefix(FR),Title_type_part(EN),Title_type_part(FR)
    -> TestFilter

Bookmark: KEYWORDS
TestFilter
    DEFAULT_VALUE = sans_parenthese
    TEST_LIST:
      "BOOL_OP,OR,COMPOSITE_TEST,""""""1 OR 2"""""",TEST_CLAUSE,CASE_INSENSITIVE_TEST @Value(CommoditiesEN) CONTAINS (
      CASE_INSENSITIVE_TEST @Value(CommoditiesFR) CONTAINS (",parentheses
    parentheses -> PythonCaller
    sans_parenthese -> AttributeCreator_8
PythonCaller
    NEW_ATTRIBUTES = KeywordsEN
    PYTHONSOURCE:
      import fme
      import fmeobjects
      import re

      def processFeature(feature):
          pass

      class FeatureProcessor:
          def __init__(self):
              pass

          def transform_elements(self, input_string):
              # Split by semicolons or commas NOT inside parentheses
              parts = re.split(r';|,(?![^()]*\))', input_string)
              result = []

              for part in parts:
                  part = part.strip()
                  if '(' in part and ')' in part:
                      base = part.split('(')[0].strip()
                      if base:  # Add base as-is (do NOT split hyphens)
                          result.append(base)
                      result.append(part)  # Add full part
                  else:
                      # No parentheses: keep the term as-is (do NOT split hyphens)
                      if part:
                          result.append(part)

              # Remove duplicates while preserving order
              seen = set()
              unique_result = []
              for item in result:
                  if item not in seen:
                      seen.add(item)
                      unique_result.append(item)

              return '; '.join(unique_result)

          def input(self, feature):
              input_str = feature.getAttribute('CommoditiesEN')
              if input_str:
                  output_str = self.transform_elements(input_str)
                  feature.setAttribute('KeywordsEN', output_str)
              else:
                  feature.setAttribute('KeywordsEN', '')
              self.pyoutput(feature)

          def close(self):
              pass
    PYTHONSYMBOL = FeatureProcessor
    -> PythonCaller_4
PythonCaller_4
    NEW_ATTRIBUTES = KeywordsFR
    PYTHONSOURCE:
      import fme
      import fmeobjects
      import re

      def processFeature(feature):
          pass

      class FeatureProcessor:
          def __init__(self):
              pass

          def transform_elements(self, input_string):
              # Split by semicolons or commas NOT inside parentheses
              parts = re.split(r';|,(?![^()]*\))', input_string)
              result = []

              for part in parts:
                  part = part.strip()
                  if '(' in part and ')' in part:
                      base = part.split('(')[0].strip()
                      if base:  # Add base as-is (do NOT split hyphens)
                          result.append(base)
                      result.append(part)  # Add full part
                  else:
                      # No parentheses: keep the term as-is (do NOT split hyphens)
                      if part:
                          result.append(part)

              # Remove duplicates while preserving order
              seen = set()
              unique_result = []
              for item in result:
                  if item not in seen:
                      seen.add(item)
                      unique_result.append(item)

              return '; '.join(unique_result)

          def input(self, feature):
              input_str = feature.getAttribute('CommoditiesFR')
              if input_str:
                  output_str = self.transform_elements(input_str)
                  feature.setAttribute('KeywordsFR', output_str)
              else:
                  feature.setAttribute('KeywordsFR', '')
              self.pyoutput(feature)

          def close(self):
              pass
    PYTHONSYMBOL = FeatureProcessor
    -> AttributeCreator_9
AttributeCreator_9
    ATTR_TABLE:
      SET_TO Keywords (EN) = @Value(KeywordsEN)
      SET_TO Keywords (FR) = @Value(KeywordsFR)
    -> AttributeRemover_6
AttributeCreator_8
    ATTR_TABLE:
      SET_TO Keywords (EN) = @Value(CommoditiesEN)
      SET_TO Keywords (FR) = @Value(CommoditiesFR)
    -> StringReplacer
StringReplacer
    CASE = NO
    FIND_TEXT = ,
    NO_MATCH = _FME_NO_OP_
    REGEXP = NO
    REPLACE_TEXT = ;
    SRC_ATTRS = Keywords (EN),Keywords (FR)
    -> AttributeRemover_6
AttributeRemover_6
    LIST_ATTRS = commodity_list_EN{} commodity_list_FR{}
    REMOVE_ATTRS = KeywordsEN,KeywordsFR
    -> StringConcatenator

Bookmark: UUID
StringConcatenator
    ACTION = Create New Attribute
    PARM_LINE = fme_basicstring:18%25:@Value(Title (EN))@Value(Coverage.Geometry)
    VAL_ATTR = UUID_generator
    -> UNIQUE_ID_CREATOR
UNIQUE_ID_CREATOR
    UNIQUE_ATT = @Value(UUID_generator)
    -> AttributeCreator_14
AttributeCreator_14
    ATTR_TABLE = SET_TO Identifier.Artifact = @Value(id)
    -> AttributeCreator_30

Bookmark: CITATIONS
AttributeCreator_30
    ATTR_TABLE:
      SET_TO _citationDate_en = @Value(Date.Published)
      SET_TO _citationDate_fr = @Value(Date.Published)
    -> DateTimeConverter_6
DateTimeConverter_6
    DATETIME_ATTR = _citationDate_en
    OUT_FORMAT = %Y, %B %e
    PASSTHROUGH = NO
    REPAIR_INPUT = YES
    -> DateTimeConverter_7
    <REJECTED> -> Terminator_2
DateTimeConverter_7
    DATETIME_ATTR = _citationDate_fr
    OUT_FORMAT = %Y, %e %B
    PASSTHROUGH = NO
    REPAIR_INPUT = YES
    -> PythonCaller_3
    <REJECTED> -> Terminator_2
PythonCaller_3
    NEW_ATTRIBUTES = _citationDate_fr _error_date
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              mois={}
              mois['January']='janvier'
              mois['February']='février'
              mois['March']='mars'
              mois['April']='avril'
              mois['May']='mai'
              mois['June']='juin'
              mois['July']='juillet'
              mois['August']='août'
              mois['September']='septembre'
              mois['October']='octobre'
              mois['November']='novembre'
              mois['December']='décembre'

              fr=False
              for keys in mois:
                  if keys in feature.getAttribute('_citationDate_fr'):
                      feature.setAttribute('_citationDate_fr',feature.getAttribute('_citationDate_fr').replace(keys,mois[keys]))
                      fr=True

              if not fr:
                  feature.setAttribute('_error_date','Impossible de mapper la date %s en français'%(feature.getAttribute('_citationDate_fr')))


              self.pyoutput(feature)
          def close(self):
              pass
    PYTHONSYMBOL = FeatureProcessor
    -> Tester_4
Tester_4
    BOOL_OP = OR
    TEST_CLAUSE = TEST @Value(_error_date) = ""
    TEST_MODE = TEST
    PASSED -> AttributeCreator_29
    FAILED -> Terminator_3
AttributeCreator_29
    ATTR_TABLE:
      SET_TO Citation.Value (EN)[1] = @Value(Creator (EN)). (@Value(_citationDate_en)). @Value(Title (EN)). @Value(Publisher (EN)), Open Science and Data Platform. https://osdp-psdo.canada.ca/dp/en/search/metadata/NRCAN-CRITICAL-MINERALS-1-@Value(Identifier.Artifact)
      SET_TO Citation.Value (FR)[1] = @Value(Creator (FR)). (@Value(_citationDate_fr)). @Value(Title (FR)). @Value(Publisher (FR)), Plateforme de science et de données ouvertes. https://osdp-psdo.canada.ca/dp/fr/recherche/metadonnees/NRCAN-CRITICAL-MINERALS-1-@Value(Identifier.Artifact)
      SET_TO Citation Total = 1
      SET_TO Citation.Format[1] = APA
    -> AttributeRemover_3
AttributeRemover_3
    REMOVE_ATTRS = _citationDate_en,_citationDate_fr,_error_date
    -> AttributeCreator_3
Terminator_3
    MESSAGE = @Value(_error_date)
Terminator_2
    MESSAGE = Problème avec la gestion des dates pour les citations/références

Bookmark: SUBJECT TOPIC
Note: GÉNÉRATION / SECTIONS
AttributeCreator_3
    ATTR_TABLE:
      SET_TO SubTop_AllRec = Resource Development; Commodities; Mining Industry;
      SET_TO SubTop_uranium = FME_CONDITIONAL:DEFAULT_VALUE'_FME_NO_OP_'BOOL_OP;OR;COMPOSITE_TEST;1;CASE_INSENSITIVE_TEST @Value(CommoditiesEN) CONTAINS uranium'Radioactive Minerals; Nuclear Energy; 'FME_NUM_CONDITIONS2___
      SET_TO SubTop_OperGroupMines = FME_CONDITIONAL:DEFAULT_VALUE'_FME_NO_OP_'BOOL_OP;OR;COMPOSITE_TEST;1;TEST @Value(OperationGroupEN) = Mines and other primary producing sites'Extraction; 'FME_NUM_CONDITIONS2___
      SET_TO SubTop_OperGroupProcessing = FME_CONDITIONAL:DEFAULT_VALUE'_FME_NO_OP_'BOOL_OP;OR;COMPOSITE_TEST;1;TEST @Value(OperationGroupEN) = Processing'Refining Processes; 'FME_NUM_CONDITIONS2___
    -> AttributeCreator_4
AttributeCreator_4
    ATTR_TABLE = SET_TO Subject Topic = @Value(SubTop_AllRec)@Value(SubTop_OperGroupMines)@Value(SubTop_OperGroupProcessing)@Value(SubTop_uranium)
    -> AttributeTrimmer
AttributeTrimmer
    SRC_ATTRS = "Subject Topic"
    TRIM_CHARS = "; "
    TRIM_TO_NONE = Yes
    TRIM_TYPE = Right
    -> AttributeRemover_4
AttributeRemover_4
    REMOVE_ATTRS = SubTop_AllRec,SubTop_OperGroupMines,SubTop_OperGroupProcessing,SubTop_uranium
    -> attr_creator_eng

Bookmark: DESCRIPTIONS
Note: SECTIONS / ANGLAIS
attr_creator_eng: AttributeCreator
    ATTR_TABLE:
      SET_TO commodities = Commodities: @Value(CommoditiesEN)
      SET_TO operation_group = Operation Group: @Value(OperationGroupEN)
      SET_TO property_name = Property Name: @Value(PropertyNameEN)
      SET_TO operator_owners = Operator Owners: @Value(OperatorOwnersEN)
      SET_TO Development_stage = Development Stage: @Value(DevelopmentStageEN)
      SET_TO Activity_status = Activity Status: @Value(ActivityStatusEN)
      SET_TO Desc_Static_en =
        This OSDP record contains specific details regarding a critical minerals site represented within the <a href="/dp/en/search/metadata/NRCAN-FGP-1-22b2db8a-dc12-47f2-9737-99d3da921751" target="_blank">Critical minerals advanced projects, mines and processing facilities in Canada</a> dataset layer produced by Natural Resources Canada, permitting direct search and discovery based on geographic location and/or contextual details.

        The above dataset contains primary processing facilities (e.g., smelters and refineries), mines and advanced projects related to Canada’s 34 critical minerals.

        Advanced projects are those with mineral reserves or resources (measured or indicated), the potential viability of which is supported by a preliminary economic assessment or a prefeasibility/feasibility study. These sites process, produce or consider producing at least one of Canada's critical minerals, but other minerals and metals may also be present.

        Primary processing facilities and mines data are sourced from <a href="/dp/en/search/metadata/NRCAN-FGP-1-000183ed-8864-42f0-ae43-c4313a860720" target="_blank">Principal Mineral Areas, Producing Mines, and Oil and Gas Fields (900A)</a>. Data on advanced critical minerals projects are produced and published annually by Natural Resources Canada, in collaboration with provinces and territories. Data are compiled from a variety of public sources. Natural Resources Canada does not assume responsibility for errors or omissions. Please report any recommended revisions.
    -> Attr_creator_french
Note: SECTIONS / FRANÇAIS
Attr_creator_french: AttributeCreator
    ATTR_TABLE:
      SET_TO commodités = Commodités : @Value(CommoditiesFR)
      SET_TO operation_groupe = Groupe d'exploitation : @Value(OperationGroupFR)
      SET_TO property_nom = Nom de la propriété : @Value(PropertyNameFR)
      SET_TO operator_proprio = Opérateurs propriétaires : @Value(OperatorOwnersFR)
      SET_TO Development_etat = Stade de développement : @Value(DevelopmentStageFR)
      SET_TO Activity_etat = Statut des activités : @Value(ActivityStatusFR)
      SET_TO Desc_Static_fr =
        Cet enregistrement dans la PSDO contient des détails spécifiques concernant un site de minéraux critiques représenté dans la couche de données <a href="/dp/fr/recherche/metadonnees/NRCAN-FGP-1-22b2db8a-dc12-47f2-9737-99d3da921751" target="_blank">Projets avancés, mines et installations de traitement de minéraux critiques du Canada</a> couche d'ensembles de données produite par Ressources naturelles Canada, permettant une recherche et une découverte directes en fonction de l'emplacement géographique et/ou de détails contextuels.

        Ce jeu de données contient les installations de traitement primaire (p. ex., usines de fusion et affineries), les mines et les projets avancés concernant les 34 minéraux critiques du Canada.

        Les projets avancés sont ceux qui comportent des réserves ou des ressources minérales (mesurées ou indiquées) et dont la viabilité potentielle est appuyée par une étude économique préliminaire ou une étude de préfaisabilité/faisabilité. Ces sites traitent, produisent ou envisagent de produire au moins un des minéraux critiques du Canada, mais d'autres minéraux et métaux peuvent aussi être présents.

        Les données sur les installations de traitement primaire et les mines sont tirées de la carte <a href="/dp/fr/recherche/metadonnees/NRCAN-FGP-1-000183ed-8864-42f0-ae43-c4313a860720" target="_blank">Principales régions minières, principales mines productrices, principaux champs de pétrole et de gaz (900A)</a>. Les données sur les projets avancés de minéraux critiques sont produites et publiées annuellement par Ressources naturelles Canada, en collaboration avec les provinces et territoires. Les données sont compilées à partir de diverses sources publiques. Ressources naturelles Canada n'assume aucune responsabilité quant aux erreurs ou omissions. Veuillez signaler toute modification recommandée.
    -> AttributeCreator_7
AttributeCreator_7
    ATTR_TABLE:
      SET_TO Description (EN) = @Value(commodities)
        @Value(operation_group)
        @Value(property_name)
        @Value(operator_owners)
        @Value(Development_stage)
        @Value(Activity_status)
        @Value(Desc_Static_en)
      SET_TO Description (FR) = @Value(commodités)
        @Value(operation_groupe)
        @Value(property_nom)
        @Value(operator_proprio)
        @Value(Development_etat)
        @Value(Activity_etat)
        @Value(Desc_Static_fr)
    -> AttributeRemover_5
AttributeRemover_5
    REMOVE_ATTRS = Desc_Static_en,Desc_Static_fr,Activity_etat,Activity_status,Development_etat,Development_stage,commodities,commodités,operation_group,operation_groupe,operator_owners,operator_proprio,property_name,property_nom,ActivityStatusEN,ActivityStatusFR,CommoditiesEN,CommoditiesFR,DevelopmentStageEN,DevelopmentStageFR,Groupe d'exploitation,Nom de la propriété,OperationGroupEN,OperationGroupFR,OperatorOwnersEN,OperatorOwnersFR,Opérateurs propriétaires,PropertyNameEN,PropertyNameFR,ProvincesEN,ProvincesFR,Stade de développement,Statut des activités
    -> DateTimeConverter_2

Bookmark: gestion des dates
DateTimeConverter_2
    DATETIME_ATTR = Date.Start Date.End Date.Published
    OUT_FORMAT = %Y-%m-%d
    PASSTHROUGH = NO
    REPAIR_INPUT = YES
    -> FeatureMerger [SUPPLIER]

Bookmark: Comparaison du contenu depuis le dernier traitement
Note: Existing / Records
FeatureMerger
    ATTR_ACCUM_MODE = Merge Supplier
    ATTR_CONFLICT_RES = Use Supplier
    IGNORE_NULLS = No
    JOIN_KEYS = @Value(Identifier.Artifact) @Value(Identifier.Artifact) AUTO
    MERGE_TYPE = Attributes Only
    PROCESS_DUPS = NO
    REJECT_NULL_MISSING_KEYS = No
    SUPPLIERS_FIRST = No
    MERGED -> VariableRetriever_4
    UNMERGED_REQUESTOR -> VariableRetriever
    UNUSED_SUPPLIER -> VariableRetriever_4
VariableRetriever
    SCOPE = Global
    VALUE_ATTR = DateLastSync_value
    VARNAME = DateLastSync
    -> AttributeCreator_6
Note: Enregistrements supprimés / Ajustements des attributs
AttributeCreator_6
    ATTR_TABLE:
      SET_TO Action = D
      SET_TO Publisher (EN)
      SET_TO Publisher (FR)
      SET_TO PublishedFor
      SET_TO Creator (EN)
      SET_TO Creator (FR)
      SET_TO Subject Area
      SET_TO Subject Topic
      SET_TO Title (EN)
      SET_TO Title (FR)
      SET_TO Description (EN)
      SET_TO Description (FR)
      SET_TO Keywords (EN)
      SET_TO Keywords (FR)
      SET_TO Date.LastUpdate = @Value(DateLastSync_value)
      SET_TO Date.Published
      SET_TO Date.Start
      SET_TO Date.End
      SET_TO Coverage.Geometry
      SET_TO Coverage.ProvinceCd
      SET_TO Coverage.PlaceName (EN)
      SET_TO Coverage.PlaceName (FR)
      SET_TO Coverage.Country
      SET_TO Coverage.Region
      SET_TO External.DatasetCategory
      SET_TO External.ProjectCategory
      SET_TO Rights.Disposition
      SET_TO Rights.License
      SET_TO UpdateFrequency
      SET_TO RecordKeeper.LastSyncTS = @Value(DateLastSync_value)
      SET_TO Citation Total
      SET_TO Citation.Format[1]
      SET_TO Citation.Value (EN)[1]
      SET_TO Citation.Value (FR)[1]
      SET_TO Note Total
      SET_TO Note.Type[1]
      SET_TO Note.Title (EN)[1]
      SET_TO Note.Title (FR)[1]
      SET_TO Note.Desc (EN)[1]
      SET_TO Note.Desc (FR)[1]
      SET_TO Resource Total = 0
      SET_TO Resource.Type[1]
      SET_TO Resource.Format[1]
      SET_TO Resource.ServiceProtocol[1]
      SET_TO Resource.Language[1]
      SET_TO Resource.Name (EN)[1]
      SET_TO Resource.Name (FR)[1]
      SET_TO Resource.URL (EN)[1]
      SET_TO Resource.URL (FR)[1]
      SET_TO Resource.Type[2]
      SET_TO Resource.Format[2]
      SET_TO Resource.ServiceProtocol[2]
      SET_TO Resource.Language[2]
      SET_TO Resource.Name (EN)[2]
      SET_TO Resource.Name (FR)[2]
      SET_TO Resource.URL (EN)[2]
      SET_TO Resource.URL (FR)[2]
      SET_TO Resource.Type[3]
      SET_TO Resource.Format[3]
      SET_TO Resource.ServiceProtocol[3]
      SET_TO Resource.Language[3]
      SET_TO Resource.Name (EN)[3]
      SET_TO Resource.Name (FR)[3]
      SET_TO Resource.URL (EN)[3]
      SET_TO Resource.URL (FR)[3]
      SET_TO Resource.Type[4]
      SET_TO Resource.Format[4]
      SET_TO Resource.ServiceProtocol[4]
      SET_TO Resource.Language[4]
      SET_TO Resource.Name (EN)[4]
      SET_TO Resource.Name (FR)[4]
      SET_TO Resource.URL (EN)[4]
      SET_TO Resource.URL (FR)[4]
    -> FeatureHolder

Bookmark: MISE À JOUR DateLastUpdate
VariableRetriever_4
    SCOPE = Global
    VALUE_ATTR = _datelastupdate
    VARNAME = DateLastUpdate
    -> AttributeCreator_12
AttributeCreator_12
    ATTR_TABLE = SET_TO Date.LastUpdate = @Value(_datelastupdate)
    -> FeatureHolder

Bookmark: Valider unicité UUID
DuplicateFilter
    INPUT_ORDERED_CHOICE = No
    KEYATTR = Identifier.Artifact
    UNIQUE -> VariableRetriever_2
    DUPLICATE -> Terminator_5
Terminator_5
    MESSAGE:
      Translation Terminated

      Doublons UUID

Bookmark: Upload to OSDP S3 bucket
AttributeCreator_13
    ATTR_TABLE:
      SET_TO name = s3FileUploadACL
      SET_TO region = ca-central-1
      SET_TO s3_ftp_bucket = FME_CONDITIONAL:DEFAULT_VALUE'osdp-lz-prod-sftp-files'BOOL_OP;OR;COMPOSITE_TEST;1;TEST $(ENV) = STAGING'osdp-lz-dev-sftp-files'FME_NUM_CONDITIONS2___
      SET_TO destination_path = Project/Request/NRCAN-CRITICAL-MINERALS-@Value(_feature_type{0}._datestamp).csv
      SET_TO source_file = $(FME_SHAREDRESOURCE_DATA)\DDR\Conditioning_Data\Critical_Minerals\GeoDCAT\NRCAN-CRITICAL-MINERALS-@Value(_feature_type{0}._datestamp).csv
    -> Execute_decrypt
Execute_decrypt: 7_Library
    EXECUTION_TRACE = +Execute_decrypt
    Execution_Parameters:
      {
      "name":"name",
      "region":"region",
      "key_list" :
          [{
            "inputAttribute":"ddr_iam_role",
            "outputAttribute":"S3_file_upload.iam_role"
            },
           {
            "inputAttribute":"osdp_bucket_owner_id",
            "outputAttribute":"S3_file_upload.bucket_owner_id"
            }
           ]
      }
    Function_Name = decryptSecret
    -> Execute_s3FileUploadACL_2
Execute_s3FileUploadACL_2: 7_Library
    EXECUTION_TRACE = $(WORKSPACE_NAME)+Execute_s3FileUploadACL
    Execution_Parameters:
      {
      'iam_role':'S3_file_upload.iam_role',
      'ftp_path':'destination_path',
      'fme_server_path':'source_file',
      's3_ftp_bucket':'s3_ftp_bucket',
      'bucket_owner_id':'S3_file_upload.bucket_owner_id'
      }
    Function_Name = s3FileUploadACL

Bookmark: DATE_LAST_uPDATE
VariableSetter_2
    SCOPE = Global
    VALUE = @Value(Date_LastUpdate)
    VARNAME = DateLastUpdate

FME custom transformer Interative_translation

PythonCaller_Input (input)
    -> AttributeExposer
AttributeExposer
    ATTR_LIST = _iteration,_attr2translate,_attrlist2translate
    -> PythonCaller
Note: Translation with AWS
PythonCaller
    NEW_ATTRIBUTES = _translation_problem
    PYTHONSOURCE:
      import fme
      import fmeobjects
      import time

      def translate_attributes(inText,inlang,outlang):
          try:
              import boto3



              translate = boto3.client('translate', 'ca-central-1', use_ssl=True)
              result = translate.translate_text(Text=inText,SourceLanguageCode=inlang, TargetLanguageCode=outlang).get('TranslatedText')
              return result
          except:
              print ('NE FONCTIONNE PAS DU PREMIER COUP')
              print('PROBLEME _________________________________')
              print(inText)
              raise


      # Template Function interface:
      # When using this function, make sure its name is set as the value of
      # the 'Class or Function to Process Features' transformer parameter
      def processFeature(feature):


          attributestranslation=feature.getAttribute('_attr2translate')
          list_atttranslation=feature.getAttribute('_attrlist2translate')

          try:

              if feature.getAttribute('_mode')==r'English-->French':
                  in_lang="en"
                  out_lang="fr"
                  out_suffix=r'_fr'
              else:
                  in_lang="fr"
                  out_lang="en"
                  out_suffix=r'_en'



              if  attributestranslation:

                  for i in attributestranslation.split(','):
                      text = feature.getAttribute(i)
                      if text and not feature.getAttribute('%s%s'%(i,out_suffix)):

                          if feature.getAttribute('_aws_activation').lower()=='yes':
                              translated_text = translate_attributes(text,in_lang,out_lang)
                          else:
                              translated_text='Translation of '+text
                          if translated_text:
                              feature.setAttribute('%s%s'%(i,out_suffix),translated_text)

              if list_atttranslation:
                  for attr in list_atttranslation.split(','):
                      temp_list_value=feature.getAttribute(attr)
                      if (temp_list_value):
                          list_name=attr.split('{}.')[0]
                          list_attr=attr.split('{}.')[1]
                          list_len=len(temp_list_value)

                          for k in range(list_len):
                              temp_attr_name='%s{%d}.%s'%(list_name,k,list_attr)
                              temp_value=feature.getAttribute(temp_attr_name)

                              if temp_value and not feature.getAttribute('%s%s'%(temp_attr_name,out_suffix)):

                                  if feature.getAttribute('_aws_activation').lower()=='yes':
                                      translated_text = translate_attributes(temp_value,in_lang,out_lang)
                                  else:
                                      translated_text='Translation of '+temp_value
                                  if translated_text:
                                      feature.setAttribute('%s%s'%(temp_attr_name,out_suffix),translated_text)


              feature.setAttribute('_translation_problem',0)
          except:
              feature.setAttribute('_translation_problem',1)
    PYTHONSYMBOL = processFeature
    -> Tester_2
Note: Translation issues ?
Tester_2
    BOOL_OP = OR
    TEST_CLAUSE = TEST @Value(_translation_problem) = 0
    TEST_MODE = TEST
    PASSED -> PythonCaller_5
    FAILED -> Tester
Note: Replacing URL in translated text
PythonCaller_5
    PYTHONSOURCE:
      import fme
      import fmeobjects
      # Template Function interface:
      # When using this function, make sure its name is set as the value of
      # the 'Class or Function to Process Features' transformer parameter
      def processFeature(feature):
          try:

              if feature.getAttribute('_mode')==r'English-->French':
                  out_suffix=r'_fr'
              else:
                  out_suffix=r'_en'

              #Regeular attributes
              attr2Translate=feature.getAttribute('_attr2translate')
              if attr2Translate:
                  for attr in attr2Translate.split(','):
                      indice_https=0
                      indice_http=0
                      indice_ftp=0

                      temp_translated_value=feature.getAttribute('%s%s'%(attr,out_suffix))
                      if temp_translated_value:
                          #Catching pre identified URL
                          list_urls_https=[]
                          list_urls_http=[]
                          list_urls_ftp=[]
                          list_urls_https=feature.getAttribute('_aws_translate_temp_urls_https_%s{}'%(attr))
                          list_urls_http=feature.getAttribute('_aws_translate_temp_urls_http_%s{}'%(attr))
                          list_urls_ftp=feature.getAttribute('_aws_translate_temp_urls_ftp_%s{}'%(attr))


                          if list_urls_https:
                              for url in list_urls_https:
                                  temp_translated_value=temp_translated_value.replace(r'$U$S%d$'%(indice_https),url)
                                  indice_https=indice_https+1

                          if list_urls_http:
                              for url in list_urls_http:

                                  temp_translated_value=temp_translated_value.replace(r'$U$P%d$'%(indice_http),url)
                                  indice_http=indice_http+1

                          if list_urls_ftp:
                              for url in list_urls_ftp:

                                  temp_translated_value=temp_translated_value.replace(r'$U$F%d$'%(indice_ftp),url)
                                  indice_ftp=indice_ftp+1

                          feature.setAttribute('%s%s'%(attr,out_suffix),temp_translated_value)

              #List Attributes
              list_atttranslation=feature.getAttribute('_attrlist2translate')

              if list_atttranslation:
                  for attr in list_atttranslation.split(','):
                      temp_list_value=feature.getAttribute(attr)
                      if (temp_list_value):
                          list_name=attr.split('{}.')[0]
                          list_attr=attr.split('{}.')[1]
                          list_len=len(temp_list_value)

                          for k in range(list_len):
                              temp_attr_name='%s{%d}.%s'%(list_name,k,list_attr)
                              temp_translated_value=feature.getAttribute('%s%s'%(temp_attr_name,out_suffix))

                              if temp_translated_value:
                                  indice_https=0
                                  indice_http=0
                                  indice_ftp=0



                                  #Catching pre identified URL
                                  list_urls_https=[]
                                  list_urls_http=[]
                                  list_urls_ftp=[]

                                  list_urls_https=feature.getAttribute('_aws_translate_temp_urls_https_%s{}'%(temp_attr_name))
                                  list_urls_http=feature.getAttribute('_aws_translate_temp_urls_http_%s{}'%(temp_attr_name))
                                  list_urls_ftp=feature.getAttribute('_aws_translate_temp_urls_ftp_%s{}'%(temp_attr_name))


                                  if list_urls_https:
                                      for url in list_urls_https:
                                          temp_translated_value=temp_translated_value.replace(r'$U$S%d$'%(indice_https),url)
                                          indice_https=indice_https+1

                                  if list_urls_http:
                                      for url in list_urls_http:

                                          temp_translated_value=temp_translated_value.replace(r'$U$P%d$'%(indice_http),url)
                                          indice_http=indice_http+1

                                  if list_urls_ftp:
                                      for url in list_urls_ftp:

                                          temp_translated_value=temp_translated_value.replace(r'$U$F%d$'%(indice_ftp),url)
                                          indice_ftp=indice_ftp+1

                                  feature.setAttribute('%s%s'%(temp_attr_name,out_suffix),temp_translated_value)




              feature.setAttribute('_translation_problem',0)
          except:
              feature.setAttribute('_translation_problem',1)
    PYTHONSYMBOL = processFeature
    -> Tester_3
Tester_3
    BOOL_OP = OR
    TEST_CLAUSE = TEST @Value(_translation_problem) = 0
    TEST_MODE = TEST
    PASSED -> TRANSLATED (output)
    FAILED -> Tester
TRANSLATED (output)
Tester
    BOOL_OP = OR
    TEST_CLAUSE = TEST @Value(_iteration) = 10
    TEST_MODE = TEST
    PASSED -> FAILED (output)
    FAILED -> AttributeCreator
FAILED (output)
AttributeCreator
    ATTR_TABLE = SET_TO _iteration = @Evaluate(@Value(_iteration)+1)
    -> PythonCaller_2
PythonCaller_2
    PYTHONSOURCE:
      import fme
      import fmeobjects
      import time

      # Template Function interface:
      # When using this function, make sure its name is set as the value of
      # the 'Class or Function to Process Features' transformer parameter
      def processFeature(feature):
          print('Attente de 60 secondes pour essai no %d'%(feature.getAttribute('_iteration')))
          time.sleep(60)
    PYTHONSYMBOL = processFeature
    -> PythonCaller_Input (output)
PythonCaller_Input (output)
