FME workspace DFO_OSDP_API_new_file_R8.fmw

Parameters:
- SourceDataset_XLSXR = $(FME_SHAREDRESOURCE_DATA)\DDR\Conditioning_Data\DFO_OSDP_API\CC_OSDP_DFO_order.xlsx   # Mapping Excel File
- Out_Xlsx_Directory = $(FME_SHAREDRESOURCE_DATA)\DDR\Conditioning_Data\DFO_OSDP_API   # Fichier_erreurs_mapping(folder)
- ENV = PROD
- ACTIVATE_TRANSLATION = yes

Readers:
- XLSXR_1: XLSXR from $(SourceDataset_XLSXR)

Writers:
- XLSXW_1: XLSXW to $(Out_Xlsx_Directory)

Creator
    GEOMTYPE = Geometry Object
    NUM = 1
    CREATED -> HTTPCaller
Create_message_4: Create message
    EXECUTION_TRACE = +Create_message_4
    EnMessage = API malfunction
    FrMessage = API non fonctionnel
    MessageType = ADMIN
    Severity = FATAL
    Communication_Thread -> Create_message_3 [Communication_Thread]
Create_message_3: Create message
    EXECUTION_TRACE = +Create_message_3
    EnMessage = Problem with the number of records... API malfunction
    FrMessage = problème au niveau du nombre d'éléments...API non fonctionnel
    MessageType = ADMIN
    Severity = FATAL
    Communication_Thread -> Create_message_1 [Communication_Thread]
AttributeExposer_8
    ATTR_LIST = P_A_L_24_ID_SubjTop,P_P_L_08_ID_SubjTop,Proponent(Organization),"Promoteur (Organisme)","Auth Date/Date de auth","Effective Date/Date en vigueur","Expiry Date/Date d'expire","Longitude / Longitude","Latitude / Latitude",P_A_L_03_ID,P_A_L_24_ID,P_A_L_24_ID_SubjTop,P_A_L_24_ID_Work,P_C_L_03_ID,P_P_L_03_ID,P_P_L_01_ID,P_P_L_08_ID,P_P_L_08_ID_Main,P_P_L_08_ID_SubjTop,Title_en,Title_fr,"Watershed/Nom du Bassin",PlaceName,ID,"Authorization Type","Type de authorization",Description,Title
    -> AttributeRemover_2
ListElementCounter_2
    CNT_ATTR = publisher_element_count
    LIST_NAME = publisher_en_list{}
    -> Tester_4
Tester_4
    BOOL_OP = OR
    COMPOSITE_TEST = 1
    TEST_CLAUSE = TEST @Value(publisher_element_count) > 10
    TEST_MODE = TEST
    PASSED -> Terminator
    FAILED -> AttributeCreator_26
AttributeCreator_26
    ATTR_TABLE:
      SET_TO Publisher_citation_en = FME_CONDITIONAL:DEFAULT_VALUE'_FME_NO_OP_'BOOL_OP;OR;COMPOSITE_TEST;1;TEST @Value(publisher_element_count) = 1'@Value(Publisher (EN))'BOOL_OP;OR;COMPOSITE_TEST;1;TEST @Value(publisher_element_count) = 2'@Value(publisher_en_list{0}.value) & @Value(publisher_en_list{1}.value)'BOOL_OP;OR;COMPOSITE_TEST;1;TEST @Value(publisher_element_count) = 3'@Value(publisher_en_list{0}.value), @Value(publisher_en_list{1}.value) & @Value(publisher_en_list{2}.value)'BOOL_OP;OR;COMPOSITE_TEST;1;TEST @Value(publisher_element_count) = 4'@Value(publisher_en_list{0}.value), @Value(publisher_en_list{1}.value), @Value(publisher_en_list{2}.value) & @Value(publisher_en_list{3}.value)'BOOL_OP;OR;COMPOSITE_TEST;1;TEST @Value(publisher_element_count) = 5'@Value(publisher_en_list{0}.value), @Value(publisher_en_list{1}.value), @Value(publisher_en_list{2}.value), @Value(publisher_en_list{3}.value) & @Value(publisher_en_list{4}.value)'BOOL_OP;OR;COMPOSITE_TEST;1;TEST @Value(publisher_element_count) = 6'@Value(publisher_en_list{0}.value), @Value(publisher_en_list{1}.value), @Value(publisher_en_list{2}.value), @Value(publisher_en_list{3}.value), @Value(publisher_en_list{4}.value) & @Value(publisher_en_list{5}.value)'BOOL_OP;OR;COMPOSITE_TEST;1;TEST @Value(publisher_element_count) = 7'@Value(publisher_en_list{0}.value), @Value(publisher_en_list{1}.value), @Value(publisher_en_list{2}.value), @Value(publisher_en_list{3}.value), @Value(publisher_en_list{4}.value), @Value(publisher_en_list{5}.value) & @Value(publisher_en_list{6}.value)'BOOL_OP;OR;COMPOSITE_TEST;1;TEST @Value(publisher_element_count) = 8'@Value(publisher_en_list{0}.value), @Value(publisher_en_list{1}.value), @Value(publisher_en_list{2}.value), @Value(publisher_en_list{3}.value), @Value(publisher_en_list{4}.value), @Value(publisher_en_list{5}.value), @Value(publisher_en_list{6}.value) & @Value(publisher_en_list{7}.value)'BOOL_OP;OR;COMPOSITE_TEST;1;TEST @Value(publisher_element_count) = 9'@Value(publisher_en_list{0}.value), @Value(publisher_en_list{1}.value), @Value(publisher_en_list{2}.value), @Value(publisher_en_list{3}.value), @Value(publisher_en_list{4}.value), @Value(publisher_en_list{5}.value), @Value(publisher_en_list{6}.value), @Value(publisher_en_list{7}.value) & @Value(publisher_en_list{8}.value)'BOOL_OP;OR;COMPOSITE_TEST;1;TEST @Value(publisher_element_count) = 10'@Value(publisher_en_list{0}.value), @Value(publisher_en_list{1}.value), @Value(publisher_en_list{2}.value), @Value(publisher_en_list{3}.value), @Value(publisher_en_list{4}.value), @Value(publisher_en_list{5}.value), @Value(publisher_en_list{6}.value), @Value(publisher_en_list{7}.value), @Value(publisher_en_list{8}.value) & @Value(publisher_en_list{9}.value)'FME_NUM_CONDITIONS11___
      SET_TO Publisher_citation_fr = FME_CONDITIONAL:DEFAULT_VALUE'_FME_NO_OP_'BOOL_OP;OR;COMPOSITE_TEST;1;TEST @Value(publisher_element_count) = 1'@Value(Publisher (FR))'BOOL_OP;OR;COMPOSITE_TEST;1;TEST @Value(publisher_element_count) = 2'@Value(publisher_fr_list{0}.value) et @Value(publisher_fr_list{1}.value)'BOOL_OP;OR;COMPOSITE_TEST;1;TEST @Value(publisher_element_count) = 3'@Value(publisher_fr_list{0}.value), @Value(publisher_fr_list{1}.value) et @Value(publisher_fr_list{2}.value)'BOOL_OP;OR;COMPOSITE_TEST;1;TEST @Value(publisher_element_count) = 4'@Value(publisher_fr_list{0}.value), @Value(publisher_fr_list{1}.value), @Value(publisher_fr_list{2}.value) et @Value(publisher_fr_list{3}.value)'BOOL_OP;OR;COMPOSITE_TEST;1;TEST @Value(publisher_element_count) = 5'@Value(publisher_fr_list{0}.value), @Value(publisher_fr_list{1}.value), @Value(publisher_fr_list{2}.value), @Value(publisher_fr_list{3}.value) et @Value(publisher_fr_list{4}.value)'BOOL_OP;OR;COMPOSITE_TEST;1;TEST @Value(publisher_element_count) = 6'@Value(publisher_fr_list{0}.value), @Value(publisher_fr_list{1}.value), @Value(publisher_fr_list{2}.value), @Value(publisher_fr_list{3}.value), @Value(publisher_fr_list{4}.value) et @Value(publisher_fr_list{5}.value)'BOOL_OP;OR;COMPOSITE_TEST;1;TEST @Value(publisher_element_count) = 7'@Value(publisher_fr_list{0}.value), @Value(publisher_fr_list{1}.value), @Value(publisher_fr_list{2}.value), @Value(publisher_fr_list{3}.value), @Value(publisher_fr_list{4}.value), @Value(publisher_fr_list{5}.value) et @Value(publisher_fr_list{6}.value)'BOOL_OP;OR;COMPOSITE_TEST;1;TEST @Value(publisher_element_count) = 8'@Value(publisher_fr_list{0}.value), @Value(publisher_fr_list{1}.value), @Value(publisher_fr_list{2}.value), @Value(publisher_fr_list{3}.value), @Value(publisher_fr_list{4}.value), @Value(publisher_fr_list{5}.value), @Value(publisher_fr_list{6}.value) et @Value(publisher_fr_list{7}.value)'BOOL_OP;OR;COMPOSITE_TEST;1;TEST @Value(publisher_element_count) = 9'@Value(publisher_fr_list{0}.value), @Value(publisher_fr_list{1}.value), @Value(publisher_fr_list{2}.value), @Value(publisher_fr_list{3}.value), @Value(publisher_fr_list{4}.value), @Value(publisher_fr_list{5}.value), @Value(publisher_fr_list{6}.value), @Value(publisher_fr_list{7}.value) et @Value(publisher_fr_list{8}.value)'BOOL_OP;OR;COMPOSITE_TEST;1;TEST @Value(publisher_element_count) = 10'@Value(publisher_fr_list{0}.value), @Value(publisher_fr_list{1}.value), @Value(publisher_fr_list{2}.value), @Value(publisher_fr_list{3}.value), @Value(publisher_fr_list{4}.value), @Value(publisher_fr_list{5}.value), @Value(publisher_fr_list{6}.value), @Value(publisher_fr_list{7}.value), @Value(publisher_fr_list{8}.value) et @Value(publisher_fr_list{9}.value)'FME_NUM_CONDITIONS11___
    -> AttributeKeeper_3
AttributeKeeper_3
    CREATE_BULK_MODE_FEATURES = NO
    KEEP_ATTRS = Action,Content Category,Contributor Org,Contributor System,Coverage.Country,Coverage.Geometry,Coverage.ProvinceCd,Coverage.Region,Creator (EN),Creator (FR),Date.End,Date.LastUpdate,Date.Published,Date.Start,Description,External.DatasetCategory,External.ProjectCategory,Identifier.Artifact,Identifier.Artifact (DOI),Identifier.Bundle,Identifier.Child,Keywords (EN),Keywords (FR),PublishedFor,Publisher (EN),Publisher (FR),Record Type,RecordKeeper.LastUserToModify,RecordKeeper.Organization,RecordKeeper.System,Resource Total,Resource.Format[1],Resource.Format[2],Resource.Format[3],Resource.Format[4],Resource.Language[1],Resource.Language[2],Resource.Language[3],Resource.Language[4],Resource.Name (EN)[1],Resource.Name (EN)[2],Resource.Name (EN)[3],Resource.Name (EN)[4],Resource.Name (FR)[1],Resource.Name (FR)[2],Resource.Name (FR)[3],Resource.Name (FR)[4],Resource.ServiceProtocol[1],Resource.ServiceProtocol[2],Resource.ServiceProtocol[3],Resource.ServiceProtocol[4],Resource.Type[1],Resource.Type[2],Resource.Type[3],Resource.Type[4],Resource.URL (EN)[1],Resource.URL (EN)[2],Resource.URL (EN)[3],Resource.URL (EN)[4],Resource.URL (FR)[1],Resource.URL (FR)[2],Resource.URL (FR)[3],Resource.URL (FR)[4],Rights.Disposition,Rights.License,Subject Area,Subject Topic,Title,P_P_L_01_ID,PlaceName,Authorization Type,Type de authorization,UpdateFrequency,Publisher_citation_en,Publisher_citation_fr
    -> Tester
FeatureHolder
    -> DuplicateFilter
DuplicateFilter
    INPUT_ORDERED_CHOICE = No
    KEYATTR = Identifier.Artifact
    UNIQUE -> AttributeKeeper_2
    DUPLICATE -> Create_message_2
AttributeKeeper_2
    CREATE_BULK_MODE_FEATURES = NO
    KEEP_ATTRS = Action,Content Category,Contributor Org,Contributor System,Coverage.Country,Coverage.PlaceName (EN),Coverage.PlaceName (FR),Coverage.ProvinceCd,Coverage.Region,Date.End,Date.LastUpdate,Date.Published,Date.Start,Description (EN),Description (FR),External.DatasetCategory,External.ProjectCategory,Identifier.Artifact,Identifier.Artifact (DOI),Identifier.Bundle,Identifier.Child,Keywords (EN),Keywords (FR),PublishedFor,Publisher (EN),Publisher (FR),Record Type,RecordKeeper.LastUserToModify,RecordKeeper.Organization,RecordKeeper.System,Resource Total,Resource.Format[1],Resource.Format[2],Resource.Language[1],Resource.Language[2],Resource.Name (EN)[1],Resource.Name (EN)[2],Resource.Name (FR)[1],Resource.Name (FR)[2],Resource.ServiceProtocol[1],Resource.ServiceProtocol[2],Resource.Type[1],Resource.Type[2],Resource.URL (EN)[1],Resource.URL (EN)[2],Resource.URL (FR)[1],Resource.URL (FR)[2],Rights.Disposition,Rights.License,Subject Area,Subject Topic,Title (EN),Title (FR),Creator (EN),Creator (FR),Coverage.Geometry,UpdateFrequency,Citation Total,Citation.Format[1],Citation.Value (EN)[1],Citation.Value (FR)[1]
    -> VariableRetriever_2
VariableRetriever_2
    SCOPE = Global
    VALUE_ATTR = _dateStamp
    VARNAME = Var_date
    -> AttributeCreator_9
Terminator
    MESSAGE:
      Too many organization for the publisher citation
      Translation Terminated
Create_message_1: Create message
    EXECUTION_TRACE = +Create_message_1
    EnMessage = @DateTimeFormat(@round(@DateTimeNow(),0), %Y-%m-%d %H:%M:%S) -> Codelist needs to be updated (si file Action_to_do)
    FrMessage = @DateTimeFormat(@round(@DateTimeNow(),0), %Y-%m-%d %H:%M:%S) -> Certains codelist demande des ajustements (Voir fichier Action to do)
    MessageType = ADMIN
    Severity = WARNING
    Communication_Thread -> Create_message_2 [Communication_Thread]
Create_message_2: Create message
    EXECUTION_TRACE = +Create_message_3
    EnMessage = @DateTimeFormat(@round(@DateTimeNow(),0), %Y-%m-%d %H:%M:%S) -> Record rejected when validating the update/delete
    FrMessage = @DateTimeFormat(@round(@DateTimeNow(),0), %Y-%m-%d %H:%M:%S) -> Enregistrement rejeté lors de la validation des ID effacés
    MessageType = ADMIN
    Severity = WARNING
    Communication_Thread -> Output [Communication]

Bookmark: Connexion à l'API pour obtenir les enregistrements et exposer les attributs
HTTPCaller
    CONNECTION_TIMEOUT_LENGTH = 60
    CUSTOM_HEADERS = Accept;application/json
    FOLLOW_REDIRECTS = FOLLOW_WITH_GET
    HTTP_METHOD = GET
    REDIRECT_AUTH = ORIGINAL_DOMAIN_ONLY
    SAVE_FILE = Attribute
    TARGET_ATTR = _response_body
    TARGET_ATTR_ENCODING = utf-8
    TARGET_URL = https://gisp.dfo-mpo.gc.ca/arcgis/rest/services/FGP/PATH/MapServer/0/query?where=1%3D1&outFields=*&returnGeometry=true&f=pjson
    TRANSFER_TIMEOUT_LENGTH = 90
    USE_COOKIES = No
    VERIFY_SSL_CERTIFICATES = Yes
    -> JSONFlattener_2
    <REJECTED> -> Create_message_4
    <REJECTED> -> Create_message_4 [Communication_Thread]
    <REJECTED> -> Terminator_3
JSONFlattener_2
    ERROR_LIST_ATTR = _json_error
    JSON_DOCUMENT = @Value(_response_body)
    READ_FROM_FILE = NO
    RECURSIVE = Yes
    -> AttributeRemover
AttributeRemover
    REMOVE_ATTRS = _creation_instance,_response_body
    -> AttributeExposer
AttributeExposer
    ATTR_LIST = features{}
    -> ListElementCounter
ListElementCounter
    CNT_ATTR = _element_count
    LIST_NAME = features{}
    -> Tester_2
Tester_2
    BOOL_OP = OR
    COMPOSITE_TEST = 1
    TEST_CLAUSE = TEST @Value(_element_count) > 100
    TEST_MODE = TEST
    PASSED -> ListExploder
    FAILED -> Terminator_2
    FAILED -> Create_message_3
ListExploder
    ATTR_ACCUM_MODE = Merge List Attributes
    ATTR_CONFLICT_RES = Use List Attribute Values
    INDEX_ATTR = _element_index
    LIST_ATTR = features{}
    ELEMENTS -> AttributeExposer_2
AttributeExposer_2
    ATTR_LIST = attributes.ACTION_DT,attributes.AUTHORIZATION_EN,attributes.AUTHORIZATION_FR,attributes.DECIMAL_LATITUDE,attributes.DECIMAL_LONGITUDE,attributes.DESCRIPTION,attributes.EFFECT_DT,attributes.EXPIRY_DT,attributes.EXPIRY_EXT_DT,attributes.FED_OGD_ID_LIST,attributes.FEDERAL_EN,attributes.FEDERAL_FR,attributes.ID,attributes.LOCATION_DESCRIPT,attributes.MAIN_CATEGORY_EN,attributes.MAIN_CATEGORY_FR,attributes.P_A_A_01_ID,attributes.P_A_L_03_ID,attributes.P_A_L_24_ID,attributes.P_B_A_01_ID,attributes.P_C_L_03_ID,attributes.P_P_L_01_ID,attributes.P_P_L_03_ID,attributes.P_P_L_08_ID,attributes.P_P_L_11_ID,attributes.P_U_A_01_ID,attributes.PRIMARY_WORK_EN,attributes.PRIMARY_WORK_FR,attributes.PRO_P_I_A_01_ID,attributes.PROGRAM_ACTIVITY_EN,attributes.PROGRAM_ACTIVITY_FR,attributes.PROJECT_TYPE_EN,attributes.PROJECT_TYPE_FR,attributes.PROJECT_TYPE_ID,attributes.PROPONENT_EN,attributes.PROPONENT_FR,attributes.PROV_OGD_ID_LIST,attributes.PROVINCE_EN,attributes.PROVINCE_FR,attributes.PROVINCIAL_EN,attributes.PROVINCIAL_FR,attributes.REF_FILE_NO,attributes.REGION_EN,attributes.REGION_FR,attributes.REGISTRY_CONTACT,attributes.REGISTRY_IND,attributes.STATUS_EN,attributes.STATUS_FR,attributes.TITLE,attributes.URL_ADDRESS_EN,attributes.URL_ADDRESS_FR,attributes.WATERSHED_NAME
    -> AttributeRenamer
Terminator_2
    MESSAGE:
      Problème avec l'API... Nombre d'enregistrement problématique

      API data problem... Lack of records

      Translation Terminated
Terminator_3
    MESSAGE:
      Problème avec l'API

      API problem...

      Translation Terminated

Bookmark: attribut API vs OSDP
AttributeRenamer
    ATTR_TABLE:
      RENAME_SET_DEFAULT attributes.P_P_L_01_ID > P_P_L_01_ID
      RENAME_SET_DEFAULT attributes.TITLE > Title
      RENAME_SET_DEFAULT attributes.P_A_A_01_ID > P_A_A_01_ID
      RENAME_SET_DEFAULT attributes.PROVINCE_EN > Province
      RENAME_SET_DEFAULT attributes.PROVINCE_FR > Territoire
      RENAME_SET_DEFAULT attributes.P_B_A_01_ID > P_B_A_01_ID
      RENAME_SET_DEFAULT attributes.DECIMAL_LATITUDE > Latitude / Latitude
      RENAME_SET_DEFAULT attributes.DECIMAL_LONGITUDE > Longitude / Longitude
      RENAME_SET_DEFAULT attributes.WATERSHED_NAME > Watershed/Nom du Bassin
      RENAME_SET_DEFAULT attributes.P_A_L_24_ID > P_A_L_24_ID
      RENAME_SET_DEFAULT attributes.PRIMARY_WORK_EN > Primary Work
      RENAME_SET_DEFAULT attributes.PRIMARY_WORK_FR > Ouvrage principal
      RENAME_SET_DEFAULT attributes.P_P_L_08_ID > P_P_L_08_ID
      RENAME_SET_DEFAULT attributes.MAIN_CATEGORY_EN > Main Category
      RENAME_SET_DEFAULT attributes.MAIN_CATEGORY_FR > Catégorie principale
      RENAME_SET_DEFAULT attributes.P_A_L_03_ID > P_A_L_03_ID
      RENAME_SET_DEFAULT attributes.STATUS_EN > Status
      RENAME_SET_DEFAULT attributes.STATUS_FR > État
      RENAME_SET_DEFAULT attributes.PRO_P_I_A_01_ID > PRO_P_I_A_01_ID
      RENAME_SET_DEFAULT attributes.PROPONENT_EN > Proponent(Organization)
      RENAME_SET_DEFAULT attributes.PROPONENT_FR > Promoteur (Organisme)
      RENAME_SET_DEFAULT attributes.REGISTRY_CONTACT > Registry Contact du Registre
      RENAME_SET_DEFAULT attributes.URL_ADDRESS_EN > Contact URL
      RENAME_SET_DEFAULT attributes.URL_ADDRESS_FR > URL de contact
      RENAME_SET_DEFAULT attributes.ACTION_DT > Auth Date/Date de auth
      RENAME_SET_DEFAULT attributes.EFFECT_DT > Effective Date/Date en vigueur
      RENAME_SET_DEFAULT attributes.EXPIRY_DT > Expiry Date/Date d'expire
      RENAME_SET_DEFAULT attributes.EXPIRY_EXT_DT > Expiry Date Other_Date d'exp. Autre
      RENAME_SET_DEFAULT attributes.P_C_L_03_ID > P_C_L_03_ID
      RENAME_SET_DEFAULT attributes.AUTHORIZATION_EN > Authorization Type
      RENAME_SET_DEFAULT attributes.AUTHORIZATION_FR > Type de authorization
      RENAME_SET_DEFAULT attributes.REGISTRY_IND > REGISTRY_IND
      RENAME_SET_DEFAULT attributes.P_U_A_01_ID > REGISTRY_ID
      RENAME_SET_DEFAULT attributes.DESCRIPTION > Description
      RENAME_SET_DEFAULT attributes.LOCATION_DESCRIPT > PlaceName
      RENAME_SET_DEFAULT attributes.FED_OGD_ID_LIST > FED_OGD_ID_LIST
      RENAME_SET_DEFAULT attributes.FEDERAL_EN > FEDERAL_EN
      RENAME_SET_DEFAULT attributes.FEDERAL_FR > FEDERAL_FR
      RENAME_SET_DEFAULT attributes.PROV_OGD_ID_LIST > PROV_OGD_ID_LIST
      RENAME_SET_DEFAULT attributes.PROVINCIAL_EN > PROVINCIAL_EN
      RENAME_SET_DEFAULT attributes.PROVINCIAL_FR > PROVINCIAL_FR
      RENAME_SET_DEFAULT attributes.P_P_L_11_ID > P_P_L_11_ID
      RENAME_SET_DEFAULT attributes.PROGRAM_ACTIVITY_EN > Program Activity
      RENAME_SET_DEFAULT attributes.PROGRAM_ACTIVITY_FR > Activités du programme
      RENAME_SET_DEFAULT attributes.P_P_L_03_ID > P_P_L_03_ID
      RENAME_SET_DEFAULT attributes.REGION_FR > RÉGION
      RENAME_SET_DEFAULT attributes.REGION_EN > REGION
      RENAME_SET_DEFAULT attributes.ID > ID
      RENAME_SET_DEFAULT attributes.PROJECT_TYPE_ID > PROJECT_TYPE_ID
      RENAME_SET_DEFAULT attributes.PROJECT_TYPE_EN > PROJECT_TYPE_EN
      RENAME_SET_DEFAULT attributes.PROJECT_TYPE_FR > PROJECT_TYPE_FR
    -> DateTimeStamper

Bookmark: création d'une variable datetime pour les attributs et les noms de fichiers
DateTimeStamper
    DATETIME_ATTR = _date
    INCLUDE_OFFSET = NO
    STAMP_TYPE = datetime
    TIMEZONE = utc
    -> SubstringExtractor_4
Note: Enlever fractions de secondes
SubstringExtractor_4
    END = 13
    RESULT_ATTR = _datetime
    SRC_STRING = @Value(_date)
    START = 0
    -> VariableSetter
VariableSetter
    SCOPE = Global
    VALUE = @Value(_datetime)
    VARNAME = Var_date
    -> Attribute_splitter_DeLuxe

Bookmark: Séparations des attributs "bar-delimited"
Attribute_splitter_DeLuxe: Attribute splitter DeLuxe
    ATTR_2_SPLIT = FED_OGD_ID_LIST
    DELIMITER = |
    OUT_LIST_ATTR_NAME = value
    OUT_LIST_NAME = fed_ogd_list
    -> Attribute_splitter_DeLuxe_2
Attribute_splitter_DeLuxe_2: Attribute splitter DeLuxe
    ATTR_2_SPLIT = PROV_OGD_ID_LIST
    DELIMITER = |
    OUT_LIST_ATTR_NAME = value
    OUT_LIST_NAME = prov_ogd_list
    -> Attribute_splitter_DeLuxe_3
Attribute_splitter_DeLuxe_3: Attribute splitter DeLuxe
    ATTR_2_SPLIT = FEDERAL_EN
    DELIMITER = |
    OUT_LIST_ATTR_NAME = value
    OUT_LIST_NAME = fed_stakeholders_list
    -> Attribute_splitter_DeLuxe_4
Attribute_splitter_DeLuxe_4: Attribute splitter DeLuxe
    ATTR_2_SPLIT = PROVINCIAL_EN
    DELIMITER = |
    OUT_LIST_ATTR_NAME = value
    OUT_LIST_NAME = prov_stakeholders_list
    -> Attribute_splitter_DeLuxe_5
Attribute_splitter_DeLuxe_5: Attribute splitter DeLuxe
    ATTR_2_SPLIT = FEDERAL_FR
    DELIMITER = |
    OUT_LIST_ATTR_NAME = value
    OUT_LIST_NAME = fed_parties_prenantes_list
    -> Attribute_splitter_DeLuxe_6
Attribute_splitter_DeLuxe_6: Attribute splitter DeLuxe
    ATTR_2_SPLIT = PROVINCIAL_FR
    DELIMITER = |
    OUT_LIST_ATTR_NAME = value
    OUT_LIST_NAME = prov_parties_prenantes_list
    -> AttributeCreator_10

Bookmark: Mapping des codes DFO avec les valeurs désirée OSDP (codelist et valeur présent dans le fichier excel CC_OSDP_DFO - Valeurs à modifier si message à ce sujet)
AttributeCreator_10
    ATTR_TABLE:
      SET_TO P_A_L_24_ID_SubjTop = @Value(P_A_L_24_ID)
      SET_TO P_A_L_24_ID_Work = @Value(P_A_L_24_ID)
      SET_TO P_P_L_08_ID_Main = @Value(P_P_L_08_ID)
      SET_TO P_P_L_08_ID_SubjTop = @Value(P_P_L_08_ID)
    -> NullAttributeMapper
NullAttributeMapper
    ATTRCHOICE = All Attributes
    NEW_VALUE = no_value
    NULL_TREATMENT = New Value
    REG_EXP = none
    SOURCE_ATTR_VAL = Null Empty "Missing (Selected Attributes Only)"
    -> METADATA_VALUE_MAPPER_14 [DATA_INPUT]
Fed_Stake_SubjectTopic (reader XLSXR_1)
    attributes: original_value number(3,0), real_value_english char(37), C string
    -> METADATA_VALUE_MAPPER_14 [LOOKUP_TABLE_INPUT]
MainCategorySubjectTop (reader XLSXR_1)
    attributes: original_value number(3,0), real_value_english char(55), C string
    -> METADATA_VALUE_MAPPER_13 [LOOKUP_TABLE_INPUT]
Prov_Stake_SubjectTopic (reader XLSXR_1)
    attributes: original_value number(3,0), real_value_english char(67), C string
    -> METADATA_VALUE_MAPPER_15 [LOOKUP_TABLE_INPUT]
RegionSubjectTopic (reader XLSXR_1)
    attributes: original_value number(2,0), real_value_english char(26)
    -> METADATA_VALUE_MAPPER_6 [LOOKUP_TABLE_INPUT]
Creator_2
    GEOMTYPE = Geometry Object
    NUM = 1
    CREATED -> AttributeCreator_2
    CREATED -> AttributeCreator
AttributeCreator
    ATTR_TABLE:
      SET_TO original_value = no_value
      SET_TO real_value_english = no_value
      SET_TO real_value_french = no_value
    -> Junction
AttributeCreator_2
    ATTR_TABLE:
      SET_TO original_value = none
      SET_TO real_value_english = no_value
      SET_TO real_value_french = no_value
    -> Junction
Junction
    -> METADATA_VALUE_MAPPER [LOOKUP_TABLE_INPUT]
    -> METADATA_VALUE_MAPPER_6 [LOOKUP_TABLE_INPUT]
    -> METADATA_VALUE_MAPPER_5 [LOOKUP_TABLE_INPUT]
    -> METADATA_VALUE_MAPPER_15 [LOOKUP_TABLE_INPUT]
    -> METADATA_VALUE_MAPPER_12 [LOOKUP_TABLE_INPUT]
    -> METADATA_VALUE_MAPPER_14 [LOOKUP_TABLE_INPUT]
    -> METADATA_VALUE_MAPPER_17 [LOOKUP_TABLE_INPUT]
    -> METADATA_VALUE_MAPPER_16 [LOOKUP_TABLE_INPUT]
    -> METADATA_VALUE_MAPPER_13 [LOOKUP_TABLE_INPUT]
METADATA_VALUE_MAPPER_14
    ATT_TO_MAP = fed_ogd_list{}.value
    CODE_REFRESH = NO
    ENGLISH_REFRESH = YES
    ERROR_NOT_MAPPED = YES
    FRENCH_REFRESH = NO
    -> METADATA_VALUE_MAPPER_15 [DATA_INPUT]
METADATA_VALUE_MAPPER_15
    ATT_TO_MAP = prov_ogd_list{}.value
    CODE_REFRESH = NO
    ENGLISH_REFRESH = YES
    ERROR_NOT_MAPPED = YES
    FRENCH_REFRESH = NO
    -> METADATA_VALUE_MAPPER_16 [DATA_INPUT]
PrimaryWorkDevAct (reader XLSXR_1)
    attributes: original_value number(3,0), real_value_english char(82), C string, D string, E string
    -> METADATA_VALUE_MAPPER_16 [LOOKUP_TABLE_INPUT]
METADATA_VALUE_MAPPER_16
    ATT_TO_MAP = P_A_L_24_ID_Work
    CODE_REFRESH = NO
    ENGLISH_REFRESH = YES
    ERROR_NOT_MAPPED = YES
    FRENCH_REFRESH = NO
    -> METADATA_VALUE_MAPPER [DATA_INPUT]
AuthorizationTypeSubjectTop (reader XLSXR_1)
    attributes: original_value number(4,0), real_value_english char(12), C string
    -> METADATA_VALUE_MAPPER_5 [LOOKUP_TABLE_INPUT]
PrimaryWorkSubjectTop (reader XLSXR_1)
    attributes: original_value number(3,0), real_value_english char(46), C string, D string
    -> METADATA_VALUE_MAPPER [LOOKUP_TABLE_INPUT]
METADATA_VALUE_MAPPER
    ATT_TO_MAP = P_A_L_24_ID_SubjTop
    CODE_REFRESH = NO
    ENGLISH_REFRESH = YES
    ERROR_NOT_MAPPED = YES
    FRENCH_REFRESH = NO
    -> METADATA_VALUE_MAPPER_12 [DATA_INPUT]
Province (reader XLSXR_1)
    attributes: original_value number(3,0), real_value_english char(3)
    -> METADATA_VALUE_MAPPER_17 [LOOKUP_TABLE_INPUT]
MainCategoryDevAct (reader XLSXR_1)
    attributes: original_value number(3,0), real_value_english char(36), C string, D string, E string
    -> METADATA_VALUE_MAPPER_12 [LOOKUP_TABLE_INPUT]
METADATA_VALUE_MAPPER_12
    ATT_TO_MAP = P_P_L_08_ID_Main
    CODE_REFRESH = NO
    ENGLISH_REFRESH = YES
    ERROR_NOT_MAPPED = YES
    FRENCH_REFRESH = NO
    -> METADATA_VALUE_MAPPER_13 [DATA_INPUT]
METADATA_VALUE_MAPPER_13
    ATT_TO_MAP = P_P_L_08_ID_SubjTop
    CODE_REFRESH = NO
    ENGLISH_REFRESH = YES
    ERROR_NOT_MAPPED = YES
    FRENCH_REFRESH = NO
    -> METADATA_VALUE_MAPPER_6 [DATA_INPUT]
METADATA_VALUE_MAPPER_6
    ATT_TO_MAP = P_P_L_03_ID
    CODE_REFRESH = NO
    ENGLISH_REFRESH = YES
    ERROR_NOT_MAPPED = YES
    FRENCH_REFRESH = NO
    -> METADATA_VALUE_MAPPER_5 [DATA_INPUT]
METADATA_VALUE_MAPPER_5
    ATT_TO_MAP = P_C_L_03_ID
    CODE_REFRESH = NO
    ENGLISH_REFRESH = YES
    ERROR_NOT_MAPPED = YES
    FRENCH_REFRESH = NO
    -> METADATA_VALUE_MAPPER_17 [DATA_INPUT]
METADATA_VALUE_MAPPER_17
    ATT_TO_MAP = P_P_L_01_ID
    CODE_REFRESH = NO
    ENGLISH_REFRESH = YES
    ERROR_NOT_MAPPED = YES
    FRENCH_REFRESH = NO
    -> METADATA_VALUE_MAPPER_ERROR_MANAGER

Bookmark: validation du mapping et communication des erreurs présentes
METADATA_VALUE_MAPPER_ERROR_MANAGER
    ERROR_OUTPUT -> VariableRetriever
    ERROR_OUTPUT -> Create_message_1
    DATA_OUTPUT -> AttributeExposer_8
VariableRetriever
    SCOPE = Global
    VALUE_ATTR = _dateStamp
    VARNAME = Var_date
    -> DFO_mapping_error (writer XLSXW_1)
DFO_mapping_error (writer XLSXW_1)
    attributes: error string(200), id string(200), _element_index string(200), _dateStamp string(200)

Bookmark: Ménage des attributs non utilisés
AttributeRemover_2
    -> PythonCaller

Bookmark: création des attributs selon les valeurs et la structure demandées (concaténation de listes et création d'attributs et gestion des valeurs "no_value"
PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              attr_name=['P_A_L_24_ID','P_A_L_24_ID_SubjTop','P_P_L_08_ID','P_P_L_08_ID_SubjTop','P_P_L_03_ID','P_C_L_03_ID','P_P_L_01_ID','P_A_L_24_ID_Work','P_A_L_24_ID_SubjTop','P_P_L_08_ID_SubjTop','P_P_L_08_ID_Main','Federal Stakeholders','Provincial Stakeholders','Les parties prenantes prov','Les parties prenantes fed','Proponent(Organization)','Promoteur (Organisme)','PlaceName','Watershed/Nom du Bassin']
              attr_list=[r'fed_ogd_list{}.value',r'prov_ogd_list{}.value',r'prov_stakeholders_list{}.value',r'fed_stakeholders_list{}.value',r'prov_parties_prenantes_list{}.value',r'fed_parties_prenantes_list{}.value']


              for attr in attr_name:
                  val_en=feature.getAttribute(attr)
                  val_fr=feature.getAttribute('%s_fr'%(attr))
                  if val_en=='no_value':
                     feature.setAttribute(attr,'')
                  if val_fr=='no_value':
                     feature.setAttribute('%s_fr'%(attr),'')

              for attr in attr_list:
                  list_temp=feature.getAttribute(attr)
                  attr_temp=attr.split('{}.')
                  for i in range(len(list_temp)):

                      val_en=feature.getAttribute('%s{%i}.%s'%(attr_temp[0],i,attr_temp[1]))
                      val_fr=feature.getAttribute('%s{%i}.%s_fr'%(attr_temp[0],i,attr_temp[1]))
                      if val_en=='no_value':
                          feature.setAttribute('%s{%i}.%s'%(attr_temp[0],i,attr_temp[1]),'')
                      if val_fr=='no_value':
                          feature.setAttribute('%s{%i}.%s_fr'%(attr_temp[0],i,attr_temp[1]),'')

              self.pyoutput(feature)
          def close(self):
              pass
    PYTHONSYMBOL = FeatureProcessor
    -> AttributeExposer_5
AttributeExposer_5
    ATTR_LIST = WatershedName,WatershedName_fr,fed_stakeholders_list{}.value,fed_ogd_list{}.value,prov_ogd_list{}.value,prov_stakeholders_list{}.value,prov_parties_prenantes_list{}.value,fed_parties_prenantes_list{}.value
    -> ListConcatenator
ListConcatenator
    DROP_EMPTY_PARTS = Yes
    LIST_ATTR = fed_ogd_list{}.value
    SEP = "; "
    VAL_ATTR = _concatenated_fed_ogd_list
    -> ListConcatenator_2
ListConcatenator_2
    DROP_EMPTY_PARTS = Yes
    LIST_ATTR = fed_stakeholders_list{}.value
    SEP = "; "
    VAL_ATTR = _concatenated_fed_stakeholders_list
    -> ListConcatenator_3
ListConcatenator_3
    DROP_EMPTY_PARTS = Yes
    LIST_ATTR = prov_ogd_list{}.value
    SEP = "; "
    VAL_ATTR = _concatenated_prov_ogd_list
    -> ListConcatenator_5
ListConcatenator_5
    DROP_EMPTY_PARTS = Yes
    LIST_ATTR = fed_parties_prenantes_list{}.value
    SEP = "; "
    VAL_ATTR = _concatenated_fed_parties_prenantes_list
    -> ListConcatenator_6
ListConcatenator_6
    DROP_EMPTY_PARTS = Yes
    LIST_ATTR = prov_parties_prenantes_list{}.value
    SEP = "; "
    VAL_ATTR = _concatenated_prov_parties_prenantes_list
    -> ListConcatenator_4
ListConcatenator_4
    DROP_EMPTY_PARTS = Yes
    LIST_ATTR = prov_stakeholders_list{}.value
    SEP = "; "
    VAL_ATTR = _concatenated_prov_stakeholders_list
    -> AttributeCreator_3
AttributeCreator_3
    ATTR_TABLE:
      SET_TO watershed = FME_CONDITIONAL:DEFAULT_VALUE'_FME_NO_OP_'BOOL_OP;OR;COMPOSITE_TEST;1;TEST Watershed/Nom du Bassin ATTRIBUTE_HAS_A_VALUE _FME_BLANK_STRING_' Watersheds'FME_NUM_CONDITIONS2___
      SET_TO Main_order = FME_CONDITIONAL:DEFAULT_VALUE'@Value(P_A_L_24_ID_Work); @Value(P_P_L_08_ID_Main);'BOOL_OP;OR;COMPOSITE_TEST;1;CASE_INSENSITIVE_TEST @Value(Promoteur (Organisme)) BEGINS_WITH Ministère des Transports'@Value(P_A_L_24_ID_Work); @Value(P_P_L_08_ID_Main); fTransport Industry'FME_NUM_CONDITIONS2___
    -> AttributeCreator_23
AttributeCreator_23
    ATTR_TABLE = SET_TO Subject Topic = FME_CONDITIONAL:DEFAULT_VALUE'@Value(_concatenated_fed_ogd_list); @Value(_concatenated_prov_ogd_list); @Value(P_A_L_24_ID_SubjTop); @Value(P_P_L_08_ID_SubjTop); @Value(P_P_L_03_ID); @Value(P_C_L_03_ID); @Value(watershed)'BOOL_OP;OR;COMPOSITE_TEST;1;CASE_INSENSITIVE_TEST @Value(Promoteur (Organisme)) BEGINS_WITH Ministère des Transports'@Value(_concatenated_fed_ogd_list); @Value(_concatenated_prov_ogd_list); @Value(P_A_L_24_ID_SubjTop); @Value(P_P_L_08_ID_SubjTop); @Value(P_P_L_03_ID); @Value(P_C_L_03_ID); Transport Industry; @Value(watershed); 'FME_NUM_CONDITIONS2___
    -> Junction_2
Note: DevActTopics
Junction_2
    -> Junction_3
Junction_5
    -> StringReplacer_2
StringReplacer_2
    CASE = NO
    FIND_TEXT = " ;"
    NO_MATCH = _FME_NO_OP_
    REGEXP = NO
    SRC_ATTRS = Main_order
    -> StringReplacer_3
StringReplacer_3
    CASE = NO
    FIND_TEXT = " ;; "
    NO_MATCH = _FME_NO_OP_
    REGEXP = NO
    REPLACE_TEXT = " "
    SRC_ATTRS = Main_order
    -> Attribute_splitter_DeLuxe_12
Attribute_splitter_DeLuxe_12: Attribute splitter DeLuxe
    ATTR_2_SPLIT = Main_order
    DELIMITER = ;
    OUT_LIST_ATTR_NAME = value
    OUT_LIST_NAME = main_list
    -> AttributeExposer_7
AttributeExposer_7
    ATTR_LIST = main_list{}.value
    -> ListSorter
ListSorter
    ORDER = Ascending
    SRC_LIST = main_list{}.value
    TYPE = Alphabetic
    -> AttributeTrimmer_2
AttributeTrimmer_2
    SRC_ATTRS = main_list{0}.value,main_list{1}.value,main_list{2}.value,main_list{3}.value,main_list{4}.value,main_list{5}.value,main_list{6}.value,main_list{7}.value,main_list{8}.value,main_list{9}.value,main_list{10}.value
    TRIM_CHARS = abcdefghijkl
    TRIM_TO_NONE = Yes
    TRIM_TYPE = Left
    -> ListConcatenator_11
ListConcatenator_11
    DROP_EMPTY_PARTS = Yes
    LIST_ATTR = main_list{}.value
    SEP = "; "
    VAL_ATTR = Main
    -> AttributeCreator_4
AttributeCreator_4
    ATTR_TABLE:
      SET_TO Action = U
      SET_TO Record Type = 1
      SET_TO Contributor System = DFO-IA
      SET_TO Contributor Org = GC:DFO-MPO
      SET_TO Content Category = Project
      SET_TO PublishedFor = Proponent
      SET_TO Subject Area = Water
      SET_TO Rights.License = GC-OpenData
      SET_TO Rights.Disposition = Open
      SET_TO UpdateFrequency = FME_CONDITIONAL:DEFAULT_VALUE'not_planned'BOOL_OP;OR;COMPOSITE_TEST;1 OR 2;TEST @Value(P_A_L_03_ID) = 1;TEST @Value(P_A_L_03_ID) = 6'continual'FME_NUM_CONDITIONS2___
      SET_TO RecordKeeper.Organization = GC:NRCan-RNCan
      SET_TO RecordKeeper.System = NRCAN-OSDP
      SET_TO RecordKeeper.LastUserToModify = OSDP.DFO-IA.Project
      SET_TO Resource.Type[1] = Project
      SET_TO Resource.Format[1] = HTML
      SET_TO Resource.ServiceProtocol[1] = HTTP
      SET_TO Resource.Language[1] = eng; fre
      SET_TO Resource.Name (EN)[1] = Contact the Fish and Fish Habitat Protection Program
      SET_TO Resource.Name (FR)[1] = Contactez le Programme de protection du poisson et de son l'habitat
      SET_TO Resource.URL (EN)[1] = http://www.dfo-mpo.gc.ca/pnw-ppe/contact-eng.html
      SET_TO Resource.URL (FR)[1] = http://www.dfo-mpo.gc.ca/pnw-ppe/contact-fra.html
      SET_TO Resource.Type[2] = Dataset
      SET_TO Resource.Format[2] = HTML
      SET_TO Resource.ServiceProtocol[2] = HTTPS
      SET_TO Resource.Language[2] = eng; fre
      SET_TO Resource.Name (EN)[2] = Fisheries Act Registry
      SET_TO Resource.Name (FR)[2] = Registre de la Loi sur les pêches
      SET_TO Resource.URL (EN)[2] = https://open.canada.ca/data/en/dataset/2c09d2fd-9a8e-4d8c-b5af-95747e36eaac
      SET_TO Resource.URL (FR)[2] = https://ouvert.canada.ca/data/fr/dataset/2c09d2fd-9a8e-4d8c-b5af-95747e36eaac
      SET_TO Creator (EN) = @Value(Proponent(Organization))
      SET_TO Creator (FR) = FME_CONDITIONAL:DEFAULT_VALUE'@Value(Promoteur (Organisme))'BOOL_OP;OR;COMPOSITE_TEST;1;TEST @Value(Promoteur (Organisme)) = _FME_BLANK_STRING_'@Value(Creator (EN))'FME_NUM_CONDITIONS2___
      SET_TO Resource Total = 2
      SET_TO Date.LastUpdate = @Evaluate(@Value(Auth Date/Date de auth)/1000)
      SET_TO Date.Published = @Evaluate(@Value(Auth Date/Date de auth)/1000)
      SET_TO Date.Start = @Evaluate(@Value(Effective Date/Date en vigueur)/1000)
      SET_TO Date.End = @Evaluate(@Value(Expiry Date/Date d'expire)/1000)
      SET_TO Coverage.Geometry = FME_CONDITIONAL:DEFAULT_VALUE'POINT(@Value(Longitude / Longitude) @Value(Latitude / Latitude))'BOOL_OP;OR;COMPOSITE_TEST;1 OR 2;CASE_INSENSITIVE_TEST @Value(Latitude / Latitude) CONTAINS no_value;CASE_INSENSITIVE_TEST @Value(Longitude / Longitude) CONTAINS no_value''FME_NUM_CONDITIONS2___
      SET_TO Identifier.Bundle = FME_NULL_VALUE
      SET_TO Identifier.Artifact = @Value(ID)
      SET_TO Identifier.Artifact (DOI) = FME_NULL_VALUE
      SET_TO Identifier.Child = FME_NULL_VALUE
      SET_TO Coverage.Country = FME_NULL_VALUE
      SET_TO Coverage.Region = FME_NULL_VALUE
      SET_TO External.DatasetCategory = FME_NULL_VALUE
      SET_TO External.ProjectCategory = @Value(Main)
      SET_TO Keywords (EN) = FME_CONDITIONAL:DEFAULT_VALUE'FME_NULL_VALUE'BOOL_OP;OR;COMPOSITE_TEST;1;TEST Watershed/Nom du Bassin ATTRIBUTE_HAS_A_VALUE _FME_BLANK_STRING_' @Value(Watershed/Nom du Bassin) Watershed'FME_NUM_CONDITIONS2___
      SET_TO Keywords (FR) = FME_CONDITIONAL:DEFAULT_VALUE'FME_NULL_VALUE'BOOL_OP;OR;COMPOSITE_TEST;1;TEST Watershed/Nom du Bassin ATTRIBUTE_HAS_A_VALUE _FME_BLANK_STRING_' @Value(Watershed/Nom du Bassin) Watershed'FME_NUM_CONDITIONS2___
      SET_TO Coverage.ProvinceCd = @Value(P_P_L_01_ID)
      SET_TO Publisher (EN) = @ReplaceString(Fisheries and Oceans Canada;@Value(_concatenated_fed_stakeholders_list);@Value(_concatenated_prov_stakeholders_list),|,;)
      SET_TO Publisher (FR) = @ReplaceString(Pêches et Océans Canada;@Value(_concatenated_fed_parties_prenantes_list);@Value(_concatenated_prov_parties_prenantes_list),|,;)
      SET_TO Resource.Type[3]
      SET_TO Resource.Format[3]
      SET_TO Resource.ServiceProtocol[3]
      SET_TO Resource.Language[3]
      SET_TO Resource.Name (EN)[3]
      SET_TO Resource.Name (FR)[3]
      SET_TO Resource.URL (EN)[3]
      SET_TO Resource.URL (FR)[3]
      SET_TO Resource.Type[4]
      SET_TO Resource.Format[4]
      SET_TO Resource.ServiceProtocol[4]
      SET_TO Resource.Language[4]
      SET_TO Resource.Name (EN)[4]
      SET_TO Resource.Name (FR)[4]
      SET_TO Resource.URL (EN)[4]
      SET_TO Resource.URL (FR)[4]
    -> AttributeRemover_3
AttributeRemover_3
    LIST_ATTRS = Main_list{} Main_list{}.value
    REMOVE_ATTRS = Main,Main_order
    -> StringReplacer
StringReplacer
    CASE = NO
    FIND_TEXT = ;+
    NO_MATCH = _FME_NO_OP_
    REGEXP = YES
    REPLACE_TEXT = ;
    SRC_ATTRS = Keywords (EN),Keywords (FR),Publisher (EN),Publisher (FR),Subject Topic,External.ProjectCategory
    -> AttributeTrimmer
AttributeTrimmer
    SRC_ATTRS = "Keywords (EN)","Keywords (FR)","Publisher (EN)","Publisher (FR)","Subject Topic",External.ProjectCategory
    TRIM_CHARS = ;
    TRIM_TO_NONE = Yes
    TRIM_TYPE = Both
    -> DateTimeConverter_3

Bookmark: Ajouter éléments dans Dev. Activities quand valeurs présentes dans Sub Topic
Junction_3
    -> AttributeCreator_11
AttributeCreator_11
    ATTR_TABLE = SET_TO Main_order = FME_CONDITIONAL:DEFAULT_VALUE'@Value(Main_order)'BOOL_OP;AND;COMPOSITE_TEST;1;CASE_INSENSITIVE_TEST @Value(Subject Topic) CONTAINS Mining Industry'@Value(Main_order); aMining Industry'FME_NUM_CONDITIONS2___
    -> AttributeCreator_12
AttributeCreator_12
    ATTR_TABLE = SET_TO Main_order = FME_CONDITIONAL:DEFAULT_VALUE'@Value(Main_order)'BOOL_OP;OR;COMPOSITE_TEST;1;CASE_INSENSITIVE_TEST @Value(Subject Topic) CONTAINS Petroleum Industry'@Value(Main_order); bPetroleum Industry'FME_NUM_CONDITIONS2___
    -> AttributeCreator_13
AttributeCreator_13
    ATTR_TABLE = SET_TO Main_order = FME_CONDITIONAL:DEFAULT_VALUE'@Value(Main_order)'BOOL_OP;OR;COMPOSITE_TEST;1;CASE_INSENSITIVE_TEST @Value(Subject Topic) CONTAINS Energy'@Value(Main_order); cEnergy'FME_NUM_CONDITIONS2___
    -> AttributeCreator_14
AttributeCreator_14
    ATTR_TABLE = SET_TO Main_order = FME_CONDITIONAL:DEFAULT_VALUE'@Value(Main_order)'BOOL_OP;OR;COMPOSITE_TEST;1;CASE_INSENSITIVE_TEST @Value(Subject Topic) CONTAINS Agriculture'@Value(Main_order); dAgriculture'FME_NUM_CONDITIONS2___
    -> AttributeCreator_15
AttributeCreator_15
    ATTR_TABLE = SET_TO Main_order = FME_CONDITIONAL:DEFAULT_VALUE'@Value(Main_order)'BOOL_OP;OR;COMPOSITE_TEST;1;CASE_INSENSITIVE_TEST @Value(Subject Topic) CONTAINS Forestry Industry'@Value(Main_order); eForestry Industry'FME_NUM_CONDITIONS2___
    -> AttributeCreator_16
AttributeCreator_16
    ATTR_TABLE = SET_TO Main_order = FME_CONDITIONAL:DEFAULT_VALUE'@Value(Main_order)'BOOL_OP;OR;COMPOSITE_TEST;1 OR 2;CASE_INSENSITIVE_TEST @Value(Subject Topic) CONTAINS Transport Industry;CASE_INSENSITIVE_TEST @Value(Subject Topic) CONTAINS fTransport Industry'@Value(Main_order); fTransport Industry'FME_NUM_CONDITIONS2___
    -> AttributeCreator_17
AttributeCreator_17
    ATTR_TABLE = SET_TO Main_order = FME_CONDITIONAL:DEFAULT_VALUE'@Value(Main_order)'BOOL_OP;OR;COMPOSITE_TEST;1;CASE_INSENSITIVE_TEST @Value(Subject Topic) CONTAINS Waste Management'@Value(Main_order); gWaste Management'FME_NUM_CONDITIONS2___
    -> AttributeCreator_18
AttributeCreator_18
    ATTR_TABLE = SET_TO Main_order = FME_CONDITIONAL:DEFAULT_VALUE'@Value(Main_order)'BOOL_OP;OR;COMPOSITE_TEST;1;CASE_INSENSITIVE_TEST @Value(Subject Topic) CONTAINS Water Management'@Value(Main_order); hWater Management'FME_NUM_CONDITIONS2___
    -> AttributeCreator_19
AttributeCreator_19
    ATTR_TABLE = SET_TO Main_order = FME_CONDITIONAL:DEFAULT_VALUE'@Value(Main_order)'BOOL_OP;OR;COMPOSITE_TEST;1;CASE_INSENSITIVE_TEST @Value(Subject Topic) CONTAINS Environmental Management'@Value(Main_order); iEnvironmental Management'FME_NUM_CONDITIONS2___
    -> AttributeCreator_20
AttributeCreator_20
    ATTR_TABLE = SET_TO Main_order = FME_CONDITIONAL:DEFAULT_VALUE'@Value(Main_order)'BOOL_OP;OR;COMPOSITE_TEST;1;CASE_INSENSITIVE_TEST @Value(Subject Topic) CONTAINS Defence Industry'@Value(Main_order); jDefence Industry'FME_NUM_CONDITIONS2___
    -> AttributeCreator_21
AttributeCreator_21
    ATTR_TABLE = SET_TO Main_order = FME_CONDITIONAL:DEFAULT_VALUE'@Value(Main_order)'BOOL_OP;OR;COMPOSITE_TEST;1;CASE_INSENSITIVE_TEST @Value(Subject Topic) CONTAINS Tourism'@Value(Main_order); kTourism'FME_NUM_CONDITIONS2___
    -> AttributeCreator_22
AttributeCreator_22
    ATTR_TABLE = SET_TO Main_order = FME_CONDITIONAL:DEFAULT_VALUE'@Value(Main_order)'BOOL_OP;OR;COMPOSITE_TEST;1;CASE_INSENSITIVE_TEST @Value(Subject Topic) CONTAINS Construction'@Value(Main_order); lConstruction'FME_NUM_CONDITIONS2___
    -> Junction_4
Junction_4
    -> Junction_5

Bookmark: Gestion des dates et heures et du format demandé
DateTimeConverter_3
    DATETIME_ATTR = Date.LastUpdate
    IN_FORMAT = %s$
    OUT_FORMAT = %Y-%m-%dT%H:%M:%S
    PASSTHROUGH = NO
    REPAIR_INPUT = YES
    -> DateTimeConverter
DateTimeConverter
    DATETIME_ATTR = Date.Published
    IN_FORMAT = %Es$
    OUT_FORMAT = %Y-%m-%d
    PASSTHROUGH = NO
    REPAIR_INPUT = YES
    -> DateTimeConverter_2
DateTimeConverter_2
    DATETIME_ATTR = Date.End Date.Start
    IN_FORMAT = %Es$
    OUT_FORMAT = %Y-%m-%d
    PASSTHROUGH = NO
    REPAIR_INPUT = YES
    -> SubstringExtractor
    <REJECTED> -> AttributeCreator_5
AttributeCreator_5
    ATTR_TABLE:
      SET_TO Date.Start
      SET_TO Date.End
    -> SubstringExtractor
Note: Enlever fractions de secondes
SubstringExtractor
    END = 18
    RESULT_ATTR = Date.LastUpdate
    SRC_STRING = @Value(Date.LastUpdate)
    START = 0
    -> StringConcatenator
Note: Ajouter Z
StringConcatenator
    ACTION = Overwrite Existing Attributes
    ATTRLIST = Date.LastUpdate
    PARM_LINE = fme_basicstring:23%1:@Value(Date.LastUpdate)Z
    -> Attribute_splitter_DeLuxe_7

Bookmark: Enlever les doublons dans les concaténations
Attribute_splitter_DeLuxe_7: Attribute splitter DeLuxe
    ATTR_2_SPLIT = Publisher (EN)
    DELIMITER = ;
    OUT_LIST_ATTR_NAME = value
    OUT_LIST_NAME = publisher_en_list
    -> Attribute_splitter_DeLuxe_8
Attribute_splitter_DeLuxe_8: Attribute splitter DeLuxe
    ATTR_2_SPLIT = Publisher (FR)
    DELIMITER = ;
    OUT_LIST_ATTR_NAME = value
    OUT_LIST_NAME = publisher_fr_list
    -> Attribute_splitter_DeLuxe_9
Attribute_splitter_DeLuxe_9: Attribute splitter DeLuxe
    ATTR_2_SPLIT = Subject Topic
    DELIMITER = ;
    OUT_LIST_ATTR_NAME = value
    OUT_LIST_NAME = Subject_topic_list
    -> Attribute_splitter_DeLuxe_10
Attribute_splitter_DeLuxe_10: Attribute splitter DeLuxe
    ATTR_2_SPLIT = External.ProjectCategory
    DELIMITER = ;
    OUT_LIST_ATTR_NAME = value
    OUT_LIST_NAME = External_project_category_list
    -> AttributeExposer_6
AttributeExposer_6
    ATTR_LIST = publisher_en_list{}.value,publisher_fr_list{}.value,Subject_topic_list{}.value,External_project_category_list{}.value
    -> ListDuplicateRemover
ListDuplicateRemover
    SRC_LIST = publisher_en_list{}.value
    -> ListDuplicateRemover_2
ListDuplicateRemover_2
    SRC_LIST = publisher_fr_list{}.value
    -> ListDuplicateRemover_3
ListDuplicateRemover_3
    SRC_LIST = Subject_topic_list{}.value
    -> ListDuplicateRemover_4
ListDuplicateRemover_4
    SRC_LIST = External_project_category_list{}.value
    -> ListConcatenator_7
ListConcatenator_7
    DROP_EMPTY_PARTS = Yes
    LIST_ATTR = publisher_en_list{}.value
    SEP = "; "
    VAL_ATTR = Publisher (EN)
    -> ListConcatenator_8
ListConcatenator_8
    DROP_EMPTY_PARTS = Yes
    LIST_ATTR = publisher_fr_list{}.value
    SEP = "; "
    VAL_ATTR = Publisher (FR)
    -> ListConcatenator_9
ListConcatenator_9
    DROP_EMPTY_PARTS = Yes
    LIST_ATTR = Subject_topic_list{}.value
    SEP = "; "
    VAL_ATTR = Subject Topic
    -> ListConcatenator_10
ListConcatenator_10
    DROP_EMPTY_PARTS = Yes
    LIST_ATTR = External_project_category_list{}.value
    SEP = "; "
    VAL_ATTR = External.ProjectCategory
    -> ListElementCounter_2

Bookmark: Title - Description - CoveragePlacename (traduction des nouveaux enregistrements ou de ceux qui ont été mis à jour)
Note: Utilisation de la province pour déterminer langue: Données Qc = français
Tester
    BOOL_OP = OR
    COMPOSITE_TEST = 1
    TEST_CLAUSE = TEST @Value(P_P_L_01_ID) = 5
    TEST_MODE = TEST
    PASSED -> AWS_TRANSLATE_2
    FAILED -> AWS_TRANSLATE_3
AWS_TRANSLATE_2
    ACTIVATE_TRANSLATION = $(ACTIVATE_TRANSLATION)
    ATTR_2_TRANSLATE = Description,PlaceName,Title
    MODE = French-->English
    -> AttributeExposer_10
AttributeExposer_10
    ATTR_LIST = Title_en,Description_en,PlaceName_en,Title,Description,PlaceName
    -> AttributeCreator_6
AttributeCreator_6
    ATTR_TABLE:
      SET_TO Title_fr = @Value(Title)
      SET_TO Description_fr = @Value(Description)
      SET_TO PlaceName_fr = @Value(PlaceName)
    -> AttributeExposer_3
AWS_TRANSLATE_3
    ACTIVATE_TRANSLATION = $(ACTIVATE_TRANSLATION)
    ATTR_2_TRANSLATE = Description,PlaceName,Title
    MODE = English-->French
    -> AttributeExposer_9
AttributeExposer_9
    ATTR_LIST = Title_fr,Description_fr,PlaceName_fr,Title,Description,PlaceName
    -> AttributeCreator_24
AttributeCreator_24
    ATTR_TABLE:
      SET_TO Title_en = @Value(Title)
      SET_TO Description_en = @Value(Description)
      SET_TO PlaceName_en = @Value(PlaceName)
    -> AttributeExposer_3
AttributeExposer_3
    ATTR_LIST = "Authorization Type",Date.Published,Date.Start,Date.End,"Type de authorization",Action,"Content Category","Contributor Org","Contributor System",Coverage.Country,Coverage.Geometry,Coverage.ProvinceCd,Coverage.Region,"Creator (EN)","Creator (FR)",Date.LastUpdate,External.DatasetCategory,External.ProjectCategory,Identifier.Artifact,"Identifier.Artifact (DOI)",Identifier.Bundle,Identifier.Child,"Keywords (EN)","Keywords (FR)",P_P_L_01_ID,PublishedFor,"Publisher (EN)","Publisher (FR)","Record Type",RecordKeeper.LastUserToModify,RecordKeeper.Organization,RecordKeeper.System,"Resource Total",Resource.Format[1],Resource.Format[2],Resource.Format[3],Resource.Format[4],Resource.Language[1],Resource.Language[2],Resource.Language[3],Resource.Language[4],"Resource.Name (EN)[1]","Resource.Name (EN)[2]","Resource.Name (EN)[3]","Resource.Name (EN)[4]","Resource.Name (FR)[1]","Resource.Name (FR)[2]","Resource.Name (FR)[3]","Resource.Name (FR)[4]",Resource.ServiceProtocol[1],Resource.ServiceProtocol[2],Resource.ServiceProtocol[3],Resource.ServiceProtocol[4],Resource.Type[1],Resource.Type[2],Resource.Type[3],Resource.Type[4],"Resource.URL (EN)[1]","Resource.URL (EN)[2]","Resource.URL (EN)[3]","Resource.URL (EN)[4]","Resource.URL (FR)[1]","Resource.URL (FR)[2]","Resource.URL (FR)[3","Resource.URL (FR)[4]",Rights.Disposition,Rights.License,"Subject Area","Subject Topic",UpdateFrequency,Publisher_citation_en,Publisher_citation_fr
    -> AttributeCreator_8
AttributeCreator_8
    ATTR_TABLE:
      SET_TO Description (EN) = Authorization Type: @Value(Authorization Type)
        Authorization Date: @Value(Date.Published)
        Effective Date: @Value(Date.Start)
        Expiry Date: @Value(Date.End)
        @Value(Description_en)
      SET_TO Description (FR) = Type d'autorisation : @Value(Type de authorization)
        Date d'autorisation : @Value(Date.Published)
        Date d'entrée en vigueur : @Value(Date.Start)
        Date d'expiration : @Value(Date.End)
        @Value(Description_fr)
      SET_TO Title (EN) = @Value(Title_en)
      SET_TO Title (FR) = @Value(Title_fr)
      SET_TO Coverage.PlaceName (EN) = @Value(PlaceName_en)
      SET_TO Coverage.PlaceName (FR) = @Value(PlaceName_fr)
    -> SubstringExtractor_2

Bookmark: Création des attributs de Citation
SubstringExtractor_2
    END = 9
    RESULT_ATTR = Date_citation
    SRC_STRING = @Value(Date.LastUpdate)
    START = 0
    -> AttributeCreator_7
AttributeCreator_7
    ATTR_TABLE:
      SET_TO _citationDate_en = @Value(Date_citation)
      SET_TO _citationDate_fr = @Value(Date_citation)
    -> DateTimeConverter_4
DateTimeConverter_4
    DATETIME_ATTR = _citationDate_en
    OUT_FORMAT = %Y, %B %e
    PASSTHROUGH = NO
    REPAIR_INPUT = YES
    -> DateTimeConverter_5
    <REJECTED> -> Terminator_5
DateTimeConverter_5
    DATETIME_ATTR = _citationDate_fr
    OUT_FORMAT = %Y,  %e %B
    PASSTHROUGH = NO
    REPAIR_INPUT = YES
    -> PythonCaller_10
    <REJECTED> -> Terminator_5
PythonCaller_10
    NEW_ATTRIBUTES = _citationDate_fr _error_date
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              mois={}
              mois['January']='janvier'
              mois['February']='février'
              mois['March']='mars'
              mois['April']='avril'
              mois['May']='mai'
              mois['June']='juin'
              mois['July']='juillet'
              mois['August']='août'
              mois['September']='septembre'
              mois['October']='octobre'
              mois['November']='novembre'
              mois['December']='décembre'

              fr=False
              for keys in mois:
                  if keys in feature.getAttribute('_citationDate_fr'):
                      feature.setAttribute('_citationDate_fr',feature.getAttribute('_citationDate_fr').replace(keys,mois[keys]))
                      fr=True

              if not fr:
                  feature.setAttribute('_error_date','Impossible de mapper la date %s en français'%(feature.getAttribute('_citationDate_fr')))


              self.pyoutput(feature)
          def close(self):
              pass
    PYTHONSYMBOL = FeatureProcessor
    -> Tester_3
Tester_3
    BOOL_OP = OR
    COMPOSITE_TEST = 1
    TEST_CLAUSE = TEST @Value(_error_date) = ""
    TEST_MODE = TEST
    PASSED -> AttributeCreator_25
    FAILED -> Terminator_6
AttributeCreator_25
    ATTR_TABLE:
      SET_TO Citation Total = 1
      SET_TO Citation.Value (EN)[1] = Fisheries Act Registry. (@Value(_citationDate_en)). @Value(Title (EN)). @Value(Publisher_citation_en). https://osdp-psdo.canada.ca/dp/en/search/metadata/@Value(Contributor System)-1-@Value(Identifier.Artifact)
      SET_TO Citation.Value (FR)[1] = Registre de la Loi sur les pêches. (@Value(_citationDate_fr)). @Value(Title (FR)). @Value(Publisher_citation_fr). https://osdp-psdo.canada.ca/dp/fr/recherche/metadonnees/@Value(Contributor System)-1-@Value(Identifier.Artifact)
      SET_TO Citation.Format[1] = APA
    -> FeatureHolder
Terminator_6
    MESSAGE = @Value(_error_date)
Terminator_5
    MESSAGE = Problème avec la gestion des dates pour les citations/références

Bookmark: Ajout attributs nom fichier
AttributeCreator_9
    ATTR_TABLE:
      SET_TO export_date = @Left(@Value(_dateStamp),8)T@Substring(@Value(_dateStamp),8,2)@Substring(@Value(_dateStamp),10,2)@Substring(@Value(_dateStamp),12,2)Z
      SET_TO RecordKeeper.LastSyncTS = @Left(@Value(export_date),4)-@Substring(@Value(export_date),4,2)-@Substring(@Value(export_date),6,5):@Substring(@Value(export_date),11,2):@Substring(@Value(export_date),13,3)
      SET_TO conditioning_parameters.source_directory = $(FME_SHAREDRESOURCE_DATA)/DDR/Conditioning_Data/DFO_OSDP_API
      SET_TO _DDR_ServiceName = DFO_OSDP_API
      SET_TO _bck_date = @DateTimeFormat(@round(@DateTimeNow(),0), %Y-%m-%d_%H%M%S)
      SET_TO last_run = @DateTimeFormat(@round(@DateTimeNow(),0), %Y-%m-%dT%H:%M:%S)
    -> Output [Execution]
    -> Output [Dataset]

Bookmark: Copie des fichiers de sortie et gestion des messages
Note: Activer upload
Output
    ENV = $(ENV)
    EXECUTION_TRACE = $(WORKSPACE_NAME)+Output
    EXPORT_DATE = @Value(export_date)
    Execution -> Messages [Execution]
    Communication -> Messages [Communication]
Messages
    EXECUTION_TRACE = $(WORKSPACE_NAME)+Messages

FME custom transformer Interative_translation

PythonCaller_Input (input)
    -> AttributeExposer
AttributeExposer
    ATTR_LIST = _iteration,_attr2translate,_attrlist2translate
    -> PythonCaller
Note: Translation with AWS
PythonCaller
    NEW_ATTRIBUTES = _translation_problem
    PYTHONSOURCE:
      import fme
      import fmeobjects
      import time

      def translate_attributes(inText,inlang,outlang):
          try:
              import boto3



              translate = boto3.client('translate', 'ca-central-1', use_ssl=True)
              result = translate.translate_text(Text=inText,SourceLanguageCode=inlang, TargetLanguageCode=outlang).get('TranslatedText')
              return result
          except:
              print ('NE FONCTIONNE PAS DU PREMIER COUP')
              print('PROBLEME _________________________________')
              print(inText)
              raise


      # Template Function interface:
      # When using this function, make sure its name is set as the value of
      # the 'Class or Function to Process Features' transformer parameter
      def processFeature(feature):


          attributestranslation=feature.getAttribute('_attr2translate')
          list_atttranslation=feature.getAttribute('_attrlist2translate')

          try:

              if feature.getAttribute('_mode')==r'English-->French':
                  in_lang="en"
                  out_lang="fr"
                  out_suffix=r'_fr'
              else:
                  in_lang="fr"
                  out_lang="en"
                  out_suffix=r'_en'



              if  attributestranslation:

                  for i in attributestranslation.split(','):
                      text = feature.getAttribute(i)
                      if text and not feature.getAttribute('%s%s'%(i,out_suffix)):

                          if feature.getAttribute('_aws_activation').lower()=='yes':
                              translated_text = translate_attributes(text,in_lang,out_lang)
                          else:
                              translated_text='Translation of '+text
                          if translated_text:
                              feature.setAttribute('%s%s'%(i,out_suffix),translated_text)

              if list_atttranslation:
                  for attr in list_atttranslation.split(','):
                      temp_list_value=feature.getAttribute(attr)
                      if (temp_list_value):
                          list_name=attr.split('{}.')[0]
                          list_attr=attr.split('{}.')[1]
                          list_len=len(temp_list_value)

                          for k in range(list_len):
                              temp_attr_name='%s{%d}.%s'%(list_name,k,list_attr)
                              temp_value=feature.getAttribute(temp_attr_name)

                              if temp_value and not feature.getAttribute('%s%s'%(temp_attr_name,out_suffix)):

                                  if feature.getAttribute('_aws_activation').lower()=='yes':
                                      translated_text = translate_attributes(temp_value,in_lang,out_lang)
                                  else:
                                      translated_text='Translation of '+temp_value
                                  if translated_text:
                                      feature.setAttribute('%s%s'%(temp_attr_name,out_suffix),translated_text)


              feature.setAttribute('_translation_problem',0)
          except:
              feature.setAttribute('_translation_problem',1)
    PYTHONSYMBOL = processFeature
    -> Tester_2
Note: Translation issues ?
Tester_2
    BOOL_OP = OR
    COMPOSITE_TEST = 1
    TEST_CLAUSE = TEST @Value(_translation_problem) = 0
    TEST_MODE = TEST
    PASSED -> PythonCaller_5
    FAILED -> Tester
Note: Replacing URL in translated text
PythonCaller_5
    PYTHONSOURCE:
      import fme
      import fmeobjects
      # Template Function interface:
      # When using this function, make sure its name is set as the value of
      # the 'Class or Function to Process Features' transformer parameter
      def processFeature(feature):
          try:

              if feature.getAttribute('_mode')==r'English-->French':
                  out_suffix=r'_fr'
              else:
                  out_suffix=r'_en'

              #Regeular attributes
              attr2Translate=feature.getAttribute('_attr2translate')
              if attr2Translate:
                  for attr in attr2Translate.split(','):
                      indice_https=0
                      indice_http=0
                      indice_ftp=0

                      temp_translated_value=feature.getAttribute('%s%s'%(attr,out_suffix))
                      if temp_translated_value:
                          #Catching pre identified URL
                          list_urls_https=[]
                          list_urls_http=[]
                          list_urls_ftp=[]
                          list_urls_https=feature.getAttribute('_aws_translate_temp_urls_https_%s{}'%(attr))
                          list_urls_http=feature.getAttribute('_aws_translate_temp_urls_http_%s{}'%(attr))
                          list_urls_ftp=feature.getAttribute('_aws_translate_temp_urls_ftp_%s{}'%(attr))


                          if list_urls_https:
                              for url in list_urls_https:
                                  temp_translated_value=temp_translated_value.replace(r'$U$S%d$'%(indice_https),url)
                                  indice_https=indice_https+1

                          if list_urls_http:
                              for url in list_urls_http:

                                  temp_translated_value=temp_translated_value.replace(r'$U$P%d$'%(indice_http),url)
                                  indice_http=indice_http+1

                          if list_urls_ftp:
                              for url in list_urls_ftp:

                                  temp_translated_value=temp_translated_value.replace(r'$U$F%d$'%(indice_ftp),url)
                                  indice_ftp=indice_ftp+1

                          feature.setAttribute('%s%s'%(attr,out_suffix),temp_translated_value)

              #List Attributes
              list_atttranslation=feature.getAttribute('_attrlist2translate')

              if list_atttranslation:
                  for attr in list_atttranslation.split(','):
                      temp_list_value=feature.getAttribute(attr)
                      if (temp_list_value):
                          list_name=attr.split('{}.')[0]
                          list_attr=attr.split('{}.')[1]
                          list_len=len(temp_list_value)

                          for k in range(list_len):
                              temp_attr_name='%s{%d}.%s'%(list_name,k,list_attr)
                              temp_translated_value=feature.getAttribute('%s%s'%(temp_attr_name,out_suffix))

                              if temp_translated_value:
                                  indice_https=0
                                  indice_http=0
                                  indice_ftp=0



                                  #Catching pre identified URL
                                  list_urls_https=[]
                                  list_urls_http=[]
                                  list_urls_ftp=[]

                                  list_urls_https=feature.getAttribute('_aws_translate_temp_urls_https_%s{}'%(temp_attr_name))
                                  list_urls_http=feature.getAttribute('_aws_translate_temp_urls_http_%s{}'%(temp_attr_name))
                                  list_urls_ftp=feature.getAttribute('_aws_translate_temp_urls_ftp_%s{}'%(temp_attr_name))


                                  if list_urls_https:
                                      for url in list_urls_https:
                                          temp_translated_value=temp_translated_value.replace(r'$U$S%d$'%(indice_https),url)
                                          indice_https=indice_https+1

                                  if list_urls_http:
                                      for url in list_urls_http:

                                          temp_translated_value=temp_translated_value.replace(r'$U$P%d$'%(indice_http),url)
                                          indice_http=indice_http+1

                                  if list_urls_ftp:
                                      for url in list_urls_ftp:

                                          temp_translated_value=temp_translated_value.replace(r'$U$F%d$'%(indice_ftp),url)
                                          indice_ftp=indice_ftp+1

                                  feature.setAttribute('%s%s'%(temp_attr_name,out_suffix),temp_translated_value)




              feature.setAttribute('_translation_problem',0)
          except:
              feature.setAttribute('_translation_problem',1)
    PYTHONSYMBOL = processFeature
    -> Tester_3
Tester_3
    BOOL_OP = OR
    COMPOSITE_TEST = 1
    TEST_CLAUSE = TEST @Value(_translation_problem) = 0
    TEST_MODE = TEST
    PASSED -> TRANSLATED (output)
    FAILED -> Tester
TRANSLATED (output)
Tester
    BOOL_OP = OR
    COMPOSITE_TEST = 1
    TEST_CLAUSE = TEST @Value(_iteration) = 10
    TEST_MODE = TEST
    PASSED -> FAILED (output)
    FAILED -> AttributeCreator
FAILED (output)
AttributeCreator
    ATTR_TABLE = SET_TO _iteration = @Evaluate(@Value(_iteration)+1)
    -> PythonCaller_2
PythonCaller_2
    PYTHONSOURCE:
      import fme
      import fmeobjects
      import time

      # Template Function interface:
      # When using this function, make sure its name is set as the value of
      # the 'Class or Function to Process Features' transformer parameter
      def processFeature(feature):
          print('Attente de 60 secondes pour essai no %d'%(feature.getAttribute('_iteration')))
          time.sleep(60)
    PYTHONSYMBOL = processFeature
    -> PythonCaller_Input (output)
PythonCaller_Input (output)

FME custom transformer AWS_TRANSLATE
Description
This custom transformers translates FME attributes and/or lists in either English or French using AWS translation services.  The attribute names or list to translate are specified using FME Published Parameters
Note1: Before translating an attribute the CT will verify if the destination attribute name exists. When the name exists, if the destination attribute value is different from the source attribute value to translate, the CT considers that the translation is done and the process stops for this attribute.  If destination attribute value is the same, the CT will try to guess (using AWS translation service) the language of the source attribute value to translate and adjust the translation accordignly.
Note2:: When an attribute and or list is translated, the CT always creates 2 new attributes with the suffix fr and en.  It keeps the original attribute name as is.
Input Ports
INPUT: The features to translate.
Output Ports
OUTPUT: The features with translated attributes and/or lists
TRANSLATION_PROBLEM: The features with a translation problem.
Parameters
ACTIVATE_TRANSLATION: Flag to enable or disable the translation. Ca take 2 values: Yes: Translate the attributes; No: Do not translate the attributes.  If the flag is set to No, the transformer will copy the text to translate in the output attribute and add the prefix: Translation of.
MODE: Flag for the direction of the translation. can take 2 values: English-->French for an English to French translation; Franch-->English for a French to English translation;
ATTR_2_TRANSLATE: Coma separated list of FME attribute to translate;
ATTR_LIST_2_TRANSLATE: Coma separated list of FME lists to translate.

Parameters:
- ACTIVATE_TRANSLATION =
- MODE =
- ATTR_2_TRANSLATE =
- ATTR_LIST_2_TRANSLATE =

INPUT (input)
    -> AttributeCreator
OUTPUT (output)
TRANSLATION_PROBLEM (output)

Bookmark: AWS Service Translation
Note: Create attributes needed for the translation
AttributeCreator
    ATTR_TABLE:
      SET_TO _aws_activation = $(ACTIVATE_TRANSLATION)
      SET_TO _mode = $(MODE)
      SET_TO _attr2translate = $(ATTR_2_TRANSLATE)
      SET_TO _attrlist2translate = $(ATTR_LIST_2_TRANSLATE)
    -> PythonCaller
Note: Translate requested attributes
PythonCaller
    NEW_ATTRIBUTES = _translation_status
    PYTHONSOURCE = from Python.AWS_TRANSLATE import process_feature
    PYTHONSYMBOL = process_feature
    -> TestFilter
TestFilter
    DEFAULT_VALUE = FAILURE
    TEST_LIST = "BOOL_OP,OR,COMPOSITE_TEST,""""""1"""""",TEST_CLAUSE,TEST @Value(_translation_status) = 0",SUCCESS
    SUCCESS -> AttributeRemover
    FAILURE -> TRANSLATION_PROBLEM (output)
Note: Remove unnecessary attribute
AttributeRemover
    REMOVE_ATTRS = _attr2translate,_attrlist2translate,_aws_activation,_mode,_translation_status
    -> ATTRIBUTE_UNEXPOSER
ATTRIBUTE_UNEXPOSER
    -> OUTPUT (output)

FME custom transformer Attribute splitter DeLuxe

Parameters:
- ATTR_2_SPLIT =   # " " ATTR_2_SPLIT
- DELIMITER =
- OUT_LIST_NAME =
- OUT_LIST_ATTR_NAME =

Input (input)
    -> AttributeSplitter_2
AttributeSplitter_2
    ATTR_NAME = $(ATTR_2_SPLIT)
    DELIMITER = $(DELIMITER)
    DROP_EMPTY_PARTS = No
    LIST_NAME = _list_Splitter_DeLuxe
    TRIM_OPTION = Both
    -> ListElementCounter
ListElementCounter
    CNT_ATTR = _element_count
    LIST_NAME = $(OUT_LIST_NAME)
    -> Tester
Tester
    BOOL_OP = OR
    COMPOSITE_TEST = 1
    TEST_CLAUSE = TEST @Value(_element_count) = 0
    TEST_MODE = TEST
    PASSED -> AttributeCreator
    FAILED -> Terminator
AttributeCreator
    ATTR_TABLE:
      SET_TO nom_liste = $(OUT_LIST_NAME)
      SET_TO nom_attribut = $(OUT_LIST_ATTR_NAME)
    -> Tester_2
Tester_2
    BOOL_OP = AND
    COMPOSITE_TEST = 1 AND 2
    TEST_CLAUSE:
      TEST @Value(nom_attribut) != ""
      TEST @Value(nom_liste) != ""
    TEST_MODE = TEST
    PASSED -> PythonCaller
    FAILED -> Terminator_2
PythonCaller
    PYTHONSOURCE:
      import fme
      import fmeobjects
      # Template Function interface:
      # When using this function, make sure its name is set as the value of
      # the 'Class or Function to Process Features' transformer parameter
      def processFeature(feature):
          list=feature.getAttribute('_list_Splitter_DeLuxe{}')
          attr_name=feature.getAttribute('nom_attribut')
          list_name=feature.getAttribute('nom_liste')

          #creation de l'index

          i=0


          for elem in list:
              feature.setAttribute('%s{%i}.%s'%(list_name,i,attr_name),elem)
              i=i+1
    PYTHONSYMBOL = processFeature
    -> AttributeRemover
AttributeRemover
    LIST_ATTRS = _list_Splitter_DeLuxe{}
    REMOVE_ATTRS = _element_count,nom_attribut,nom_liste
    -> Output (output)
Output (output)
Terminator_2
    MESSAGE = Translation Terminated
Terminator
    MESSAGE:
      Translation Terminated
      Liste déjà existante

FME custom transformer Messages

Parameters:
- EXECUTION_TRACE =   # Execution Trace

Bookmark: Messages du processus
Execution (input)
    -> FeatureMerger_2 [REQUESTOR]
Communication (input)
    -> AttributeExposer
AttributeExposer
    ATTR_LIST = _DDR_ServiceName,_en_message,_execution_trace,_fr_message,_job_id,_message_type,_severity,_timestamp,generic_parameters.METADATA_UUID,newLineCharacter
    -> TestFilter
    -> Aggregator_2

Bookmark: Success email
Aggregator_2
    ACCUM_ATTRS_NAME = Drop Incoming Attributes
    CONCAT_ATTRS = _fr_message _en_message
    LIST_ATTRS_TO_INCLUDE = _feature_type{}.name _severity
    LIST_NAME = _input_msg
    MODE = Attributes Only
    SEP = \n
    AGGREGATE -> AttributeCreator_3
AttributeCreator_3
    ATTR_TABLE:
      SET_TO email_body = The OSDP database has been updated with the latest data from DFO's Fisheries Act Registry API.\n\nMessage log:\n@Value(_en_message)\n\nBest regards,\nThe FGP team.\n\n------------------------------------------------------------------------------------\n\nLa base de données de la PSDO a été mise à jour avec les dernières données du Registre de la Loi sur les pêches du MPO.\n\nJournal des messages:\n@Value(_fr_message)\n\nCordialement,\nL'équipe de la PGF.
      SET_TO email_sent = {

        "email_to": "fgpcontributorssupport-pgfsupportcontributeurs@nrcan-rncan.gc.ca",

        "email_replyto": "fgpcontributorssupport-pgfsupportcontributeurs@nrcan-rncan.gc.ca",

        "email_subject": "DFO's Fisheries Act Registry update / Mise à jour du Registre de la loi sur les pêches du MPO",

        "subscriber_content": "@Value(email_body)"

        }
    -> JSONValidator_2
    -> Try_to_recover_2 [Execution_info]
    -> Tester
JSONValidator_2
    ERROR_LIST_ATTR = _json_error
    JSON_DOCUMENT = @Value(email_sent)
    READ_FROM_FILE = NO
    PASSED -> JSONFormatter_2
    FAILED -> Try_to_recover_2 [Invalid_Json]
Try_to_recover_2: Try to recover
    EXECUTION_TRACE = $(EXECUTION_TRACE)+Try_to_recover
    Valid_Json -> JSONFormatter_2
JSONFormatter_2
    ERROR_LIST_ATTR = _json_error
    FORMAT = Pretty Print
    INDENT_STYLE = 3 spaces
    JSON_DOCUMENT = @Value(email_sent)
    OUTPUT_ATTR = email_sent_line
    OUTPUT_ENCODING = UTF-8
    READ_FROM_FILE = NO
    REMOVE_EMPTY_OBJECTS_AND_ARRAYS = No
    REMOVE_EMPTY_STRINGS = No
    REMOVE_NULLS = No
    -> FeatureMerger_2 [SUPPLIER]
FeatureMerger_2
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = 1 1 NUM
    MERGE_TYPE = Attributes Only
    PROCESS_DUPS = YES
    REJECT_NULL_MISSING_KEYS = No
    SUPPLIERS_FIRST = No
    MERGED -> Execute_getFmeConfig
Execute_getFmeConfig: 7_Library
    Attributes_to_Expose = fmeServerUserName fmeServerPassword
    EXECUTION_TRACE = $(EXECUTION_TRACE)+Execute_getFmeConfig
    Execution_Parameters:
      {
      'userNameAttribute' : 'fmeServerUserName',
      'passwordAttribute' : 'fmeServerPassword'
      }
    Function_Name = getFmeConfig
    -> FMEServerNotifier
FMEServerNotifier
    BODY = @Value(email_sent_line)
    PASSWORD = @Value(fmeServerPassword)
    SERVER_NAME = $(FME_SERVER_WEB_URL)
    TOPIC = DDR_SEND_EMAIL
    USERNAME = @Value(fmeServerUserName)

Bookmark: Failure email
Tester
    BOOL_OP = OR
    COMPOSITE_TEST = 1 OR 2 OR 3 OR 4 OR 5 OR 6 OR 7 OR 8 OR 9 OR 10 OR 11 OR 12 OR 13 OR 14 OR 15 OR 16 OR 17 OR 18 OR 19 OR 20
    TEST_CLAUSE:
      TEST @Value(_input_msg{0}._severity) = ERROR
      TEST @Value(_input_msg{1}._severity) = ERROR
      TEST @Value(_input_msg{2}._severity) = ERROR
      TEST @Value(_input_msg{3}._severity) = ERROR
      TEST @Value(_input_msg{4}._severity) = ERROR
      TEST @Value(_input_msg{5}._severity) = ERROR
      TEST @Value(_input_msg{6}._severity) = ERROR
      TEST @Value(_input_msg{7}._severity) = ERROR
      TEST @Value(_input_msg{8}._severity) = ERROR
      TEST @Value(_input_msg{9}._severity) = ERROR
      TEST @Value(_input_msg{0}._severity) = FATAL
      TEST @Value(_input_msg{1}._severity) = FATAL
      TEST @Value(_input_msg{2}._severity) = FATAL
      TEST @Value(_input_msg{3}._severity) = FATAL
      TEST @Value(_input_msg{4}._severity) = FATAL
      TEST @Value(_input_msg{5}._severity) = FATAL
      TEST @Value(_input_msg{6}._severity) = FATAL
      TEST @Value(_input_msg{7}._severity) = FATAL
      TEST @Value(_input_msg{8}._severity) = FATAL
      TEST @Value(_input_msg{9}._severity) = FATAL
    TEST_MODE = TEST
    PASSED -> AttributeCreator_4
AttributeCreator_4
    ATTR_TABLE:
      SET_TO email_body_admin = La mise à jour des données du MPO pour la PSDO a échoué.\n@Value(_fr_message)\n\nThe DFO data update for the OSDP database has failed.\n@Value(_en_message)\n\nJOB ID: $(FME_JOB_ID)
      SET_TO email_sent_admin = {
           "email_to": "fgpcontributorssupport-pgfsupportcontributeurs@nrcan-rncan.gc.ca",
           "email_replyto": "fgpcontributorssupport-pgfsupportcontributeurs@nrcan-rncan.gc.ca",
           "email_subject": "ÉCHEC: Mise à jour des données du MPO / FAILURE:DFO data update",
           "subscriber_content": "@Value(email_body_admin)"
        }
    -> AttributeKeeper_2
AttributeKeeper_2
    CREATE_BULK_MODE_FEATURES = No
    KEEP_ATTRS = email_sent,email_sent_admin
    -> JSONValidator_3
    -> Try_to_recover_3 [Execution_info]
JSONValidator_3
    ERROR_LIST_ATTR = _json_error
    JSON_DOCUMENT = @Value(email_sent_admin)
    READ_FROM_FILE = NO
    PASSED -> JSONFormatter_3
    FAILED -> Try_to_recover_3 [Invalid_Json]
Try_to_recover_3: Try to recover
    EXECUTION_TRACE = $(EXECUTION_TRACE)+Try_to_recover
    Valid_Json -> JSONFormatter_3
JSONFormatter_3
    ERROR_LIST_ATTR = _json_error
    FORMAT = Pretty Print
    INDENT_STYLE = 3 spaces
    JSON_DOCUMENT = @Value(email_sent_admin)
    OUTPUT_ATTR = email_sent_line
    OUTPUT_ENCODING = UTF-8
    READ_FROM_FILE = NO
    REMOVE_EMPTY_OBJECTS_AND_ARRAYS = No
    REMOVE_EMPTY_STRINGS = No
    REMOVE_NULLS = No
    -> Execute_getFmeConfig_2
Execute_getFmeConfig_2: 7_Library
    Attributes_to_Expose = fmeServerUserName fmeServerPassword
    EXECUTION_TRACE = $(EXECUTION_TRACE)+Execute_getFmeConfig_2
    Execution_Parameters:
      {
      'userNameAttribute' : 'fmeServerUserName',
      'passwordAttribute' : 'fmeServerPassword'
      }
    Function_Name = getFmeConfig
    -> FMEServerNotifier_3
FMEServerNotifier_3
    BODY = @Value(email_sent_line)
    PASSWORD = @Value(fmeServerPassword)
    SERVER_NAME = $(FME_SERVER_WEB_URL)
    TOPIC = DDR_SEND_EMAIL
    USERNAME = @Value(fmeServerUserName)

Bookmark: Server log
TestFilter
    DEFAULT_VALUE = Keep other messages
    TEST_LIST = BOOL_OP,OR,COMPOSITE_TEST,<Unused>,TEST_CLAUSE,"TEST @Value(_message_type) = INTERNAL",Drop internal messages
    Drop internal messages -> AttributeCreator
    Keep other messages -> AttributeCreator
AttributeCreator
    ATTR_TABLE:
      SET_TO newLineCharacter =

      SET_TO _job_id = $(FME_JOB_ID)
      SET_TO _json_message = {
        "MetadataUUID" : "@Value(generic_parameters.METADATA_UUID)",
        "JobID" : "@Value(_job_id)",
        "ServiceName" : "@Value(_DDR_ServiceName)",
        "TimeStamp" : "@Value(_timestamp)",
        "MessageType" : "@Value(_message_type)",
        "Severity" : "@Value(_severity)",
        "ExecutionTrace" : "@ReplaceString(@Value(_execution_trace),@Value(newLineCharacter),\n)",
        "FrMessage" : "@ReplaceString(@Value(_fr_message),@Value(newLineCharacter),\n)",
        "EnMessage" : "@ReplaceString(@Value(_en_message),@Value(newLineCharacter),\n)"
        }
      SET_TO _head = {"MessageList" : [
      SET_TO _tail = ]}
    -> Aggregator
Aggregator
    ACCUM_ATTRS_NAME = Merge Incoming Attributes
    CONCAT_ATTRS = _json_message
    MODE = Attributes Only
    SEP = ",\n"
    AGGREGATE -> StringConcatenator
StringConcatenator
    ACTION = Overwrite Existing Attributes
    ATTRLIST = _json_message
    PARM_LINE = {"MessageList" : [@Value(_json_message)]}
    -> JSONValidator
    -> Try_to_recover [Execution_info]
JSONValidator
    ERROR_LIST_ATTR = _json_error
    JSON_DOCUMENT = @Value(_json_message)
    READ_FROM_FILE = NO
    PASSED -> JSONFormatter
    FAILED -> Try_to_recover [Invalid_Json]
Try_to_recover: Try to recover
    EXECUTION_TRACE = $(EXECUTION_TRACE)+Try_to_recover
    Valid_Json -> JSONFormatter
JSONFormatter
    ERROR_LIST_ATTR = _json_error
    FORMAT = Pretty Print
    INDENT_STYLE = 3 spaces
    JSON_DOCUMENT = @Value(_json_message)
    OUTPUT_ATTR = text_line_data
    OUTPUT_ENCODING = UTF-8
    READ_FROM_FILE = NO
    REMOVE_EMPTY_OBJECTS_AND_ARRAYS = No
    REMOVE_EMPTY_STRINGS = No
    REMOVE_NULLS = No
    -> AttributeCreator_2
AttributeCreator_2
    ATTR_TABLE = SET_TO _outputStreamDestination = $(FME_SHAREDRESOURCE_TEMP)/DDR/Admin/$(FME_JOB_ID)/$(WORKSPACE_NAME)_log.json
    -> AttributeFileWriter_1
AttributeFileWriter_1
    CHAR_ENCODING = utf-8
    FILE_NAME = @Value(_outputStreamDestination)
    OVERWRITE_FILE = Overwrite file
    SOURCE_ATTR = text_line_data

FME custom transformer Output

Parameters:
- EXECUTION_TRACE =   # Execution Trace
- EXPORT_DATE = @Value(export_date)   # Export Date
- ENV = @Value(ENV)

Note: Désactiver lorsque upload OSDP est actif

Bookmark: Output
Execution (input)
    -> Sampler
Sampler
    RATE = 1
    SAMPLE_MODE = No
    SAMPLE_TYPE_LONG = First N Features
    SAMPLED -> FeatureMerger_2 [SUPPLIER]
Dataset (input)
    -> FeatureWriter [CSV00]
Note: Écrire le CSV geoDCAT
FeatureWriter
    CSV2_COORDINATE_SYSTEM_GRANULARITY = FEATURE_TYPE
    CSV2_DELIMITER = ,
    CSV2_ENCODING = utf-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = yes
    CSV2_QUALIFY_FIELD_VALUES = yes
    CSV2_ROW_TERMINATION = System
    CSV2_WRITE_BOM_FOR_UNICODE = Yes
    CSV2_WRITE_FIELD_NAMES = firstrow
    CSV2_WRITE_SCHEMA_FILE = NO
    DATASET = $(FME_SHAREDRESOURCE_DATA)\DDR\Conditioning_Data\DFO_OSDP_API\GeoDCAT
    DATASET_ATTR = _dataset
    FEATURE_TYPE_LIST_ATTR = _feature_type
    FORMAT = CSV2
    MORE_SUMMARY_ATTRS = export_date
    TOTAL_FEATURES_WRITTEN_ATTR = _total_features_written
    SUMMARY -> FeatureMerger_2 [REQUESTOR]
FeatureMerger_2
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = 1 1 NUM
    MERGE_TYPE = Attributes Only
    PROCESS_DUPS = YES
    REJECT_NULL_MISSING_KEYS = No
    SUPPLIERS_FIRST = No
    MERGED -> Create_message_10a
    MERGED -> Execute_Python_3.7_Library
    UNMERGED_REQUESTOR -> Create_message_10e
Note: Copier dernier fichier DFO
Execute_Python_3.7_Library: 7_Library
    EXECUTION_TRACE = $(EXECUTION_TRACE)+Execute_Python_fileCopy
    Execution_Parameters:
      [
      {"parametersAreAttributeNames":False},
      {
        "source":"@Value(_dataset)\@Value(_feature_type{0}.name).csv",
        "destination":"$(FME_SHAREDRESOURCE_DATA)\DDR\Conditioning_Data\DFO_OSDP_API\last_dfo_file.csv"
      },
      ]
    Function_Name = fileCopy
    -> AttributeExposer
    Communication_Thread -> Create_message_10b
AttributeExposer
    ATTR_LIST = registry.download_info{0}.owner_username,last_run,_feature_type{0}.export_date
    -> FeatureWriter_2 [Output]
Note: Date de mise à jour pour DFO_OSDP_Check
FeatureWriter_2
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_WRITE_BOM_FOR_UNICODE = Yes
    CSV2_WRITE_FIELD_NAMES = firstrow
    CSV2_WRITE_SCHEMA_FILE = NO
    DATASET = $(FME_SHAREDRESOURCE_DATA)\DDR\Conditioning_Data\DFO_OSDP_API
    DATASET_ATTR = _dataset
    FEATURE_TYPE_LIST_ATTR = _feature_type
    FORMAT = CSV2
    MORE_SUMMARY_ATTRS = _feature_type{0}.export_date
    TOTAL_FEATURES_WRITTEN_ATTR = _total_features_written
    SUMMARY -> Tester
Tester
    BOOL_OP = OR
    COMPOSITE_TEST = 1
    TEST_CLAUSE = TEST @Value(_total_features_written) > 0
    TEST_MODE = TEST
    PASSED -> Execution (output) [off]
    PASSED -> AttributeExposer_2
    FAILED -> Create_message_10d
AttributeExposer_2
    ATTR_LIST = ddr_iam_role,osdp_bucket_owner_id,S3_file_upload.iam_role,S3_file_upload.bucket_owner_id
    -> AttributeCreator_3
Execution (output)
Communication (input)
    -> Create_message_10e [Communication_Thread]
Create_message_10e: Create message
    EXECUTION_TRACE = $(EXECUTION_TRACE)+Create_message_10e
    EnMessage = @DateTimeFormat(@round(@DateTimeNow(),0), %Y-%m-%d %H:%M:%S) -> Error creating geoDCAT file.
    FrMessage = @DateTimeFormat(@round(@DateTimeNow(),0), %Y-%m-%d %H:%M:%S) -> Erreur lors de la création du fichier geoDCAT.
    MessageType = USER
    Severity = ERROR
    Communication_Thread -> Create_message_10a [Communication_Thread]
Create_message_10a: Create message
    EXECUTION_TRACE = $(EXECUTION_TRACE)+Create_message_10a
    EnMessage = @DateTimeFormat(@round(@DateTimeNow(),0), %Y-%m-%d %H:%M:%S) -> The geoDCAT file for the OSDP database has been created with @Value(_total_features_written) features.
    FrMessage = @DateTimeFormat(@round(@DateTimeNow(),0), %Y-%m-%d %H:%M:%S) -> Le fichier geoDCAT pour la base de données de la PSDO a été créé avec @Value(_total_features_written) entités.
    MessageType = USER
    Severity = INFO
    Communication_Thread -> Create_message_10b [Communication_Thread]
Create_message_10b: Create message
    EXECUTION_TRACE = $(EXECUTION_TRACE)+Create_message_10b
    EnMessage = @DateTimeFormat(@round(@DateTimeNow(),0), %Y-%m-%d %H:%M:%S) -> The geoDCAT file copy (last_dfo_file.csv) has failed.
    FrMessage = @DateTimeFormat(@round(@DateTimeNow(),0), %Y-%m-%d %H:%M:%S) -> La copie du fichier geoDCAT (last_dfo_file.csv) a échoué.
    MessageType = USER
    Severity = FATAL
    Communication_Thread -> Create_message_10d [Communication_Thread]
Create_message_10d: Create message
    EXECUTION_TRACE = $(EXECUTION_TRACE)+Create_message_10d
    EnMessage = @DateTimeFormat(@round(@DateTimeNow(),0), %Y-%m-%d %H:%M:%S) -> Error creating last run date (last_run.csv).
    FrMessage = @DateTimeFormat(@round(@DateTimeNow(),0), %Y-%m-%d %H:%M:%S) -> Erreur lors de la création de la date de mise à jour (last_run.csv).
    MessageType = USER
    Severity = ERROR
    Communication_Thread -> Create_message_10f [Communication_Thread]
Create_message_10f: Create message
    EXECUTION_TRACE = $(EXECUTION_TRACE)+Create_message_10f
    EnMessage = The geoDCAT file @Value(_feature_type{0}.name).csv transfer to the OSDP servers has failed.
    FrMessage = Le transfert du fichier geoDCAT @Value(_feature_type{0}.name).csv sur le serveur du PSDO a échoué.
    MessageType = USER
    Severity = FATAL
    Communication_Thread -> Create_message_10c [Communication_Thread]
Create_message_10c: Create message
    EXECUTION_TRACE = $(EXECUTION_TRACE)+Create_message_10c
    EnMessage = @DateTimeFormat(@round(@DateTimeNow(),0), %Y-%m-%d %H:%M:%S) -> The geoDCAT file @Value(_feature_type{0}.name).csv has been transfered successfully to the OSDP servers.
    FrMessage = @DateTimeFormat(@round(@DateTimeNow(),0), %Y-%m-%d %H:%M:%S) -> Le fichier geoDCAT @Value(_feature_type{0}.name).csv a été transféré avec succès sur le serveur de la PSDO.
    MessageType = USER
    Severity = INFO
    Communication_Thread -> Communication (output)
Communication (output)

Bookmark: Upload to OSDP S3 bucket
AttributeCreator_3
    ATTR_TABLE:
      SET_TO name = s3FileUploadACL
      SET_TO region = ca-central-1
      SET_TO s3_ftp_bucket = FME_CONDITIONAL:DEFAULT_VALUE'osdp-lz-prod-sftp-files'BOOL_OP;OR;COMPOSITE_TEST;1;TEST $(ENV) = STAGING'osdp-lz-dev-sftp-files'FME_NUM_CONDITIONS2___
      SET_TO destination_path = Project/Request/DFO-IA-@Value(_feature_type{0}._feature_type{0}.export_date).csv
      SET_TO source_file = $(FME_SHAREDRESOURCE_DATA)\DDR\Conditioning_Data\DFO_OSDP_API\geoDCAT\DFO-IA-@Value(_feature_type{0}._feature_type{0}.export_date).csv
    -> Execute_decrypt
Execute_decrypt: 7_Library
    EXECUTION_TRACE = $(EXECUTION_TRACE)+Execute_decrypt
    Execution_Parameters:
      {
      "name":"name",
      "region":"region",
      "key_list" :
          [{
            "inputAttribute":"ddr_iam_role",
            "outputAttribute":"S3_file_upload.iam_role"
            },
           {
            "inputAttribute":"osdp_bucket_owner_id",
            "outputAttribute":"S3_file_upload.bucket_owner_id"
            }
           ]
      }
    Function_Name = decryptSecret
    -> Execute_s3FileUploadACL_2
    Communication_Thread -> Create_message_10f [Communication_Thread]
    Communication_Thread -> Create_message_10f
Execute_s3FileUploadACL_2: 7_Library
    EXECUTION_TRACE = $(WORKSPACE_NAME)+Execute_s3FileUploadACL
    Execution_Parameters:
      {
      'iam_role':'S3_file_upload.iam_role',
      'ftp_path':'destination_path',
      'fme_server_path':'source_file',
      's3_ftp_bucket':'s3_ftp_bucket',
      'bucket_owner_id':'S3_file_upload.bucket_owner_id'
      }
    Function_Name = s3FileUploadACL
    -> Execution (output)
    -> Create_message_10c
    Communication_Thread -> Create_message_10f
    Communication_Thread -> Create_message_10c [Communication_Thread]

FME custom transformer Try to recover

Parameters:
- EXECUTION_TRACE =   # Execution Trace

Bookmark: Try to recover
Invalid_Json (input)
    -> AttributeExposer
AttributeExposer
    ATTR_LIST = _json_error{}
    -> ListExploder
    -> doubleInvalidJsonEscapeChars
doubleInvalidJsonEscapeChars: 7_Library
    Attributes_to_Expose = _json_message
    EXECUTION_TRACE = $(EXECUTION_TRACE)+Execute_doubleInvalidJsonEscapeChars
    Execution_Parameters = _json_message
    Function_Name = doubleInvalidJsonEscapeChars
    -> FeatureMerger_2 [REQUESTOR]
    Communication_Thread -> Terminator
Terminator
    MESSAGE:
      There is a problem with the Json code generation.
      Il y a eu un problème avec la génération du code Json.
ListExploder
    ATTR_ACCUM_MODE = Only Use List Attributes
    INDEX_ATTR = _error_index
    LIST_ATTR = _json_error{}
    ELEMENTS -> AttributeExposer_2
AttributeExposer_2
    ATTR_LIST = line,column,severity,message
    -> AttributeCreator_4
AttributeCreator_4
    ATTR_TABLE:
      SET_TO _fr_json_error_message = Ligne @Value(line), colonne @Value(column) : @ReplaceString(@ReplaceString(@Value(severity),\,\\),"\"",\") - @ReplaceString(@ReplaceString(@Value(message),\,\\),"\"",\")
      SET_TO _en_json_error_message = Line @Value(line), column @Value(column) : @ReplaceString(@ReplaceString(@Value(severity),\,\\),"\"",\") - @ReplaceString(@ReplaceString(@Value(message),\,\\),"\"",\")
    -> Aggregator_2
Aggregator_2
    ACCUM_ATTRS_NAME = Merge Incoming Attributes
    CONCAT_ATTRS = _fr_json_error_message _en_json_error_message
    MODE = Attributes Only
    SEP = "\n"
    AGGREGATE -> FeatureMerger [REQUESTOR]
Execution_info (input)
    -> AttributeExposer_4
AttributeExposer_4
    ATTR_LIST = generic_parameters.METADATA_UUID,_job_id,_DDR_ServiceName,newLineCharacter,_fr_message,_en_message,_execution_trace,_head,_tail
    -> Sampler
Sampler
    RATE = 1
    SAMPLE_MODE = No
    SAMPLE_TYPE_LONG = First N Features
    SAMPLED -> FeatureMerger [SUPPLIER]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeCreator_3
AttributeCreator_3
    ATTR_TABLE:
      SET_TO _en_json_error_message = @ReplaceString(@ReplaceString(@Value(_en_json_error_message),\,\\),"\"",\")
      SET_TO _fr_json_error_message = @ReplaceString(@ReplaceString(@Value(_fr_json_error_message),\,\\),"\"",\")
      SET_TO newLineCharacter =

      SET_TO _job_id = $(FME_JOB_ID)
      SET_TO _execution_trace = $(EXECUTION_TRACE)+Build_Json_message_list
      SET_TO _fr_message = Il y a eu un problème avec la génération du code Json, mais nous avons pu le corriger.
        @Value(_fr_json_error_message)
      SET_TO _en_message = There was a problem with the Json code generation, but we have been able to correct it.
        @Value(_en_json_error_message)
      SET_TO _warning_message = {
        "MetadataUUID" : "@Value(generic_parameters.METADATA_UUID)",
        "JobID" : "@Value(_job_id)",
        "ServiceName" : "@Value(_DDR_ServiceName)",
        "TimeStamp" : "@Timestamp(^Y-^m-^d ^H:^M:^S)",
        "MessageType" : "ADMIN",
        "Severity" : "WARNING",
        "ExecutionTrace" : "@ReplaceString(@Value(_execution_trace),@Value(newLineCharacter),\n)",
        "FrMessage" : "@ReplaceString(@Value(_fr_message),@Value(newLineCharacter),\n)",
        "EnMessage" : "@ReplaceString(@Value(_en_message),@Value(newLineCharacter),\n)"
        }
      SET_TO _fr_message = Il y a eu un problème avec la génération du code Json.
        Consultez le log pour voir le code Json.
        @Value(_en_json_error_message)
      SET_TO _en_message = There is a problem with the Json code generation.
        Consult the log to see the Json code.
        @Value(_en_json_error_message)
      SET_TO _consult_the_log_message = {
        "MetadataUUID" : "@Value(generic_parameters.METADATA_UUID)",
        "JobID" : "@Value(_job_id)",
        "ServiceName" : "@Value(_DDR_ServiceName)",
        "TimeStamp" : "@Timestamp(^Y-^m-^d ^H:^M:^S)",
        "MessageType" : "ADMIN",
        "Severity" : "FATAL",
        "ExecutionTrace" : "@ReplaceString(@Value(_execution_trace),@Value(newLineCharacter),\n)",
        "FrMessage" : "@ReplaceString(@Value(_fr_message),@Value(newLineCharacter),\n)",
        "EnMessage" : "@ReplaceString(@Value(_en_message),@Value(newLineCharacter),\n)"
        }
    -> FeatureMerger_2 [SUPPLIER]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeCreator_2
AttributeCreator_2
    ATTR_TABLE:
      SET_TO _json_message = @Value(_head)
        @Value(_warning_message),
        @Right(@Value(_json_message),@int(@StringLength(@Value(_json_message))-@StringLength(@Value(_head))))
    -> JSONValidator_2
JSONValidator_2
    ERROR_LIST_ATTR = _json_error
    JSON_DOCUMENT = @Value(_json_message)
    READ_FROM_FILE = NO
    PASSED -> Valid_Json (output)
    FAILED -> AttributeCreator_5
AttributeCreator_5
    ATTR_TABLE:
      SET_TO _json_message = @Value(_head)
        @Value(_consult_the_log_message),
        @Value(_tail)
    -> Valid_Json (output)
Valid_Json (output)
