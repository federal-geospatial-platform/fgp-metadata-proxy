FME workspace 900A_OSDP_PROD_R8.fmw

Parameters:
- ENV = PROD
- Last_900A_file = $(FME_SHAREDRESOURCE_DATA)\DDR\Conditioning_Data\900A_OSDP\last_900A_file.csv"
- DATETIME = 20250219134239   # Date_Last_Update "{}" Date du timeStamp sur GCGEO (000183ed-8864-42f0-ae43-c4313a860720) YYYY-MM-DDThh:mm:ss
- Date_Published = 20190607   # "{}" Date de Publication sur GCGEO (000183ed-8864-42f0-ae43-c4313a860720) (AAAA-MM-JJ)
- Date_Start = 20240101   # "{}" Début du Time Period sur GCGEO (000183ed-8864-42f0-ae43-c4313a860720) (AAAA-MM-JJ)
- Date_End = 20241231   # "{}" Fin time Period sur GCGEO (000183ed-8864-42f0-ae43-c4313a860720) (AAAA-MM-JJ)

Creator
    GEOMTYPE = Geometry Object
    NUM = 1
    CREATED -> FeatureReader_2 [INITIATOR]
    CREATED -> DateTimeStamper
    CREATED -> AttributeCreator_11
    CREATED -> FeatureReader [INITIATOR]
    CREATED -> Create_message_1 [Communication_Thread]
Note: FeatureReader : <Rejected>
Junction_2
    -> Create_message_3
FeatureReader_2
    ATTRIBUTES = MetalWorks,"OBJECTID,count,operation_group_en,operation_group_fr,province_en,province_fr,operation_en,operation_fr,operator_owners_en,operator_owners_fr,facilities_code_en_spelt,facilities_code_fr_spelt,product_group_en_spelt,product_group_fr_spelt,product_en_spelt,product_fr_spelt,latitude,longitude",OilAndGas,"OBJECTID,id,province_en,province_fr,province_nb,operation_en,operation_fr,product_en,product_fr,type_en,type_fr,latitude,longitude",ProducingMines,"OBJECTID,count,operation_group_en,operation_group_fr,operation_nb,province_abr,province_en,province_fr,province_nb,operation_name_en,operation_name_fr,operator_owners_en,operator_owners_fr,facilities_code_en_spelt,facilities_code_fr_spelt,city_en,city_fr,product_group_en_spelt,product_group_fr_spelt,product_en_spelt,product_fr_spelt,latitude,longitude,website",Top100Exp,"OBJECTID,count,project_name,province_en,province_fr,commodity_group_en,commodity_group_fr,latitude,longitude"
    ATTR_ACCUM_MODE = Only Use Result
    COMBINE_GEOM = Use Result
    DATASET = https://ftp.maps.canada.ca/pub/nrcan_rncan/Mining-industry_Industrie-miniere/900A_and_top_100/900A.gdb.zip
    FILEGDB_QUERY_FEATURE_TYPES_FOR_MERGE_FILTERS = Yes
    FILEGDB_SIMPLE_DONUT_GEOMETRY = simple
    FILEGDB_STRIP_GUID_GLOBALID_BRACES = no
    FILEGDB_USE_SEARCH_ENVELOPE = NO
    FORMAT = FILEGDB
    INTERACT = <No Spatial Filter>
    OUTPUT_FEATURES_DISPLAY = Schema and Data Features
    SELECTED_PORTS = MetalWorks OilAndGas ProducingMines
    MetalWorks -> AttributeCreator_10
    OilAndGas -> AttributeCreator
    ProducingMines -> AttributeCreator_28
    <REJECTED> -> Terminator
    <REJECTED> -> Create_message_1
FeatureHolder_2
    -> AttributeRemover_2
NullAttributeMapper
    ATTRCHOICE = All Attributes
    NULL_TREATMENT = Missing
    SOURCE_ATTR_VAL = Null
    -> AttributeCreator_2
Note: FeatureMerger : <Rejected>
Junction_4
    -> Create_message_2
FeatureHolder
    -> DuplicateFilter
VariableRetriever_2
    SCOPE = Global
    VALUE_ATTR = _datestamp
    VARNAME = DateStamp
    -> VariableRetriever_3
VariableRetriever_3
    SCOPE = Global
    VALUE_ATTR = RecordKeeper.LastSyncTS
    VARNAME = DateLastSync
    -> FeatureWriter [Output]
FeatureWriter
    CSV2_DELIMITER = ,
    CSV2_ENCODING = utf-8
    CSV2_EXISTING_FILE_HANDLING = Yes
    CSV2_FIELD_QUALIFIER_CHARACTER = "
    CSV2_FIELD_QUALIFIER_ESCAPE_CHARACTER = "
    CSV2_QUALIFY_FIELD_NAMES = yes
    CSV2_QUALIFY_FIELD_VALUES = yes
    CSV2_ROW_TERMINATION = System
    CSV2_WRITE_BOM_FOR_UNICODE = Yes
    CSV2_WRITE_FIELD_NAMES = firstrow
    CSV2_WRITE_SCHEMA_FILE = NO
    DATASET = $(FME_SHAREDRESOURCE_DATA)\DDR\Conditioning_Data\900A_OSDP\GeoDCAT
    DATASET_ATTR = _dataset
    FEATURE_TYPE_LIST_ATTR = _feature_type
    FORMAT = CSV2
    MORE_SUMMARY_ATTRS = _datestamp
    TOTAL_FEATURES_WRITTEN_ATTR = _total_features_written
    SUMMARY -> Execute_Python_3.7_Library
Note: Copier dernier fichier 900A
Execute_Python_3.7_Library: 7_Library
    EXECUTION_TRACE = +Execute_Python_fileCopy
    Execution_Parameters:
      [
      {"parametersAreAttributeNames":False},
      {
        "source":"$(FME_SHAREDRESOURCE_DATA)\DDR\Conditioning_Data\900A_OSDP\GeoDCAT\NRCAN-MINING-@Value(_feature_type{0}._datestamp).csv",
        "destination":"$(FME_SHAREDRESOURCE_DATA)\DDR\Conditioning_Data\900A_OSDP\last_900A_file.csv"
      },
      ]
    Function_Name = fileCopy
    -> AttributeExposer_2
    Communication_Thread -> Create_message_10b
AttributeExposer_2
    ATTR_LIST = ddr_iam_role,osdp_bucket_owner_id,S3_file_upload.iam_role,S3_file_upload.bucket_owner_id,_feature_type{0}._datestamp
    -> AttributeCreator_13
Terminator
    MESSAGE:
      Translation Terminated

      Lecture du fichier source a échouée
Create_message_1: Create message
    EXECUTION_TRACE = +Create_message_1
    EnMessage = 900A datasource is not reachable
    FrMessage = Problème avec le fichier source 900A
    MessageType = ADMIN
    Severity = FATAL
    Communication_Thread -> Create_message_3 [Communication_Thread]
Create_message_3: Create message
    EXECUTION_TRACE = +Create_message_2
    EnMessage = 900A existing file is not reachable
    FrMessage = Problème d'accès avec le fichier 900A existant pour comparaison
    MessageType = ADMIN
    Severity = FATAL
    Communication_Thread -> Create_message_2 [Communication_Thread]
Create_message_2: Create message
    EXECUTION_TRACE = +Create_message_3
    EnMessage = problem merging the existing content with the current.
    FrMessage = problème avec la comparaison du fichier 900A existant et le nouveau contenu.
    MessageType = ADMIN
    Severity = FATAL
    Communication_Thread -> Create_message_4 [Communication_Thread]
Create_message_4: Create message
    EXECUTION_TRACE = +Create_message_2
    EnMessage = @DateTimeFormat(@round(@DateTimeNow(),0), %Y-%m-%d %H:%M:%S) -> Record rejected when validating the update/delete
    FrMessage = @DateTimeFormat(@round(@DateTimeNow(),0), %Y-%m-%d %H:%M:%S) -> Enregistrement rejeté lors de la validation des ID effacés
    MessageType = ADMIN
    Severity = WARNING
    Communication_Thread -> Create_message_10b [Communication_Thread]
Create_message_10b: Create message
    EXECUTION_TRACE = +Create_message_10b
    EnMessage = @DateTimeFormat(@round(@DateTimeNow(),0), %Y-%m-%d %H:%M:%S) -> The geoDCAT file copy (last_900A_file.csv) has failed.
    FrMessage = @DateTimeFormat(@round(@DateTimeNow(),0), %Y-%m-%d %H:%M:%S) -> La copie du fichier geoDCAT (last_900A_file.csv) a échoué.
    MessageType = USER
    Severity = FATAL
    Communication_Thread -> Create_message_10f [Communication_Thread]
Create_message_10f: Create message
    EXECUTION_TRACE = +Create_message_10f
    EnMessage = The geoDCAT file NRCAN-MINING-@Value(_feature_type{0}._datestamp).csv transfer to the OSDP servers has failed.
    FrMessage = Le transfert du fichier geoDCAT NRCAN-MINING-@Value(_feature_type{0}._datestamp).csv sur le serveur du PSDO a échoué.
    MessageType = USER
    Severity = FATAL
    Communication_Thread -> Create_message_10f_2 [Communication_Thread]
Create_message_10f_2: Create message
    EXECUTION_TRACE = +Create_message_10f
    EnMessage = The geoDCAT file NRCAN-MINING-@Value(_feature_type{0}._datestamp).csv transfer to the OSDP servers was a success.
    FrMessage = Le transfert du fichier geoDCAT NRCAN-MINING-@Value(_feature_type{0}._datestamp).csv sur le serveur du PSDO est un succès.
    MessageType = USER
    Severity = INFO
    Communication_Thread -> Messages [Communication]
Messages
    EXECUTION_TRACE = $(WORKSPACE_NAME)+Messages

Bookmark: Lire Last_900A_File (pas les deleted records)
FeatureReader
    ATTRIBUTES = CSV,"Action,""Record Type"",""Contributor System"",""Contributor Org"",""Content Category"",""Publisher (EN)"",""Publisher (FR)"",PublishedFor,""Creator (EN)"",""Creator (FR)"",""Subject Area"",""Subject Topic"",Identifier.Bundle,Identifier.Artifact,""Identifier.Artifact (DOI)"",Identifier.Child,""Title (EN)"",""Title (FR)"",""Description (EN)"",""Description (FR)"",""Keywords (EN)"",""Keywords (FR)"",Date.LastUpdate,Date.Published,Date.Start,Date.End,Coverage.Geometry,Coverage.ProvinceCd,""Coverage.Placename (EN)"",""Coverage.Placename (FR)"",Coverage.Country,Coverage.Region,External.DatasetCategory,External.ProjectCategory,Rights.License,Rights.Disposition,UpdateFrequency,RecordKeeper.Organization,RecordKeeper.System,RecordKeeper.LastUserToModify,RecordKeeper.LastSyncTS,""Citation Total"",Citation.Format[1],""Citation.Value (EN)[1]"",""Citation.Value (FR)[1]"",""Note Total"",Note.Type[1],""Note.Title (EN)[1]"",""Note.Title (FR)[1]"",""Note.Desc (EN)[1]"",""Note.Desc (FR)[1]"",""Resource Total"",Resource.Type[1],Resource.Format[1],Resource.ServiceProtocol[1],Resource.Language[1],""Resource.Name (EN)[1]"",""Resource.Name (FR)[1]"",""Resource.URL (EN)[1]"",""Resource.URL (FR)[1]"",Resource.Type[2],Resource.Format[2],Resource.ServiceProtocol[2],Resource.Language[2],""Resource.Name (EN)[2]"",""Resource.Name (FR)[2]"",""Resource.URL (EN)[2]"",""Resource.URL (FR)[2]"",Resource.Type[3],Resource.Format[3],Resource.ServiceProtocol[3],Resource.Language[3],""Resource.Name (EN)[3]"",""Resource.Name (FR)[3]"",""Resource.URL (EN)[3]"",""Resource.URL (FR)[3]"",Resource.Type[4],Resource.Format[4],Resource.ServiceProtocol[4],Resource.Language[4],""Resource.Name (EN)[4]"",""Resource.Name (FR)[4]"",""Resource.URL (EN)[4]"",""Resource.URL (FR)[4]"""
    ATTR_ACCUM_MODE = Only Use Result
    COMBINE_GEOM = Use Result
    CSV2_CASE_SENSITIVE_FIELD_NAMES = Yes
    CSV2_DATA_START_LINE = 2
    CSV2_DELIMITER = ,
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 10000
    CSV2_SCAN_TYPES = Yes
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = $(Last_900A_file)
    FORMAT = CSV2
    INTERACT = <No Spatial Filter>
    OUTPUT_FEATURES_DISPLAY = Schema and Data Features
    SELECTED_PORTS = CSV
    CSV -> Tester_2
    <REJECTED> -> Terminator_4
    <REJECTED> -> Junction
Note: GARDE SEULEMENT ACTIVE RECORDS
Tester_2
    BOOL_OP = OR
    COMPOSITE_TEST = 1
    TEST_CLAUSE = TEST @Value(Action) = U
    TEST_MODE = TEST
    PASSED -> FeatureMerger [REQUESTOR]
Terminator_4
    MESSAGE:
      Translation Terminated

      Lecture du fichier existant a plantée
Note: Create_message_3 : Input
Junction
    -> Junction_2

Bookmark: CRÉATION VARIABLE POUR DATE DE TRAITEMENT ET DATE DU TIMESTAMP DE LA MÉTADONNÉE
DateTimeStamper
    DATETIME_ATTR = _date
    INCLUDE_OFFSET = NO
    STAMP_TYPE = datetime
    TIMEZONE = utc
    -> SubstringExtractor_4
Note: Enlever fractions de secondes
SubstringExtractor_4
    END = 13
    RESULT_ATTR = _datetime
    SRC_STRING = @Value(_date)
    START = 0
    -> DateTimeConverter
    -> DateTimeConverter_4
DateTimeConverter_4
    DATETIME_ATTR = _datetime
    OUT_FORMAT = %Y%m%d%H%M%SZ
    PASSTHROUGH = NO
    REPAIR_INPUT = YES
    -> VariableSetter_3
Note: Date traitement pour nom du fichier
VariableSetter_3
    SCOPE = Global
    VALUE = @Value(_datetime)
    VARNAME = DateStamp
DateTimeConverter
    DATETIME_ATTR = _datetime
    OUT_FORMAT = %Y-%m-%dT%H:%M:%SZ
    PASSTHROUGH = NO
    REPAIR_INPUT = YES
    -> VariableSetter
Note: Date traitement pour / RecordKeeper.LastSyncTS
VariableSetter
    SCOPE = Global
    VALUE = @Value(_datetime)
    VARNAME = DateLastSync
AttributeCreator_11
    ATTR_TABLE = SET_TO Date_LastUpdate = $(Date_Last_Update)
    -> DateTimeConverter_2
DateTimeConverter_2
    DATETIME_ATTR = Date_LastUpdate
    OUT_FORMAT = %Y-%m-%dT%H:%M:%SZ
    PASSTHROUGH = NO
    REPAIR_INPUT = YES
    -> VariableSetter_2

Bookmark: Major Group
AttributeCreator_10
    ATTR_TABLE:
      SET_TO Major_Group (EN) = Metallurgical Works
      SET_TO Major_Group (FR) = Activités métallurgiques
    -> FeatureHolder_2
AttributeCreator
    ATTR_TABLE:
      SET_TO Major_Group (EN) = Oil And Gas
      SET_TO Major_Group (FR) = Pétrole et Gaz
    -> FeatureHolder_2
AttributeCreator_28
    ATTR_TABLE:
      SET_TO Major_Group (EN) = Producing Mines
      SET_TO Major_Group (FR) = Production Minière
    -> FeatureHolder_2

Bookmark: Ménage des attributs non utilisés
AttributeRemover_2
    REMOVE_ATTRS = count,OBJECTID,province_nb,id
    -> AttributeRounder

Bookmark: arrondir lat/long 3 décimales
AttributeRounder
    PLACES = 3
    ROUND_TYPE = Nearest
    SRC_ATTRS = latitude longitude
    -> NullAttributeMapper

Bookmark: ATTRIBUTS SIMPLES
AttributeCreator_2
    ATTR_TABLE:
      SET_TO Action = U
      SET_TO Record Type = 1
      SET_TO Contributor System = NRCAN-MINING
      SET_TO Contributor Org = GC:NRCan-RNCan
      SET_TO Content Category = Project
      SET_TO PublishedFor = Author
      SET_TO Subject Area = Economy & Industry
      SET_TO Rights.License = GC-OpenData
      SET_TO Rights.Disposition = Open
      SET_TO UpdateFrequency = P1Y
      SET_TO RecordKeeper.Organization = GC:NRCan-RNCan
      SET_TO RecordKeeper.System = NRCAN-OSDP
      SET_TO RecordKeeper.LastUserToModify = OSDP.NRCAN-MINING.Project
      SET_TO Resource.Type[1] = Dataset
      SET_TO Resource.Format[1] = HTML
      SET_TO Resource.ServiceProtocol[1] = HTTPS
      SET_TO Resource.Language[1] = eng; fre
      SET_TO Resource.Name (EN)[1] = Principal Mineral Areas, Producing Mines, and Oil and Gas Fields (900A)
      SET_TO Resource.Name (FR)[1] = Principales régions minières, principales mines productrices, principaux champs de pétrole et de gaz (900A)
      SET_TO Resource.URL (EN)[1] = https://osdp-psdo.canada.ca/dp/en/search/metadata/NRCAN-FGP-1-000183ed-8864-42f0-ae43-c4313a860720
      SET_TO Resource.URL (FR)[1] = https://osdp-psdo.canada.ca/dp/fr/recherche/metadonnees/NRCAN-FGP-1-000183ed-8864-42f0-ae43-c4313a860720
      SET_TO Resource.Type[2] = Supporting Document
      SET_TO Resource.Format[2] = PDF
      SET_TO Resource.ServiceProtocol[2] = HTTPS
      SET_TO Resource.Language[2] = eng; fre
      SET_TO Resource.Name (EN)[2] = Principal Mineral Areas, Producing Mines, and Oil and Gas Fields (900A)
      SET_TO Resource.Name (FR)[2] = Principales régions minières, principales mines productrices, principaux champs de pétrole et de gaz (900A)
      SET_TO Resource.URL (EN)[2] = https://ftp.maps.canada.ca/pub/nrcan_rncan/Mining-industry_Industrie-miniere/900A_and_top_100/PDF/EN/
      SET_TO Resource.URL (FR)[2] = https://ftp.maps.canada.ca/pub/nrcan_rncan/Mining-industry_Industrie-miniere/900A_and_top_100/PDF/FR/
      SET_TO Creator (EN) = Government of Canada, Natural Resources Canada, Lands and Minerals Sector
      SET_TO Creator (FR) = Gouvernement du Canada, Ressources naturelles Canada, Secteur des terres et des minéraux
      SET_TO Resource Total = 4
      SET_TO Date.Published = $(Date_Published)
      SET_TO Date.Start = $(Date_Start)
      SET_TO Date.End = $(Date_End)
      SET_TO Coverage.Geometry = FME_CONDITIONAL:DEFAULT_VALUE'POINT(@Value(longitude) @Value(latitude))'BOOL_OP;OR;COMPOSITE_TEST;1 OR 2;CASE_INSENSITIVE_TEST @Value(latitude) CONTAINS no_value;CASE_INSENSITIVE_TEST @Value(longitude) CONTAINS no_value''FME_NUM_CONDITIONS2___
      SET_TO Identifier.Bundle = FME_NULL_VALUE
      SET_TO Identifier.Artifact (DOI) = FME_NULL_VALUE
      SET_TO Identifier.Child = FME_NULL_VALUE
      SET_TO Coverage.Placename (EN) = FME_CONDITIONAL:DEFAULT_VALUE'@Value(operation_en), @Value(province_en)'BOOL_OP;AND;COMPOSITE_TEST;1 AND 2;TEST @Value(Major_Group (EN)) = Producing Mines;TEST @Value(operation_name_en) = @Value(city_en)'@Value(operation_name_en), @Value(province_en)'BOOL_OP;AND;COMPOSITE_TEST;1 AND 2;TEST @Value(Major_Group (EN)) = Producing Mines;TEST @Value(operation_name_en) != @Value(city_en)'@Value(operation_name_en), @Value(city_en), @Value(province_en)'FME_NUM_CONDITIONS3___
      SET_TO Coverage.Placename (FR) = FME_CONDITIONAL:DEFAULT_VALUE'@Value(operation_fr), @Value(province_fr)'BOOL_OP;AND;COMPOSITE_TEST;1 AND 2;TEST @Value(Major_Group (EN)) = Producing Mines;TEST @Value(operation_name_en) = @Value(city_en)'@Value(operation_name_fr), @Value(province_fr)'BOOL_OP;AND;COMPOSITE_TEST;1 AND 2;TEST @Value(Major_Group (EN)) = Producing Mines;TEST @Value(operation_name_en) != @Value(city_en)'@Value(operation_name_fr), @Value(city_fr), @Value(province_fr)'FME_NUM_CONDITIONS3___
      SET_TO Coverage.Country = CA
      SET_TO Coverage.Region = FME_NULL_VALUE
      SET_TO External.DatasetCategory = FME_NULL_VALUE
      SET_TO External.ProjectCategory = FME_NULL_VALUE
      SET_TO Coverage.ProvinceCd = @Value(province_abr)
      SET_TO Publisher (EN) = Natural Resources Canada
      SET_TO Publisher (FR) = Ressources naturelles Canada
      SET_TO Resource.Type[3] = Website
      SET_TO Resource.Format[3] = HTML
      SET_TO Resource.ServiceProtocol[3] = HTTPS
      SET_TO Resource.Language[3] = eng; fre
      SET_TO Resource.Name (EN)[3] = Minerals and mining
      SET_TO Resource.Name (FR)[3] = Minéraux et exploitation minière
      SET_TO Resource.URL (EN)[3] = https://natural-resources.canada.ca/minerals-mining
      SET_TO Resource.URL (FR)[3] = https://ressources-naturelles.canada.ca/nos-ressources-naturelles/mines-materiaux/10684
      SET_TO Resource.Type[4] = Website
      SET_TO Resource.Format[4] = HTML
      SET_TO Resource.ServiceProtocol[4] = HTTPS
      SET_TO Resource.Language[4] = eng; fre
      SET_TO Resource.Name (EN)[4] = Mining data, statistics and analysis
      SET_TO Resource.Name (FR)[4] = Données, statistiques et analyses sur l’exploitation minière
      SET_TO Resource.URL (EN)[4] = https://natural-resources.canada.ca/minerals-mining/mining-data-statistics-and-analysis/25093
      SET_TO Resource.URL (FR)[4] = https://ressources-naturelles.canada.ca/nos-ressources-naturelles/mines-materiaux/donnees-statistiques-et-analyses-sur-lexploitation-miniere/25096
      SET_TO Note Total = 1
      SET_TO Note.Type[1] = NOTE
      SET_TO Note.Title (EN)[1] = Note
      SET_TO Note.Title (FR)[1] = Note
      SET_TO Note.Desc (EN)[1] = The (bracketed) content in the Title refers to the location of this record in the dataset layer's hierarchy.
      SET_TO Note.Desc (FR)[1] = Le contenu (entre crochets) dans le titre fait référence à l'emplacement de cet enregistrement dans la hiérarchie de la couche de jeu de données.
    -> DateTimeConverter_3

Bookmark: gestion format des dates
DateTimeConverter_3
    DATETIME_ATTR = Date.Published
    OUT_FORMAT = %Y-%m-%d
    PASSTHROUGH = NO
    REPAIR_INPUT = YES
    -> DateTimeConverter_5
DateTimeConverter_5
    DATETIME_ATTR = Date.Start
    OUT_FORMAT = %Y-%m-%d
    PASSTHROUGH = NO
    REPAIR_INPUT = YES
    -> DateTimeConverter_8
DateTimeConverter_8
    DATETIME_ATTR = Date.End
    OUT_FORMAT = %Y-%m-%d
    PASSTHROUGH = NO
    REPAIR_INPUT = YES
    -> PythonCaller_2

Bookmark: Coverage.ProvinceCd
Note: Abréviations / Provinces
PythonCaller_2
    NEW_ATTRIBUTES = "Coverage.ProvinceCd "
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              PT={}
              PT['Alberta']='AB'
              PT['British Columbia']='BC'
              PT['Manitoba']='MB'
              PT['Nova Scotia']='NS'
              PT['New Brunswick']='NB'
              PT['Newfoundland and Labrador']='NL'
              PT['Northwest Territories']='NT'
              PT['Ontario']='ON'
              PT['Saskatchewan']='SK'
              PT['Quebec']='QC'
              PT['Nunavut']='NU'
              PT['Yukon']='YT'
              PT['Prince Edward Island']='PE'

              for keys in PT:
                  if keys in feature.getAttribute('province_en'):
                      feature.setAttribute('Coverage.ProvinceCd',feature.getAttribute('province_en').replace(keys,PT[keys]))



              self.pyoutput(feature)
          def close(self):
              pass
    PYTHONSYMBOL = FeatureProcessor
    -> AttributeCreator_8

Bookmark: KEYWORDS
AttributeCreator_8
    ATTR_TABLE:
      SET_TO Keywords (EN) = FME_CONDITIONAL:DEFAULT_VALUE'@Value(Major_Group (EN)); @Value(operation_group_en); @Value(operator_owners_en)'BOOL_OP;OR;COMPOSITE_TEST;1;TEST @Value(Major_Group (EN)) = Oil And Gas'@Value(Major_Group (EN)); @Value(product_en)'BOOL_OP;OR;COMPOSITE_TEST;1;TEST @Value(Major_Group (EN)) = Producing Mines'@Value(Major_Group (EN)); @Value(operation_group_en); @Value(operator_owners_en); @Value(facilities_code_en_spelt); @Value(product_group_en_spelt); @Value(product_en_spelt)'BOOL_OP;AND;COMPOSITE_TEST;1 AND 2;TEST @Value(Major_Group (EN)) = Metallurgical Works;TEST @Value(facilities_code_en_spelt) != N/A'@Value(Major_Group (EN)); @Value(operation_group_en); @Value(operator_owners_en); @Value(facilities_code_en_spelt); @Value(product_group_en_spelt); @Value(product_en_spelt)'FME_NUM_CONDITIONS4___
      SET_TO Keywords (FR) = FME_CONDITIONAL:DEFAULT_VALUE'@Value(Major_Group (FR)); @Value(operation_group_fr); @Value(operator_owners_fr)'BOOL_OP;OR;COMPOSITE_TEST;1;TEST @Value(Major_Group (EN)) = Oil And Gas'@Value(Major_Group (FR)); @Value(product_fr)'BOOL_OP;OR;COMPOSITE_TEST;1;TEST @Value(Major_Group (EN)) = Producing Mines'@Value(Major_Group (FR)); @Value(operation_group_fr); @Value(operator_owners_fr); @Value(facilities_code_fr_spelt); @Value(product_group_fr_spelt); @Value(product_fr_spelt)'BOOL_OP;AND;COMPOSITE_TEST;1 AND 2;TEST @Value(Major_Group (EN)) = Metallurgical Works;TEST @Value(facilities_code_en_spelt) != N/A'@Value(Major_Group (FR)); @Value(operation_group_fr); @Value(operator_owners_fr); @Value(facilities_code_fr_spelt); @Value(product_group_fr_spelt); @Value(product_fr_spelt)'FME_NUM_CONDITIONS4___
    -> AttributeCreator_31

Bookmark: TITLE
Note: GÉNÉRATION / SECTIONS
AttributeCreator_31
    ATTR_TABLE:
      SET_TO Title_prefix(EN) = Mining Activity:
      SET_TO Title_prefix(FR) = Activité minière :
      SET_TO Title_location(EN) = FME_CONDITIONAL:DEFAULT_VALUE'@Value(operation_en), @Value(province_en)'BOOL_OP;AND;COMPOSITE_TEST;1 AND 2;TEST @Value(Major_Group (EN)) = Producing Mines;TEST @Value(operation_name_en) = @Value(city_en)'@Value(operation_name_en), @Value(province_en)'BOOL_OP;AND;COMPOSITE_TEST;1 AND 2;TEST @Value(Major_Group (EN)) = Producing Mines;TEST @Value(operation_name_en) != @Value(city_en)'@Value(operation_name_en), @Value(city_en), @Value(province_en)'FME_NUM_CONDITIONS3___
      SET_TO Title_location(FR) = FME_CONDITIONAL:DEFAULT_VALUE'@Value(operation_fr), @Value(province_fr)'BOOL_OP;AND;COMPOSITE_TEST;1 AND 2;TEST @Value(Major_Group (EN)) = Producing Mines;TEST @Value(operation_name_en) = @Value(city_en)'@Value(operation_name_fr), @Value(province_fr)'BOOL_OP;AND;COMPOSITE_TEST;1 AND 2;TEST @Value(Major_Group (EN)) = Producing Mines;TEST @Value(operation_name_en) != @Value(city_en)'@Value(operation_name_fr), @Value(city_fr), @Value(province_fr)'FME_NUM_CONDITIONS3___
      SET_TO Title_type_part(EN) = FME_CONDITIONAL:DEFAULT_VALUE'@Value(Major_Group (EN)) > @Value(operation_group_en) > @Value(product_group_en_spelt)'BOOL_OP;OR;COMPOSITE_TEST;1;TEST @Value(Major_Group (EN)) = Oil And Gas'@Value(Major_Group (EN)) > @Value(product_en)'BOOL_OP;AND;COMPOSITE_TEST;1 AND 2;TEST @Value(Major_Group (EN)) != Oil And Gas;TEST @Value(product_group_en_spelt) = N/A'@Value(Major_Group (EN)) > @Value(operation_group_en)'FME_NUM_CONDITIONS3___
      SET_TO Title_type_part(FR) = FME_CONDITIONAL:DEFAULT_VALUE'@Value(Major_Group (FR)) > @Value(operation_group_fr) > @Value(product_group_fr_spelt)'BOOL_OP;OR;COMPOSITE_TEST;1;TEST @Value(Major_Group (EN)) = Oil And Gas'@Value(Major_Group (FR)) > @Value(product_fr)'BOOL_OP;AND;COMPOSITE_TEST;1 AND 2;TEST @Value(Major_Group (EN)) != Oil And Gas;TEST @Value(product_group_en_spelt) = N/A'@Value(Major_Group (FR)) > @Value(operation_group_fr)'FME_NUM_CONDITIONS3___
    -> AttributeCreator_32
AttributeCreator_32
    ATTR_TABLE:
      SET_TO Title (EN) = @Value(Title_prefix(EN)) @Value(Title_location(EN)) (@Value(Title_type_part(EN)))
      SET_TO Title (FR) = @Value(Title_prefix(FR)) @Value(Title_location(FR)) (@Value(Title_type_part(FR)))
    -> AttributeRemover
AttributeRemover
    REMOVE_ATTRS = Title_location(EN),Title_location(FR),Title_prefix(EN),Title_prefix(FR),Title_type_part(EN),Title_type_part(FR)
    -> StringConcatenator

Bookmark: UUID
StringConcatenator
    ACTION = Create New Attribute
    PARM_LINE = fme_basicstring:18%25:@Value(Title (EN))@Value(Coverage.Geometry)
    VAL_ATTR = 900A_UUID_string
    -> AttributeValueMapper
AttributeValueMapper
    DIRECTION = Forward (Source To Destination)
    LUT =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
    SRC = 900A_UUID_string
    VAL_ATTR = Identifier.Artifact
    -> Tester
Tester
    BOOL_OP = OR
    COMPOSITE_TEST = 1
    TEST_CLAUSE = TEST Identifier.Artifact ATTRIBUTE_HAS_A_VALUE ""
    TEST_MODE = TEST
    PASSED -> AttributeCreator_30
    FAILED -> UNIQUE_ID_CREATOR
UNIQUE_ID_CREATOR
    UNIQUE_ATT = @Value(900A_UUID_string)
    -> AttributeCreator_14
AttributeCreator_14
    ATTR_TABLE = SET_TO Identifier.Artifact = @Value(id)
    -> AttributeCreator_30

Bookmark: CITATIONS
AttributeCreator_30
    ATTR_TABLE:
      SET_TO _citationDate_en = @Value(Date.Published)
      SET_TO _citationDate_fr = @Value(Date.Published)
    -> DateTimeConverter_6
DateTimeConverter_6
    DATETIME_ATTR = _citationDate_en
    OUT_FORMAT = %Y, %B %e
    PASSTHROUGH = NO
    REPAIR_INPUT = YES
    -> DateTimeConverter_7
    <REJECTED> -> Terminator_2
DateTimeConverter_7
    DATETIME_ATTR = _citationDate_fr
    OUT_FORMAT = %Y, %e %B
    PASSTHROUGH = NO
    REPAIR_INPUT = YES
    -> PythonCaller_3
    <REJECTED> -> Terminator_2
PythonCaller_3
    NEW_ATTRIBUTES = _citationDate_fr _error_date
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              mois={}
              mois['January']='janvier'
              mois['February']='février'
              mois['March']='mars'
              mois['April']='avril'
              mois['May']='mai'
              mois['June']='juin'
              mois['July']='juillet'
              mois['August']='août'
              mois['September']='septembre'
              mois['October']='octobre'
              mois['November']='novembre'
              mois['December']='décembre'

              fr=False
              for keys in mois:
                  if keys in feature.getAttribute('_citationDate_fr'):
                      feature.setAttribute('_citationDate_fr',feature.getAttribute('_citationDate_fr').replace(keys,mois[keys]))
                      fr=True

              if not fr:
                  feature.setAttribute('_error_date','Impossible de mapper la date %s en français'%(feature.getAttribute('_citationDate_fr')))


              self.pyoutput(feature)
          def close(self):
              pass
    PYTHONSYMBOL = FeatureProcessor
    -> Tester_4
Tester_4
    BOOL_OP = OR
    COMPOSITE_TEST = 1
    TEST_CLAUSE = TEST @Value(_error_date) = ""
    TEST_MODE = TEST
    PASSED -> AttributeCreator_29
    FAILED -> Terminator_3
AttributeCreator_29
    ATTR_TABLE:
      SET_TO Citation.Value (EN)[1] = @Value(Creator (EN)). (@Value(_citationDate_en)). @Value(Title (EN)). @Value(Publisher (EN)). https://osdp-psdo.canada.ca/dp/en/search/metadata/NRCAN-MINING-1-@Value(Identifier.Artifact)
      SET_TO Citation.Value (FR)[1] = @Value(Creator (FR)). (@Value(_citationDate_fr)). @Value(Title (FR)). @Value(Publisher (FR)). https://osdp-psdo.canada.ca/dp/fr/recherche/metadonnees/NRCAN-MINING-1-@Value(Identifier.Artifact)
      SET_TO Citation Total = 1
      SET_TO Citation.Format[1] = APA
    -> AttributeRemover_3
AttributeRemover_3
    REMOVE_ATTRS = _citationDate_en,_citationDate_fr,_error_date
    -> AttributeCreator_3
Terminator_3
    MESSAGE = @Value(_error_date)
Terminator_2
    MESSAGE = Problème avec la gestion des dates pour les citations/références

Bookmark: SUBJECT TOPIC
Note: GÉNÉRATION / SECTIONS
AttributeCreator_3
    ATTR_TABLE:
      SET_TO SubTop_AllRec = Resource Development; Commodities;
      SET_TO SubTop_Petrol = FME_CONDITIONAL:DEFAULT_VALUE'_FME_NO_OP_'BOOL_OP;OR;COMPOSITE_TEST;1 OR 2 OR 3 OR 4;TEST @Value(Major_Group (EN)) = Oil And Gas;CASE_INSENSITIVE_TEST @Value(product_en) CONTAINS Oil;CASE_INSENSITIVE_TEST @Value(product_en) CONTAINS Gas;CASE_INSENSITIVE_TEST @Value(product_group_en_spelt) CONTAINS Oil'Petroleum Industry; 'FME_NUM_CONDITIONS2___
      SET_TO SubTop_OperGroup = FME_CONDITIONAL:DEFAULT_VALUE'_FME_NO_OP_'BOOL_OP;OR;COMPOSITE_TEST;1;TEST @Value(operation_group_en) = Oil sands mine'Oil Sands; 'BOOL_OP;OR;COMPOSITE_TEST;1;TEST @Value(operation_group_en) = Coal mines'Coal; 'FME_NUM_CONDITIONS3___
      SET_TO SubTop_Mines = FME_CONDITIONAL:DEFAULT_VALUE'_FME_NO_OP_'BOOL_OP;OR;COMPOSITE_TEST;1 OR 2;TEST @Value(Major_Group (EN)) = Producing Mines;TEST @Value(Major_Group (EN)) = Metallurgical Works'Mining Industry; Mineralogy; 'FME_NUM_CONDITIONS2___
      SET_TO SubTop_Facility = FME_CONDITIONAL:DEFAULT_VALUE'_FME_NO_OP_'BOOL_OP;OR;COMPOSITE_TEST;1;CASE_INSENSITIVE_TEST @Value(facilities_code_en_spelt) CONTAINS Open-pit'Strip Mining; 'BOOL_OP;OR;COMPOSITE_TEST;1;CASE_INSENSITIVE_TEST @Value(product_group_en_spelt) CONTAINS Uranium'Radioactive Minerals; Nuclear Energy; 'BOOL_OP;OR;COMPOSITE_TEST;1;CASE_INSENSITIVE_TEST @Value(product_group_en_spelt) CONTAINS Industrial minerals'Industrial Minerals; 'FME_NUM_CONDITIONS4___
      SET_TO SubTop_MajGroupfin = FME_CONDITIONAL:DEFAULT_VALUE'_FME_NO_OP_'BOOL_OP;OR;COMPOSITE_TEST;1;TEST @Value(Major_Group (EN)) = Producing Mines'Extraction; 'BOOL_OP;OR;COMPOSITE_TEST;1;TEST @Value(Major_Group (EN)) = Metallurgical Works'Refining Processes; 'FME_NUM_CONDITIONS3___
    -> AttributeCreator_4
AttributeCreator_4
    ATTR_TABLE = SET_TO Subject Topic = @Value(SubTop_AllRec)@Value(SubTop_Petrol)@Value(SubTop_OperGroup)@Value(SubTop_Mines)@Value(SubTop_Facility)@Value(SubTop_MajGroupfin)
    -> AttributeTrimmer
AttributeTrimmer
    SRC_ATTRS = "Subject Topic"
    TRIM_CHARS = "; "
    TRIM_TO_NONE = Yes
    TRIM_TYPE = Right
    -> AttributeRemover_4
AttributeRemover_4
    REMOVE_ATTRS = SubTop_AllRec,SubTop_Facility,SubTop_MajGroupfin,SubTop_Mines,SubTop_OperGroup,SubTop_Petrol
    -> attr_creator_eng

Bookmark: DESCRIPTIONS
Note: SECTIONS / ANGLAIS
attr_creator_eng: AttributeCreator
    ATTR_TABLE:
      SET_TO Desc_product_en = FME_CONDITIONAL:DEFAULT_VALUE'_FME_NO_OP_'BOOL_OP;OR;COMPOSITE_TEST;1;TEST product_en ATTRIBUTE_HAS_A_VALUE _FME_BLANK_STRING_'Product: @Value(product_en)'BOOL_OP;AND;COMPOSITE_TEST;1 AND 2;TEST product_en_spelt ATTRIBUTE_HAS_A_VALUE _FME_BLANK_STRING_;TEST @Value(product_en_spelt) != N/A'Product: @Value(product_en_spelt)'FME_NUM_CONDITIONS3___
      SET_TO Desc_product_type_en = FME_CONDITIONAL:DEFAULT_VALUE'_FME_NO_OP_'BOOL_OP;OR;COMPOSITE_TEST;1;TEST @Value(product_en) = Oil'Product Type : Oil'BOOL_OP;OR;COMPOSITE_TEST;1 OR 2;TEST @Value(product_en) = Gas;TEST @Value(product_en) = Gas, sulfur'Product Type: Gas'BOOL_OP;OR;COMPOSITE_TEST;1;TEST @Value(product_en) = Bitumen'Product Type: Bitumen'BOOL_OP;OR;COMPOSITE_TEST;1 OR 2;CASE_INSENSITIVE_TEST @Value(product_en) CONTAINS Oil, gas;CASE_INSENSITIVE_TEST @Value(product_en) CONTAINS Gas, oil'Product Type: Oil and Gas'FME_NUM_CONDITIONS5___
      SET_TO Desc_product_group_en = FME_CONDITIONAL:DEFAULT_VALUE'_FME_NO_OP_'BOOL_OP;AND;COMPOSITE_TEST;1 AND 2;TEST @Value(Major_Group (EN)) != Oil And Gas;TEST @Value(product_group_en_spelt) != N/A'Product Group: @Value(product_group_en_spelt)'FME_NUM_CONDITIONS2___
      SET_TO Desc_major_en = Mining Category: @Value(Major_Group (EN))
      SET_TO Desc_OperationGroup_en = FME_CONDITIONAL:DEFAULT_VALUE'_FME_NO_OP_'BOOL_OP;OR;COMPOSITE_TEST;1;TEST operation_group_en ATTRIBUTE_HAS_A_VALUE _FME_BLANK_STRING_'Operation Group: @Value(operation_group_en)'FME_NUM_CONDITIONS2___
      SET_TO Desc_Facility_en = FME_CONDITIONAL:DEFAULT_VALUE'_FME_NO_OP_'BOOL_OP;AND;COMPOSITE_TEST;1 AND 2;TEST facilities_code_en_spelt ATTRIBUTE_HAS_A_VALUE _FME_BLANK_STRING_;TEST @Value(facilities_code_en_spelt) != N/A'Facility: @Value(facilities_code_en_spelt)'FME_NUM_CONDITIONS2___
      SET_TO Desc_Operator_en = FME_CONDITIONAL:DEFAULT_VALUE'_FME_NO_OP_'BOOL_OP;OR;COMPOSITE_TEST;1;TEST operator_owners_en ATTRIBUTE_HAS_A_VALUE _FME_BLANK_STRING_'Operator/Owners: @Value(operator_owners_en)'FME_NUM_CONDITIONS2___
      SET_TO Desc_Static_en =
        This OSDP record contains specific details regarding a mining site represented within the <a href="/dp/en/search/metadata/NRCAN-FGP-1-000183ed-8864-42f0-ae43-c4313a860720" target="_blank">Principal Mineral Areas, Producing Mines, and Oil and Gas Fields (900A)</a> dataset layer produced by Natural Resources Canada, permitting direct search and discovery based on geographic location and/or contextual details.

        The dataset contains a variety of statistics on Canada’s mineral production, and provides the geographic locations of significant metallic, nonmetallic and coal mines, oil sands mines, selected metallurgical works and gas fields for the provinces and territories of Canada.
    -> Attr_creator_french
Note: SECTIONS / FRANÇAIS
Attr_creator_french: AttributeCreator
    ATTR_TABLE:
      SET_TO Desc_product_fr = FME_CONDITIONAL:DEFAULT_VALUE'_FME_NO_OP_'BOOL_OP;OR;COMPOSITE_TEST;1;TEST product_en ATTRIBUTE_HAS_A_VALUE _FME_BLANK_STRING_'Produit : @Value(product_fr)'BOOL_OP;AND;COMPOSITE_TEST;1 AND 2;TEST product_en_spelt ATTRIBUTE_HAS_A_VALUE _FME_BLANK_STRING_;TEST @Value(product_en_spelt) != N/A'Product: @Value(product_fr_spelt)'FME_NUM_CONDITIONS3___
      SET_TO Desc_product_type_fr = FME_CONDITIONAL:DEFAULT_VALUE'_FME_NO_OP_'BOOL_OP;OR;COMPOSITE_TEST;1;TEST @Value(product_en) = Oil'Type Produit : Pétrole'BOOL_OP;OR;COMPOSITE_TEST;1 OR 2;TEST @Value(product_en) = Gas;TEST @Value(product_en) = Gas, sulfur'Type Produit : Gaz'BOOL_OP;OR;COMPOSITE_TEST;1;TEST @Value(product_en) = Bitumen'Type Produit : Bitume'BOOL_OP;OR;COMPOSITE_TEST;1 OR 2;CASE_INSENSITIVE_TEST @Value(product_en) CONTAINS Oil, gas;CASE_INSENSITIVE_TEST @Value(product_en) CONTAINS Gas, oil'Type Produit : Pétrole et Gaz'FME_NUM_CONDITIONS5___
      SET_TO Desc_product_group_fr = FME_CONDITIONAL:DEFAULT_VALUE'_FME_NO_OP_'BOOL_OP;AND;COMPOSITE_TEST;1 AND 2;TEST @Value(Major_Group (EN)) != Oil And Gas;TEST @Value(product_group_en_spelt) != N/A'Groupe de Produit : @Value(product_group_fr_spelt)'FME_NUM_CONDITIONS2___
      SET_TO Desc_major_fr = Catégorie minière : @Value(Major_Group (FR))
      SET_TO Desc_OperationGroup_fr = FME_CONDITIONAL:DEFAULT_VALUE'_FME_NO_OP_'BOOL_OP;OR;COMPOSITE_TEST;1;TEST operation_group_en ATTRIBUTE_HAS_A_VALUE _FME_BLANK_STRING_'Groupe d'opération : @Value(operation_group_fr)'FME_NUM_CONDITIONS2___
      SET_TO Desc_Facility_fr = FME_CONDITIONAL:DEFAULT_VALUE'_FME_NO_OP_'BOOL_OP;AND;COMPOSITE_TEST;1 AND 2;TEST facilities_code_en_spelt ATTRIBUTE_HAS_A_VALUE _FME_BLANK_STRING_;TEST @Value(facilities_code_en_spelt) != N/A'Type d'installation : @Value(facilities_code_fr_spelt)'FME_NUM_CONDITIONS2___
      SET_TO Desc_Operator_fr = FME_CONDITIONAL:DEFAULT_VALUE'_FME_NO_OP_'BOOL_OP;OR;COMPOSITE_TEST;1;TEST operator_owners_en ATTRIBUTE_HAS_A_VALUE _FME_BLANK_STRING_'Opérateur / Propriétaire : @Value(operator_owners_fr)'FME_NUM_CONDITIONS2___
      SET_TO Desc_Static_fr =
        Cet enregistrement dans la PSDO contient des détails spécifiques concernant un site minier représenté dans le <a href="/dp/fr/recherche/metadonnees/NRCAN-FGP-1-000183ed-8864-42f0-ae43-c4313a860720" target="_blank">Principales régions minières, principales mines productrices, principaux champs de pétrole et de gaz (900A)</a> couche d'ensembles de données produite par Ressources naturelles Canada, permettant une recherche et une découverte directes en fonction de l'emplacement géographique et/ou de détails contextuels.

        L’ensemble de données contient diverses statistiques sur la production minérale au Canada et fournit l’emplacement géographique des principales mines de métaux, non métalliques et de charbon, des mines de sables bitumineux, des usines métallurgiques sélectionnées et des gisements de gaz dans les provinces et territoires du Canada.
    -> AttributeCreator_7
AttributeCreator_7
    ATTR_TABLE:
      SET_TO Description (EN) = FME_CONDITIONAL:DEFAULT_VALUE'@Value(Desc_major_en)
        @Value(Desc_OperationGroup_en)
        @Value(Desc_Operator_en)
        @Value(Desc_Static_en)
        'BOOL_OP;OR;COMPOSITE_TEST;1;TEST @Value(Major_Group (EN)) = Oil And Gas'@Value(Desc_product_en)
        @Value(Desc_product_type_en)
        @Value(Desc_major_en)
        @Value(Desc_Static_en)
        'BOOL_OP;OR;COMPOSITE_TEST;1;TEST @Value(Major_Group (EN)) = Producing Mines'@Value(Desc_product_en)
        @Value(Desc_product_group_en)
        @Value(Desc_major_en)
        @Value(Desc_OperationGroup_en)
        @Value(Desc_Facility_en)
        @Value(Desc_Operator_en)
        @Value(Desc_Static_en)
        'BOOL_OP;AND;COMPOSITE_TEST;1 AND 2 AND 3;TEST @Value(Major_Group (EN)) = Metallurgical Works;TEST Desc_Facility_en ATTRIBUTE_HAS_A_VALUE _FME_BLANK_STRING_;TEST @Value(Desc_Facility_en) != Facility: N/A'@Value(Desc_product_en)
        @Value(Desc_product_group_en)
        @Value(Desc_major_en)
        @Value(Desc_OperationGroup_en)
        @Value(Desc_Facility_en)
        @Value(Desc_Operator_en)
        @Value(Desc_Static_en)
        'BOOL_OP;COMPOSITE;COMPOSITE_TEST;1 AND 2 OR 3 AND 4;TEST @Value(Major_Group (EN)) = Metallurgical Works;TEST Desc_Facility_en ATTRIBUTE_VALUE_NULL _FME_BLANK_STRING_;TEST @Value(Desc_Facility_en) = Facility: N/A;TEST product_en_spelt ATTRIBUTE_HAS_A_VALUE _FME_BLANK_STRING_'@Value(Desc_product_en)
        @Value(Desc_product_group_en)
        @Value(Desc_major_en)
        @Value(Desc_OperationGroup_en)
        @Value(Desc_Operator_en)
        @Value(Desc_Static_en)
        'FME_NUM_CONDITIONS5___
      SET_TO Description (FR) = FME_CONDITIONAL:DEFAULT_VALUE'@Value(Desc_major_fr)
        @Value(Desc_OperationGroup_fr)
        @Value(Desc_Operator_fr)
        @Value(Desc_Static_fr)
        'BOOL_OP;OR;COMPOSITE_TEST;1;TEST @Value(Major_Group (EN)) = Oil And Gas'@Value(Desc_product_fr)
        @Value(Desc_product_type_fr)
        @Value(Desc_major_fr)
        @Value(Desc_Static_fr)
        'BOOL_OP;OR;COMPOSITE_TEST;1;TEST @Value(Major_Group (EN)) = Producing Mines'@Value(Desc_product_fr)
        @Value(Desc_product_group_fr)
        @Value(Desc_major_fr)
        @Value(Desc_OperationGroup_fr)
        @Value(Desc_Facility_fr)
        @Value(Desc_Operator_fr)
        @Value(Desc_Static_fr)
        'BOOL_OP;AND;COMPOSITE_TEST;1 AND 2 AND 3;TEST @Value(Major_Group (EN)) = Metallurgical Works;TEST Desc_Facility_en ATTRIBUTE_HAS_A_VALUE _FME_BLANK_STRING_;TEST @Value(Desc_Facility_en) != Facility: N/A'@Value(Desc_product_fr)
        @Value(Desc_product_group_fr)
        @Value(Desc_major_fr)
        @Value(Desc_OperationGroup_fr)
        @Value(Desc_Facility_fr)
        @Value(Desc_Operator_fr)
        @Value(Desc_Static_fr)
        'BOOL_OP;COMPOSITE;COMPOSITE_TEST;1 AND 2 OR 3 AND 4;TEST @Value(Major_Group (EN)) = Metallurgical Works;TEST Desc_Facility_en ATTRIBUTE_VALUE_NULL _FME_BLANK_STRING_;TEST @Value(Desc_Facility_en) = Facility: N/A;TEST product_en_spelt ATTRIBUTE_HAS_A_VALUE _FME_BLANK_STRING_'@Value(Desc_product_fr)
        @Value(Desc_product_group_fr)
        @Value(Desc_major_fr)
        @Value(Desc_OperationGroup_fr)
        @Value(Desc_Operator_fr)
        @Value(Desc_Static_fr)
        'FME_NUM_CONDITIONS5___
    -> AttributeRemover_5
AttributeRemover_5
    REMOVE_ATTRS = Desc_Facility_en,Desc_Facility_fr,Desc_OperationGroup_en,Desc_OperationGroup_fr,Desc_Operator_en,Desc_Operator_fr,Desc_Static_en,Desc_Static_fr,Desc_major_en,Desc_major_fr,Desc_product_en,Desc_product_fr,Desc_product_group_en,Desc_product_group_fr,Desc_product_type_en,Desc_product_type_fr,Major_Group (EN),Major_Group (FR),city_en,city_fr,facilities_code_en_spelt,facilities_code_fr_spelt,operation_en,operation_fr,operation_group_en,operation_group_fr,operation_name_en,operation_name_fr,operation_nb,operator_owners_en,operator_owners_fr,product_en,product_en_spelt,product_fr,product_fr_spelt,product_group_en_spelt,product_group_fr_spelt,province_abr,province_en,province_fr,type_en,type_fr,website
    -> FeatureMerger [SUPPLIER]

Bookmark: Comparaison du contenu depuis le dernier traitement
Note: Existing / Records
FeatureMerger
    ATTR_ACCUM_MODE = Merge Supplier
    ATTR_CONFLICT_RES = Use Supplier
    IGNORE_NULLS = No
    JOIN_KEYS = @Value(Identifier.Artifact) @Value(Identifier.Artifact) AUTO
    MERGE_TYPE = Attributes Only
    PROCESS_DUPS = NO
    REJECT_NULL_MISSING_KEYS = No
    SUPPLIERS_FIRST = No
    MERGED -> VariableRetriever_4
    UNMERGED_REQUESTOR -> VariableRetriever
    UNUSED_SUPPLIER -> VariableRetriever_4
    <REJECTED> -> Junction_3
Note: Create_message_2 : Input
Junction_3
    -> Junction_4
VariableRetriever
    SCOPE = Global
    VALUE_ATTR = DateLastSync_value
    VARNAME = DateLastSync
    -> AttributeCreator_6
Note: Enregistrements supprimés / Ajustements des attributs
AttributeCreator_6
    ATTR_TABLE:
      SET_TO Action = D
      SET_TO Publisher (EN)
      SET_TO Publisher (FR)
      SET_TO PublishedFor
      SET_TO Creator (EN)
      SET_TO Creator (FR)
      SET_TO Subject Area
      SET_TO Subject Topic
      SET_TO Title (EN)
      SET_TO Title (FR)
      SET_TO Description (EN)
      SET_TO Description (FR)
      SET_TO Keywords (EN)
      SET_TO Keywords (FR)
      SET_TO Date.LastUpdate = @Value(DateLastSync_value)
      SET_TO Date.Published
      SET_TO Date.Start
      SET_TO Date.End
      SET_TO Coverage.Geometry
      SET_TO Coverage.ProvinceCd
      SET_TO Coverage.PlaceName (EN)
      SET_TO Coverage.PlaceName (FR)
      SET_TO Coverage.Country
      SET_TO Coverage.Region
      SET_TO External.DatasetCategory
      SET_TO External.ProjectCategory
      SET_TO Rights.Disposition
      SET_TO Rights.License
      SET_TO UpdateFrequency
      SET_TO RecordKeeper.LastSyncTS = @Value(DateLastSync_value)
      SET_TO Citation Total
      SET_TO Citation.Format[1]
      SET_TO Citation.Value (EN)[1]
      SET_TO Citation.Value (FR)[1]
      SET_TO Note Total
      SET_TO Note.Type[1]
      SET_TO Note.Title (EN)[1]
      SET_TO Note.Title (FR)[1]
      SET_TO Note.Desc (EN)[1]
      SET_TO Note.Desc (FR)[1]
      SET_TO Resource Total = 0
      SET_TO Resource.Type[1]
      SET_TO Resource.Format[1]
      SET_TO Resource.ServiceProtocol[1]
      SET_TO Resource.Language[1]
      SET_TO Resource.Name (EN)[1]
      SET_TO Resource.Name (FR)[1]
      SET_TO Resource.URL (EN)[1]
      SET_TO Resource.URL (FR)[1]
      SET_TO Resource.Type[2]
      SET_TO Resource.Format[2]
      SET_TO Resource.ServiceProtocol[2]
      SET_TO Resource.Language[2]
      SET_TO Resource.Name (EN)[2]
      SET_TO Resource.Name (FR)[2]
      SET_TO Resource.URL (EN)[2]
      SET_TO Resource.URL (FR)[2]
      SET_TO Resource.Type[3]
      SET_TO Resource.Format[3]
      SET_TO Resource.ServiceProtocol[3]
      SET_TO Resource.Language[3]
      SET_TO Resource.Name (EN)[3]
      SET_TO Resource.Name (FR)[3]
      SET_TO Resource.URL (EN)[3]
      SET_TO Resource.URL (FR)[3]
      SET_TO Resource.Type[4]
      SET_TO Resource.Format[4]
      SET_TO Resource.ServiceProtocol[4]
      SET_TO Resource.Language[4]
      SET_TO Resource.Name (EN)[4]
      SET_TO Resource.Name (FR)[4]
      SET_TO Resource.URL (EN)[4]
      SET_TO Resource.URL (FR)[4]
    -> FeatureHolder

Bookmark: MISE À JOUR DateLastUpdate
VariableRetriever_4
    SCOPE = Global
    VALUE_ATTR = _datelastupdate
    VARNAME = DateLastUpdate
    -> AttributeCreator_12
AttributeCreator_12
    ATTR_TABLE = SET_TO Date.LastUpdate = @Value(_datelastupdate)
    -> FeatureHolder

Bookmark: Valider unicité UUID
DuplicateFilter
    INPUT_ORDERED_CHOICE = No
    KEYATTR = Identifier.Artifact
    UNIQUE -> VariableRetriever_2
    DUPLICATE -> Terminator_5
    DUPLICATE -> Create_message_4
Terminator_5
    MESSAGE:
      Translation Terminated

      Doublons UUID

Bookmark: Upload to OSDP S3 bucket
AttributeCreator_13
    ATTR_TABLE:
      SET_TO name = s3FileUploadACL
      SET_TO region = ca-central-1
      SET_TO s3_ftp_bucket = FME_CONDITIONAL:DEFAULT_VALUE'osdp-lz-prod-sftp-files'BOOL_OP;OR;COMPOSITE_TEST;1;TEST $(ENV) = STAGING'osdp-lz-dev-sftp-files'FME_NUM_CONDITIONS2___
      SET_TO destination_path = Project/Request/NRCAN-MINING-@Value(_feature_type{0}._datestamp).csv
      SET_TO source_file = $(FME_SHAREDRESOURCE_DATA)\DDR\Conditioning_Data\900A_OSDP\GeoDCAT\NRCAN-MINING-@Value(_feature_type{0}._datestamp).csv
    -> Execute_decrypt
Execute_decrypt: 7_Library
    EXECUTION_TRACE = +Execute_decrypt
    Execution_Parameters:
      {
      "name":"name",
      "region":"region",
      "key_list" :
          [{
            "inputAttribute":"ddr_iam_role",
            "outputAttribute":"S3_file_upload.iam_role"
            },
           {
            "inputAttribute":"osdp_bucket_owner_id",
            "outputAttribute":"S3_file_upload.bucket_owner_id"
            }
           ]
      }
    Function_Name = decryptSecret
    -> Execute_s3FileUploadACL_2
    Communication_Thread -> Create_message_10f
Execute_s3FileUploadACL_2: 7_Library
    EXECUTION_TRACE = $(WORKSPACE_NAME)+Execute_s3FileUploadACL
    Execution_Parameters:
      {
      'iam_role':'S3_file_upload.iam_role',
      'ftp_path':'destination_path',
      'fme_server_path':'source_file',
      's3_ftp_bucket':'s3_ftp_bucket',
      'bucket_owner_id':'S3_file_upload.bucket_owner_id'
      }
    Function_Name = s3FileUploadACL
    -> Messages [Execution]
    -> Create_message_10f_2
    Communication_Thread -> Create_message_10f

Bookmark: DATE_LAST_uPDATE
VariableSetter_2
    SCOPE = Global
    VALUE = @Value(Date_LastUpdate)
    VARNAME = DateLastUpdate

FME custom transformer Interative_translation

PythonCaller_Input (input)
    -> AttributeExposer
AttributeExposer
    ATTR_LIST = _iteration,_attr2translate,_attrlist2translate
    -> PythonCaller
Note: Translation with AWS
PythonCaller
    NEW_ATTRIBUTES = _translation_problem
    PYTHONSOURCE:
      import fme
      import fmeobjects
      import time

      def translate_attributes(inText,inlang,outlang):
          try:
              import boto3



              translate = boto3.client('translate', 'ca-central-1', use_ssl=True)
              result = translate.translate_text(Text=inText,SourceLanguageCode=inlang, TargetLanguageCode=outlang).get('TranslatedText')
              return result
          except:
              print ('NE FONCTIONNE PAS DU PREMIER COUP')
              print('PROBLEME _________________________________')
              print(inText)
              raise


      # Template Function interface:
      # When using this function, make sure its name is set as the value of
      # the 'Class or Function to Process Features' transformer parameter
      def processFeature(feature):


          attributestranslation=feature.getAttribute('_attr2translate')
          list_atttranslation=feature.getAttribute('_attrlist2translate')

          try:

              if feature.getAttribute('_mode')==r'English-->French':
                  in_lang="en"
                  out_lang="fr"
                  out_suffix=r'_fr'
              else:
                  in_lang="fr"
                  out_lang="en"
                  out_suffix=r'_en'



              if  attributestranslation:

                  for i in attributestranslation.split(','):
                      text = feature.getAttribute(i)
                      if text and not feature.getAttribute('%s%s'%(i,out_suffix)):

                          if feature.getAttribute('_aws_activation').lower()=='yes':
                              translated_text = translate_attributes(text,in_lang,out_lang)
                          else:
                              translated_text='Translation of '+text
                          if translated_text:
                              feature.setAttribute('%s%s'%(i,out_suffix),translated_text)

              if list_atttranslation:
                  for attr in list_atttranslation.split(','):
                      temp_list_value=feature.getAttribute(attr)
                      if (temp_list_value):
                          list_name=attr.split('{}.')[0]
                          list_attr=attr.split('{}.')[1]
                          list_len=len(temp_list_value)

                          for k in range(list_len):
                              temp_attr_name='%s{%d}.%s'%(list_name,k,list_attr)
                              temp_value=feature.getAttribute(temp_attr_name)

                              if temp_value and not feature.getAttribute('%s%s'%(temp_attr_name,out_suffix)):

                                  if feature.getAttribute('_aws_activation').lower()=='yes':
                                      translated_text = translate_attributes(temp_value,in_lang,out_lang)
                                  else:
                                      translated_text='Translation of '+temp_value
                                  if translated_text:
                                      feature.setAttribute('%s%s'%(temp_attr_name,out_suffix),translated_text)


              feature.setAttribute('_translation_problem',0)
          except:
              feature.setAttribute('_translation_problem',1)
    PYTHONSYMBOL = processFeature
    -> Tester_2
Note: Translation issues ?
Tester_2
    BOOL_OP = OR
    COMPOSITE_TEST = 1
    TEST_CLAUSE = TEST @Value(_translation_problem) = 0
    TEST_MODE = TEST
    PASSED -> PythonCaller_5
    FAILED -> Tester
Note: Replacing URL in translated text
PythonCaller_5
    PYTHONSOURCE:
      import fme
      import fmeobjects
      # Template Function interface:
      # When using this function, make sure its name is set as the value of
      # the 'Class or Function to Process Features' transformer parameter
      def processFeature(feature):
          try:

              if feature.getAttribute('_mode')==r'English-->French':
                  out_suffix=r'_fr'
              else:
                  out_suffix=r'_en'

              #Regeular attributes
              attr2Translate=feature.getAttribute('_attr2translate')
              if attr2Translate:
                  for attr in attr2Translate.split(','):
                      indice_https=0
                      indice_http=0
                      indice_ftp=0

                      temp_translated_value=feature.getAttribute('%s%s'%(attr,out_suffix))
                      if temp_translated_value:
                          #Catching pre identified URL
                          list_urls_https=[]
                          list_urls_http=[]
                          list_urls_ftp=[]
                          list_urls_https=feature.getAttribute('_aws_translate_temp_urls_https_%s{}'%(attr))
                          list_urls_http=feature.getAttribute('_aws_translate_temp_urls_http_%s{}'%(attr))
                          list_urls_ftp=feature.getAttribute('_aws_translate_temp_urls_ftp_%s{}'%(attr))


                          if list_urls_https:
                              for url in list_urls_https:
                                  temp_translated_value=temp_translated_value.replace(r'$U$S%d$'%(indice_https),url)
                                  indice_https=indice_https+1

                          if list_urls_http:
                              for url in list_urls_http:

                                  temp_translated_value=temp_translated_value.replace(r'$U$P%d$'%(indice_http),url)
                                  indice_http=indice_http+1

                          if list_urls_ftp:
                              for url in list_urls_ftp:

                                  temp_translated_value=temp_translated_value.replace(r'$U$F%d$'%(indice_ftp),url)
                                  indice_ftp=indice_ftp+1

                          feature.setAttribute('%s%s'%(attr,out_suffix),temp_translated_value)

              #List Attributes
              list_atttranslation=feature.getAttribute('_attrlist2translate')

              if list_atttranslation:
                  for attr in list_atttranslation.split(','):
                      temp_list_value=feature.getAttribute(attr)
                      if (temp_list_value):
                          list_name=attr.split('{}.')[0]
                          list_attr=attr.split('{}.')[1]
                          list_len=len(temp_list_value)

                          for k in range(list_len):
                              temp_attr_name='%s{%d}.%s'%(list_name,k,list_attr)
                              temp_translated_value=feature.getAttribute('%s%s'%(temp_attr_name,out_suffix))

                              if temp_translated_value:
                                  indice_https=0
                                  indice_http=0
                                  indice_ftp=0



                                  #Catching pre identified URL
                                  list_urls_https=[]
                                  list_urls_http=[]
                                  list_urls_ftp=[]

                                  list_urls_https=feature.getAttribute('_aws_translate_temp_urls_https_%s{}'%(temp_attr_name))
                                  list_urls_http=feature.getAttribute('_aws_translate_temp_urls_http_%s{}'%(temp_attr_name))
                                  list_urls_ftp=feature.getAttribute('_aws_translate_temp_urls_ftp_%s{}'%(temp_attr_name))


                                  if list_urls_https:
                                      for url in list_urls_https:
                                          temp_translated_value=temp_translated_value.replace(r'$U$S%d$'%(indice_https),url)
                                          indice_https=indice_https+1

                                  if list_urls_http:
                                      for url in list_urls_http:

                                          temp_translated_value=temp_translated_value.replace(r'$U$P%d$'%(indice_http),url)
                                          indice_http=indice_http+1

                                  if list_urls_ftp:
                                      for url in list_urls_ftp:

                                          temp_translated_value=temp_translated_value.replace(r'$U$F%d$'%(indice_ftp),url)
                                          indice_ftp=indice_ftp+1

                                  feature.setAttribute('%s%s'%(temp_attr_name,out_suffix),temp_translated_value)




              feature.setAttribute('_translation_problem',0)
          except:
              feature.setAttribute('_translation_problem',1)
    PYTHONSYMBOL = processFeature
    -> Tester_3
Tester_3
    BOOL_OP = OR
    COMPOSITE_TEST = 1
    TEST_CLAUSE = TEST @Value(_translation_problem) = 0
    TEST_MODE = TEST
    PASSED -> TRANSLATED (output)
    FAILED -> Tester
TRANSLATED (output)
Tester
    BOOL_OP = OR
    COMPOSITE_TEST = 1
    TEST_CLAUSE = TEST @Value(_iteration) = 10
    TEST_MODE = TEST
    PASSED -> FAILED (output)
    FAILED -> AttributeCreator
FAILED (output)
AttributeCreator
    ATTR_TABLE = SET_TO _iteration = @Evaluate(@Value(_iteration)+1)
    -> PythonCaller_2
PythonCaller_2
    PYTHONSOURCE:
      import fme
      import fmeobjects
      import time

      # Template Function interface:
      # When using this function, make sure its name is set as the value of
      # the 'Class or Function to Process Features' transformer parameter
      def processFeature(feature):
          print('Attente de 60 secondes pour essai no %d'%(feature.getAttribute('_iteration')))
          time.sleep(60)
    PYTHONSYMBOL = processFeature
    -> PythonCaller_Input (output)
PythonCaller_Input (output)

FME custom transformer Try to recover

Parameters:
- EXECUTION_TRACE =   # Execution Trace

Bookmark: Try to recover
Invalid_Json (input)
    -> AttributeExposer
AttributeExposer
    ATTR_LIST = _json_error{}
    -> ListExploder
    -> doubleInvalidJsonEscapeChars
doubleInvalidJsonEscapeChars: 7_Library
    Attributes_to_Expose = _json_message
    EXECUTION_TRACE = $(EXECUTION_TRACE)+Execute_doubleInvalidJsonEscapeChars
    Execution_Parameters = _json_message
    Function_Name = doubleInvalidJsonEscapeChars
    -> FeatureMerger_2 [REQUESTOR]
    Communication_Thread -> Terminator
Terminator
    MESSAGE:
      There is a problem with the Json code generation.
      Il y a eu un problème avec la génération du code Json.
ListExploder
    ATTR_ACCUM_MODE = Only Use List Attributes
    INDEX_ATTR = _error_index
    LIST_ATTR = _json_error{}
    ELEMENTS -> AttributeExposer_2
AttributeExposer_2
    ATTR_LIST = line,column,severity,message
    -> AttributeCreator_4
AttributeCreator_4
    ATTR_TABLE:
      SET_TO _fr_json_error_message = Ligne @Value(line), colonne @Value(column) : @ReplaceString(@ReplaceString(@Value(severity),\,\\),"\"",\") - @ReplaceString(@ReplaceString(@Value(message),\,\\),"\"",\")
      SET_TO _en_json_error_message = Line @Value(line), column @Value(column) : @ReplaceString(@ReplaceString(@Value(severity),\,\\),"\"",\") - @ReplaceString(@ReplaceString(@Value(message),\,\\),"\"",\")
    -> Aggregator_2
Aggregator_2
    ACCUM_ATTRS_NAME = Merge Incoming Attributes
    CONCAT_ATTRS = _fr_json_error_message _en_json_error_message
    MODE = Attributes Only
    SEP = "\n"
    AGGREGATE -> FeatureMerger [REQUESTOR]
Execution_info (input)
    -> AttributeExposer_4
AttributeExposer_4
    ATTR_LIST = generic_parameters.METADATA_UUID,_job_id,_DDR_ServiceName,newLineCharacter,_fr_message,_en_message,_execution_trace,_head,_tail
    -> Sampler
Sampler
    RATE = 1
    SAMPLE_MODE = No
    SAMPLE_TYPE_LONG = First N Features
    SAMPLED -> FeatureMerger [SUPPLIER]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeCreator_3
AttributeCreator_3
    ATTR_TABLE:
      SET_TO _en_json_error_message = @ReplaceString(@ReplaceString(@Value(_en_json_error_message),\,\\),"\"",\")
      SET_TO _fr_json_error_message = @ReplaceString(@ReplaceString(@Value(_fr_json_error_message),\,\\),"\"",\")
      SET_TO newLineCharacter =

      SET_TO _job_id = $(FME_JOB_ID)
      SET_TO _execution_trace = $(EXECUTION_TRACE)+Build_Json_message_list
      SET_TO _fr_message = Il y a eu un problème avec la génération du code Json, mais nous avons pu le corriger.
        @Value(_fr_json_error_message)
      SET_TO _en_message = There was a problem with the Json code generation, but we have been able to correct it.
        @Value(_en_json_error_message)
      SET_TO _warning_message = {
        "MetadataUUID" : "@Value(generic_parameters.METADATA_UUID)",
        "JobID" : "@Value(_job_id)",
        "ServiceName" : "@Value(_DDR_ServiceName)",
        "TimeStamp" : "@Timestamp(^Y-^m-^d ^H:^M:^S)",
        "MessageType" : "ADMIN",
        "Severity" : "WARNING",
        "ExecutionTrace" : "@ReplaceString(@Value(_execution_trace),@Value(newLineCharacter),\n)",
        "FrMessage" : "@ReplaceString(@Value(_fr_message),@Value(newLineCharacter),\n)",
        "EnMessage" : "@ReplaceString(@Value(_en_message),@Value(newLineCharacter),\n)"
        }
      SET_TO _fr_message = Il y a eu un problème avec la génération du code Json.
        Consultez le log pour voir le code Json.
        @Value(_en_json_error_message)
      SET_TO _en_message = There is a problem with the Json code generation.
        Consult the log to see the Json code.
        @Value(_en_json_error_message)
      SET_TO _consult_the_log_message = {
        "MetadataUUID" : "@Value(generic_parameters.METADATA_UUID)",
        "JobID" : "@Value(_job_id)",
        "ServiceName" : "@Value(_DDR_ServiceName)",
        "TimeStamp" : "@Timestamp(^Y-^m-^d ^H:^M:^S)",
        "MessageType" : "ADMIN",
        "Severity" : "FATAL",
        "ExecutionTrace" : "@ReplaceString(@Value(_execution_trace),@Value(newLineCharacter),\n)",
        "FrMessage" : "@ReplaceString(@Value(_fr_message),@Value(newLineCharacter),\n)",
        "EnMessage" : "@ReplaceString(@Value(_en_message),@Value(newLineCharacter),\n)"
        }
    -> FeatureMerger_2 [SUPPLIER]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeCreator_2
AttributeCreator_2
    ATTR_TABLE:
      SET_TO _json_message = @Value(_head)
        @Value(_warning_message),
        @Right(@Value(_json_message),@int(@StringLength(@Value(_json_message))-@StringLength(@Value(_head))))
    -> JSONValidator_2
JSONValidator_2
    ERROR_LIST_ATTR = _json_error
    JSON_DOCUMENT = @Value(_json_message)
    READ_FROM_FILE = NO
    PASSED -> Valid_Json (output)
    FAILED -> AttributeCreator_5
AttributeCreator_5
    ATTR_TABLE:
      SET_TO _json_message = @Value(_head)
        @Value(_consult_the_log_message),
        @Value(_tail)
    -> Valid_Json (output)
Valid_Json (output)

FME custom transformer Messages

Parameters:
- EXECUTION_TRACE =   # Execution Trace

Bookmark: Messages du processus
Execution (input)
    -> FeatureMerger_2 [REQUESTOR]
Communication (input)
    -> AttributeExposer
AttributeExposer
    ATTR_LIST = _DDR_ServiceName,_en_message,_execution_trace,_fr_message,_job_id,_message_type,_severity,_timestamp,generic_parameters.METADATA_UUID,newLineCharacter
    -> TestFilter
    -> Aggregator_2

Bookmark: Success email
Aggregator_2
    ACCUM_ATTRS_NAME = Drop Incoming Attributes
    CONCAT_ATTRS = _fr_message _en_message
    LIST_ATTRS_TO_INCLUDE = _feature_type{}.name _severity
    LIST_NAME = _input_msg
    MODE = Attributes Only
    SEP = \n
    AGGREGATE -> AttributeCreator_3
AttributeCreator_3
    ATTR_TABLE:
      SET_TO email_body = The OSDP database has been updated with the latest data from 900A.\n\nMessage log:\n@Value(_en_message)\n\nBest regards,\nThe FGP team.\n\n------------------------------------------------------------------------------------\n\nLa base de données de la PSDO a été mise à jour avec les dernières données du jeu de données 900A.\n\nJournal des messages:\n@Value(_fr_message)\n\nCordialement,\nL'équipe de la PGF.
      SET_TO email_sent = {

        "email_to": "fgpcontributorssupport-pgfsupportcontributeurs@nrcan-rncan.gc.ca",

        "email_replyto": "fgpcontributorssupport-pgfsupportcontributeurs@nrcan-rncan.gc.ca",

        "email_subject": "900A Registry update / Mise à jour du Registre 900A",

        "subscriber_content": "@Value(email_body)"

        }
    -> JSONValidator_2
    -> Try_to_recover_2 [Execution_info]
    -> Tester
JSONValidator_2
    ERROR_LIST_ATTR = _json_error
    JSON_DOCUMENT = @Value(email_sent)
    READ_FROM_FILE = NO
    PASSED -> JSONFormatter_2
    FAILED -> Try_to_recover_2 [Invalid_Json]
Try_to_recover_2: Try to recover
    EXECUTION_TRACE = $(EXECUTION_TRACE)+Try_to_recover
    Valid_Json -> JSONFormatter_2
JSONFormatter_2
    ERROR_LIST_ATTR = _json_error
    FORMAT = Pretty Print
    INDENT_STYLE = 3 spaces
    JSON_DOCUMENT = @Value(email_sent)
    OUTPUT_ATTR = email_sent_line
    OUTPUT_ENCODING = UTF-8
    READ_FROM_FILE = NO
    REMOVE_EMPTY_OBJECTS_AND_ARRAYS = No
    REMOVE_EMPTY_STRINGS = No
    REMOVE_NULLS = No
    -> FeatureMerger_2 [SUPPLIER]
FeatureMerger_2
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = 1 1 NUM
    MERGE_TYPE = Attributes Only
    PROCESS_DUPS = YES
    REJECT_NULL_MISSING_KEYS = No
    SUPPLIERS_FIRST = No
    MERGED -> Execute_getFmeConfig
Execute_getFmeConfig: 7_Library
    Attributes_to_Expose = fmeServerUserName fmeServerPassword
    EXECUTION_TRACE = $(EXECUTION_TRACE)+Execute_getFmeConfig
    Execution_Parameters:
      {
      'userNameAttribute' : 'fmeServerUserName',
      'passwordAttribute' : 'fmeServerPassword'
      }
    Function_Name = getFmeConfig
    -> FMEServerNotifier
FMEServerNotifier
    BODY = @Value(email_sent_line)
    PASSWORD = @Value(fmeServerPassword)
    SERVER_NAME = $(FME_SERVER_WEB_URL)
    TOPIC = DDR_SEND_EMAIL
    USERNAME = @Value(fmeServerUserName)

Bookmark: Failure email
Tester
    BOOL_OP = OR
    COMPOSITE_TEST = 1 OR 2 OR 3 OR 4 OR 5 OR 6 OR 7 OR 8 OR 9 OR 10 OR 11 OR 12 OR 13 OR 14 OR 15 OR 16 OR 17 OR 18 OR 19 OR 20
    TEST_CLAUSE:
      TEST @Value(_input_msg{0}._severity) = ERROR
      TEST @Value(_input_msg{1}._severity) = ERROR
      TEST @Value(_input_msg{2}._severity) = ERROR
      TEST @Value(_input_msg{3}._severity) = ERROR
      TEST @Value(_input_msg{4}._severity) = ERROR
      TEST @Value(_input_msg{5}._severity) = ERROR
      TEST @Value(_input_msg{6}._severity) = ERROR
      TEST @Value(_input_msg{7}._severity) = ERROR
      TEST @Value(_input_msg{8}._severity) = ERROR
      TEST @Value(_input_msg{9}._severity) = ERROR
      TEST @Value(_input_msg{0}._severity) = FATAL
      TEST @Value(_input_msg{1}._severity) = FATAL
      TEST @Value(_input_msg{2}._severity) = FATAL
      TEST @Value(_input_msg{3}._severity) = FATAL
      TEST @Value(_input_msg{4}._severity) = FATAL
      TEST @Value(_input_msg{5}._severity) = FATAL
      TEST @Value(_input_msg{6}._severity) = FATAL
      TEST @Value(_input_msg{7}._severity) = FATAL
      TEST @Value(_input_msg{8}._severity) = FATAL
      TEST @Value(_input_msg{9}._severity) = FATAL
    TEST_MODE = TEST
    PASSED -> AttributeCreator_4
AttributeCreator_4
    ATTR_TABLE:
      SET_TO email_body_admin = La mise à jour des données de 900A pour la PSDO a échoué.\n@Value(_fr_message)\n\nThe 900A data update for the OSDP database has failed.\n@Value(_en_message)\n\nJOB ID: $(FME_JOB_ID)
      SET_TO email_sent_admin = {
           "email_to": "fgpcontributorssupport-pgfsupportcontributeurs@nrcan-rncan.gc.ca",
           "email_replyto": "fgpcontributorssupport-pgfsupportcontributeurs@nrcan-rncan.gc.ca",
           "email_subject": "ÉCHEC: Mise à jour des données du 900A / FAILURE:900A data update",
           "subscriber_content": "@Value(email_body_admin)"
        }
    -> AttributeKeeper_2
AttributeKeeper_2
    CREATE_BULK_MODE_FEATURES = NO
    KEEP_ATTRS = email_sent,email_sent_admin
    -> JSONValidator_3
    -> Try_to_recover_3 [Execution_info]
JSONValidator_3
    ERROR_LIST_ATTR = _json_error
    JSON_DOCUMENT = @Value(email_sent_admin)
    READ_FROM_FILE = NO
    PASSED -> JSONFormatter_3
    FAILED -> Try_to_recover_3 [Invalid_Json]
Try_to_recover_3: Try to recover
    EXECUTION_TRACE = $(EXECUTION_TRACE)+Try_to_recover
    Valid_Json -> JSONFormatter_3
JSONFormatter_3
    ERROR_LIST_ATTR = _json_error
    FORMAT = Pretty Print
    INDENT_STYLE = 3 spaces
    JSON_DOCUMENT = @Value(email_sent_admin)
    OUTPUT_ATTR = email_sent_line
    OUTPUT_ENCODING = UTF-8
    READ_FROM_FILE = NO
    REMOVE_EMPTY_OBJECTS_AND_ARRAYS = No
    REMOVE_EMPTY_STRINGS = No
    REMOVE_NULLS = No
    -> Execute_getFmeConfig_2
Execute_getFmeConfig_2: 7_Library
    Attributes_to_Expose = fmeServerUserName fmeServerPassword
    EXECUTION_TRACE = $(EXECUTION_TRACE)+Execute_getFmeConfig_2
    Execution_Parameters:
      {
      'userNameAttribute' : 'fmeServerUserName',
      'passwordAttribute' : 'fmeServerPassword'
      }
    Function_Name = getFmeConfig
    -> FMEServerNotifier_3
FMEServerNotifier_3
    BODY = @Value(email_sent_line)
    PASSWORD = @Value(fmeServerPassword)
    SERVER_NAME = $(FME_SERVER_WEB_URL)
    TOPIC = DDR_SEND_EMAIL
    USERNAME = @Value(fmeServerUserName)

Bookmark: Server log
TestFilter
    DEFAULT_VALUE = Keep other messages
    TEST_LIST = BOOL_OP,OR,COMPOSITE_TEST,<Unused>,TEST_CLAUSE,"TEST @Value(_message_type) = INTERNAL",Drop internal messages
    Drop internal messages -> AttributeCreator
    Keep other messages -> AttributeCreator
AttributeCreator
    ATTR_TABLE:
      SET_TO newLineCharacter =

      SET_TO _job_id = $(FME_JOB_ID)
      SET_TO _json_message = {
        "MetadataUUID" : "@Value(generic_parameters.METADATA_UUID)",
        "JobID" : "@Value(_job_id)",
        "ServiceName" : "@Value(_DDR_ServiceName)",
        "TimeStamp" : "@Value(_timestamp)",
        "MessageType" : "@Value(_message_type)",
        "Severity" : "@Value(_severity)",
        "ExecutionTrace" : "@ReplaceString(@Value(_execution_trace),@Value(newLineCharacter),\n)",
        "FrMessage" : "@ReplaceString(@Value(_fr_message),@Value(newLineCharacter),\n)",
        "EnMessage" : "@ReplaceString(@Value(_en_message),@Value(newLineCharacter),\n)"
        }
      SET_TO _head = {"MessageList" : [
      SET_TO _tail = ]}
    -> Aggregator
Aggregator
    ACCUM_ATTRS_NAME = Merge Incoming Attributes
    CONCAT_ATTRS = _json_message
    MODE = Attributes Only
    SEP = ",\n"
    AGGREGATE -> StringConcatenator
StringConcatenator
    ACTION = Overwrite Existing Attributes
    ATTRLIST = _json_message
    PARM_LINE = {"MessageList" : [@Value(_json_message)]}
    -> JSONValidator
    -> Try_to_recover [Execution_info]
JSONValidator
    ERROR_LIST_ATTR = _json_error
    JSON_DOCUMENT = @Value(_json_message)
    READ_FROM_FILE = NO
    PASSED -> JSONFormatter
    FAILED -> Try_to_recover [Invalid_Json]
Try_to_recover: Try to recover
    EXECUTION_TRACE = $(EXECUTION_TRACE)+Try_to_recover
    Valid_Json -> JSONFormatter
JSONFormatter
    ERROR_LIST_ATTR = _json_error
    FORMAT = Pretty Print
    INDENT_STYLE = 3 spaces
    JSON_DOCUMENT = @Value(_json_message)
    OUTPUT_ATTR = text_line_data
    OUTPUT_ENCODING = UTF-8
    READ_FROM_FILE = NO
    REMOVE_EMPTY_OBJECTS_AND_ARRAYS = No
    REMOVE_EMPTY_STRINGS = No
    REMOVE_NULLS = No
    -> AttributeCreator_2
AttributeCreator_2
    ATTR_TABLE = SET_TO _outputStreamDestination = $(FME_SHAREDRESOURCE_TEMP)/DDR/Admin/$(FME_JOB_ID)/$(WORKSPACE_NAME)_log.json
    -> AttributeFileWriter_1
AttributeFileWriter_1
    CHAR_ENCODING = utf-8
    FILE_NAME = @Value(_outputStreamDestination)
    OVERWRITE_FILE = Overwrite file
    SOURCE_ATTR = text_line_data
