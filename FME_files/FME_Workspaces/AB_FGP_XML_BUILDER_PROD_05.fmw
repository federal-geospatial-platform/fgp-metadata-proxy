FME workspace AB_FGP_XML_BUILDER_PROD_05.fmw

Parameters:
- ACTIVATE_GEO = Yes
- ACTIVATE_NON_GEO = No
- ACTIVATE_TRANSLATION = Yes
- CATALOGUE_READER_SELECT = Yes
- FORCED_PYCSW_URL =
- IN_CSV_LOOKUP_TABLES_DIR = $(FME_SHAREDRESOURCE_DATA)\PT_Harvester\LOOKUP_TABLES
- IN_FFS_TESTING_FILE =
- IN_GMD_XML_TEMPLATE_DIR = $(FME_SHAREDRESOURCE_DATA)\PT_Harvester\XML_TEMPLATES
- IN_TBS_JSON_TEMPLATE_DIR = $(FME_SHAREDRESOURCE_DATA)\PT_Harvester\JSON_TEMPLATES
- LOCAL_SOURCE_METADATA_DELTA_FINDER = No
- LOCAL_WRITER = No
- LOG_FILE = $(FME_SHAREDRESOURCE_DATA)\PT_Harvester\AB\LOG\AB_FGP_XML_BUILDER.log
- OUT_JSON_LOCAL_DIR = $(FME_SHAREDRESOURCE_DATA)\PT_Harvester\AB\JSON_LOCAL
- OUT_XLS_NOTIFICATION_DIR = $(FME_SHAREDRESOURCE_DATA)\PT_Harvester\AB\XLS
- OUT_XML_FAILED_DIR = $(FME_SHAREDRESOURCE_DATA)\PT_Harvester\AB\XML_FAILED
- OUT_XML_LOCAL_DIR = $(FME_SHAREDRESOURCE_DATA)\PT_Harvester\AB\XML_LOCAL
- OUT_XML_PASSED_DIR = $(FME_SHAREDRESOURCE_DATA)\PT_Harvester\AB\XML_PASSED
- P-T_ABBR = AB
- PYCSW_OVERWRITE = NO
- SAMPLE_SELECT = No
- SAMPLE_SIZE = 10
- IN_OUT_WORKING_DIR = C:\Data\PT_Harvester
- URL_VALIDATION = Yes
- FME_SHAREDRESOURCE_DATA = C:\Data   # FME Server Resource Data

Writers:
- TEXTLINE_1: TEXTLINE to $(OUT_XML_FAILED_DIR)
- TEXTLINE_2: TEXTLINE to $(OUT_XML_LOCAL_DIR)
- TEXTLINE_3: TEXTLINE to $(OUT_XML_PASSED_DIR)
- XLSXW_1: XLSXW to $(OUT_XLS_NOTIFICATION_DIR)

AttributeExposer_2
    ATTR_LIST = license_id
    -> LICENSE_FILTER
Note: Reading Licence_AB
LOOKUP_TABLES_READER
    CSV_ENCODING = utf-8
    CSV_PATH = $(IN_CSV_LOOKUP_TABLES_DIR)
    FEATURE_TYPE = License_AB
    PT = AB
    -> LICENSE_FILTER [LOOKUP_TABLE_INPUT]
LICENSE_FILTER
    LICENSE_ATT = @Value(license_id)
    LICENSE_FILTER_PASSED -> AB_DATA_READER
    UNKNOWN_LICENSE -> VariableRetriever_9
VariableRetriever_9
    SCOPE = Global
    VALUE_ATTR = _timestamp
    VARNAME = _timestamp
    -> Unknown_licence (writer XLSXW_1)
Unknown_licence (writer XLSXW_1)
    attributes: license_id auto(20), id string(37)
Note: Reading FrenchTranslation
LOOKUP_TABLES_READER_6
    CSV_ENCODING = utf-8
    CSV_PATH = $(IN_CSV_LOOKUP_TABLES_DIR)
    FEATURE_TYPE = FrenchTranslation
    PT = AB
    -> METADATA_VALUE_MAPPER_3 [LOOKUP_TABLE_INPUT]
VariableRetriever_8
    SCOPE = Global
    VALUE_ATTR = _timestamp
    VARNAME = _timestamp
    -> METADATA_MAPPING_ERRORS (writer XLSXW_1)
METADATA_MAPPING_ERRORS (writer XLSXW_1)
    attributes: id auto(20), error auto(20)
AttributeExposer_6
    ATTR_LIST = id
    -> GEOPORTAL_WEBLINK_ADDER
Note: Reading GeoportalWeblink_AB
LOOKUP_TABLES_READER_17
    CSV_ENCODING = utf-8
    CSV_PATH = $(IN_CSV_LOOKUP_TABLES_DIR)
    FEATURE_TYPE = GeoportalWeblink_AB
    PT = AB
    -> GEOPORTAL_WEBLINK_ADDER [LOOKUP_TABLE_INPUT]
GEOPORTAL_WEBLINK_ADDER
    URL_VALIDATION = $(URL_VALIDATION)
    WEBLINK_WILDCARD = @Value(id)
    -> PYCSW_URL_MAPPER
Note: Writes XML to a local folder without publishing to PyCSW, and without the PyCSW transaction headers and footers
text_line (writer TEXTLINE_2)
    attributes: text_line_data buffer
Note: Writes XML published to the PyCSW to a local folder
text_line (writer TEXTLINE_3)
    attributes: text_line_data buffer
Note: Writes XML that failed to publish to the PyCSW to a local folder
text_line (writer TEXTLINE_1)
    attributes: text_line_data buffer

Bookmark: Reading AB Geoportal datasets
Creator_2
    GEOMTYPE = Geometry Object
    NUM = 1
    CREATED -> DateTimeStamper
DateTimeStamper
    DATETIME_ATTR = _toto
    STAMP_TYPE = date
    TIMEZONE = local
    -> VariableSetter
VariableSetter
    SCOPE = Global
    VALUE = @Value(_toto)
    VARNAME = _timestamp
    -> Tester_3
Tester_3
    BOOL_OP = OR
    COMPOSITE_TEST = 1
    TEST_CLAUSE = TEST $(CATALOGUE_READER_SELECT) = Yes
    TEST_MODE = TEST
    PASSED -> Catalogue_Reader
    FAILED -> FeatureReader [INITIATOR]
FeatureReader
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> AttributeExposer_2

Bookmark: Extracting data from AB portal
Catalogue_Reader: Catalogue Reader
    CKAN_FILTER = fq=type:opendata
    CUSTOM_CSW_LIST_NAME = DefaultNoList{}
    CUSTOM_URL = https://open.alberta.ca/api/3/action
    SOURCE_URL = Manuel
    Résultats -> AttributeExposer_2

Bookmark: Extract Data
AB_DATA_READER
    NONGEO_OUTPUT -> Tester_5
    GEO_OUTPUT -> Tester_4
Tester_4
    BOOL_OP = OR
    COMPOSITE_TEST = 1
    TEST_CLAUSE = TEST $(ACTIVATE_GEO) = Yes
    TEST_MODE = TEST
    PASSED -> Tester_2
Tester_5
    BOOL_OP = OR
    COMPOSITE_TEST = 1
    TEST_CLAUSE = TEST $(ACTIVATE_NON_GEO) = Yes
    TEST_MODE = TEST
    PASSED -> Junction

Bookmark: Sampler
Tester_2
    BOOL_OP = OR
    COMPOSITE_TEST = 1
    TEST_CLAUSE = TEST $(SAMPLE_SELECT) = Yes
    TEST_MODE = TEST
    PASSED -> Sampler
    FAILED -> AB_GEODISCOVER_RESOURCE_EXTRACTOR
Sampler
    RATE = $(SAMPLE_SIZE)
    SAMPLE_MODE = No
    SAMPLE_TYPE_LONG = First N Features
    SAMPLED -> AB_GEODISCOVER_RESOURCE_EXTRACTOR

Bookmark: Pretranslation and Translation Actions
AB_GEODISCOVER_RESOURCE_EXTRACTOR
    UNWORKING_URL -> VariableRetriever_11
    -> EMPTY_FORMAT_MAPPER [DATA_INPUT]
VariableRetriever_11
    SCOPE = Global
    VALUE_ATTR = _timestamp
    VARNAME = _timestamp
    -> GEODISCOVER_BROKEN_URL (writer XLSXW_1)
GEODISCOVER_BROKEN_URL (writer XLSXW_1)
    attributes: url_xml auto(20), id auto(20)
EMPTY_FORMAT_MAPPER
    DATA_OUTPUT -> ATTRIBUTE_VALUE_TEXT_CLEANER
ATTRIBUTE_VALUE_TEXT_CLEANER
    -> FORMAT_VALIDATOR

Bookmark: Attribute_Validation
Note: Verfication if URL is valid WMS call for WMS formats
FORMAT_VALIDATOR
    -> DEFAULT_ATTRIBUTE_MAPPER

Bookmark: NON-GEO DATA OUTPUT
Junction

Bookmark: Data adjustement to be HNAP compliant
Note: Reading DefaultAB
LOOKUP_TABLES_READER_2
    CSV_ENCODING = utf-8
    CSV_PATH = $(IN_CSV_LOOKUP_TABLES_DIR)
    FEATURE_TYPE = Default_AB
    PT = AB
    -> DEFAULT_ATTRIBUTE_MAPPER [LOOKUP_TABLE_INPUT]
Note: Sets default attirbute values
DEFAULT_ATTRIBUTE_MAPPER
    -> AB_RESOURCES_FORMATTER
Note: Reading ESRI_AB
LOOKUP_TABLES_READER_3
    CSV_ENCODING = utf-8
    CSV_PATH = $(IN_CSV_LOOKUP_TABLES_DIR)
    FEATURE_TYPE = ESRI_AB
    PT = AB
    -> AB_RESOURCES_FORMATTER [LOOKUP_TABLE_INPUT]
Note: Converts WMS and ESRI REST to URL's to valid formats
AB_RESOURCES_FORMATTER
    WMS_NOT_MAPPED -> VariableRetriever
    ESRI_REST_NOT_MAPPED -> VariableRetriever_4
    -> AB_MISSING_ATTRIBUTE_MANAGER
AB_MISSING_ATTRIBUTE_MANAGER
    -> GEOSPATIAL_DATA_VALIDATOR
VariableRetriever_4
    SCOPE = Global
    VALUE_ATTR = _timestamp
    VARNAME = _timestamp
    -> ESRI_REST_NOT_MAPPED (writer XLSXW_1)
ESRI_REST_NOT_MAPPED (writer XLSXW_1)
    attributes: id string(200), _timestamp string(200)
VariableRetriever
    SCOPE = Global
    VALUE_ATTR = _timestamp
    VARNAME = _timestamp
    -> WMS_NOT_MAPPED (writer XLSXW_1)
WMS_NOT_MAPPED (writer XLSXW_1)
    attributes: id string(200), _timestamp string(200)
Note: Reading GeospatialValidation
LOOKUP_TABLES_READER_4
    CSV_ENCODING = utf-8
    CSV_PATH = $(IN_CSV_LOOKUP_TABLES_DIR)
    FEATURE_TYPE = GeospatialValidation
    PT = AB
    -> GEOSPATIAL_DATA_VALIDATOR [LOOKUP_TABLE_INPUT]
GEOSPATIAL_DATA_VALIDATOR
    KEYWORD_SEARCH = gis
    LIST_SEARCH_ATTRIBUTE = tags{}.display_name
    GEOSPATIAL -> SPATIAL_TYPE_MAPPER [DATA_INPUT]
    NON-GEOSPATIAL -> SPATIAL_TYPE_MAPPER [DATA_INPUT]
    UNKNOWN_FORMAT -> VariableRetriever_10
Note: For now, there are no need to use a lookuptable. All features have a spatial type based on format
SPATIAL_TYPE_MAPPER
    DATA_OUTPUT_FAILED -> VariableRetriever_6
    DATA_OUTPUT_PASSED -> UPDATE_TO_PROGRESS_MAPPER [DATA_INPUT]
VariableRetriever_6
    SCOPE = Global
    VALUE_ATTR = _timestamp
    VARNAME = _timestamp
    -> SPATIAL_TYPE_NOT_MAPPED (writer XLSXW_1)
SPATIAL_TYPE_NOT_MAPPED (writer XLSXW_1)
    attributes: id string(200), title string(200), notes string(200), url string(200), _timestamp string(200)
VariableRetriever_10
    SCOPE = Global
    VALUE_ATTR = _timestamp
    VARNAME = _timestamp
    -> UNKNOWN_FORMAT (writer XLSXW_1)
UNKNOWN_FORMAT (writer XLSXW_1)
    attributes: id string(200), format string(200), _timestamp string(200)
Note: Reading UpdateToProgress
LOOKUP_TABLES_READER_5
    CSV_ENCODING = utf-8
    CSV_PATH = $(IN_CSV_LOOKUP_TABLES_DIR)
    FEATURE_TYPE = UpdateToProgress
    PT = AB
    -> UPDATE_TO_PROGRESS_MAPPER [LOOKUP_TABLE_INPUT]
Note: Maps progress attribute from lookup table based on the value of the update attribute
UPDATE_TO_PROGRESS_MAPPER
    DATA_OUTPUT -> AttributeExposer_4
    PROGRESS_CODE_NOT_MAPPED -> VariableRetriever_7
VariableRetriever_7
    SCOPE = Global
    VALUE_ATTR = _timestamp
    VARNAME = _timestamp
    -> PROGRESS_CODE_NOT_MAPPED (writer XLSXW_1)
PROGRESS_CODE_NOT_MAPPED (writer XLSXW_1)
    attributes: id string(200), resource_update_cycle string(200), _timestamp string(200)

Bookmark: Email format
AttributeExposer_4
    ATTR_LIST = default_contact_email
    -> EMAIL_FORMAT_TESTER
Note: Tests for and corrects missing '@' in email addresses and email separated by a comma delimiter
EMAIL_FORMAT_TESTER
    DEFAULT_CONTACT_EMAIL = @Value(default_contact_email)
    -> METADATA_VALUE_MAPPER_3 [DATA_INPUT]

Bookmark: Attribute value mapper
Note: Correction bad translation
METADATA_VALUE_MAPPER_3
    ATT_TO_MAP = resources{}.name
    CODE_REFRESH = NO
    ENGLISH_REFRESH = NO
    ERROR_NOT_MAPPED = NO
    FRENCH_REFRESH = YES
    -> METADATA_VALUE_MAPPER_2 [DATA_INPUT]
Note: Reading Update
LOOKUP_TABLES_READER_7
    CSV_ENCODING = utf-8
    CSV_PATH = $(IN_CSV_LOOKUP_TABLES_DIR)
    FEATURE_TYPE = Update
    PT = AB
    -> METADATA_VALUE_MAPPER_2 [LOOKUP_TABLE_INPUT]
Note: METADATA_VALUE_MAPPER_2 [METADATA_VALUE_MAPPER] / [Linked] / User Parameters: / ATT_TO_MAP: resource_update_cycle / ERROR_NOT_MAPPED: YES / ENGLISH_REFRESH: YES / FRENCH_REFRESH: YES / CODE_REFRESH: YES
METADATA_VALUE_MAPPER_2
    ATT_TO_MAP = resource_update_cycle
    CODE_REFRESH = YES
    ENGLISH_REFRESH = YES
    ERROR_NOT_MAPPED = YES
    FRENCH_REFRESH = YES
    -> METADATA_FORMAT_MAPPER [DATA_INPUT]
Note: This section utilizes mulitple instances of the METADATA_VALUE_MAPPER to correct values to valid English values and to add the valid French equivalents and RI_CODES where applicable. It can be utilized for mulitple metadata items by accessing custom look up tables applicable to specific items. / Turn the error mapping options and the data items to be mapped on or off by clicking on the transformer and selecting yes/no. / - ERROR_NOT_MAPPED: enables mapping of data item values that cannot be found in the lookup tables. / - ENGLISH_REFRESH: enables updating of English attribute values. / - FRENCH_REFRESH: enables updating of French attribute values. / - CODE_REFRESH: enables updating of RI_CODE values. / Enter the attribute key name by clicking on the transformer and selecting the drop down menu next to the 'att_to_map' text box and selecting the 'Open text editor...' option. Explicitly enter the attribute key name in the text editor (ie: contacts{}.role). / IMPORTANT: Do not select the 'Attribute Value' option from the drop down menu to select the attribute key name.
Note: Reading Format
LOOKUP_TABLES_READER_8
    CSV_ENCODING = utf-8
    CSV_PATH = $(IN_CSV_LOOKUP_TABLES_DIR)
    FEATURE_TYPE = Format
    PT = AB
    -> METADATA_FORMAT_MAPPER [LOOKUP_TABLE_INPUT]
Note: METADATA_FORMAT_MAPPER [METADATA_FORMAT_MAPPER] / [Linked] / User Parameters: / ATT_TO_MAP: resources{}.format / ERROR_NOT_MAPPED: YES / REAL_VALUE_REFRESH: YES / RES_TYPE_FR_REFRESH: YES / RES_TYPE_EN_REFRESH: YES
METADATA_FORMAT_MAPPER
    ATT_TO_MAP = resources{}.format
    ERROR_NOT_MAPPED = YES
    REAL_VALUE_REFRESH = YES
    RES_TYPE_EN_REFRESH = YES
    RES_TYPE_FR_REFRESH = YES
    -> METADATA_VALUE_MAPPER_5 [DATA_INPUT]
Note: Reading Progress
LOOKUP_TABLES_READER_9
    CSV_ENCODING = utf-8
    CSV_PATH = $(IN_CSV_LOOKUP_TABLES_DIR)
    FEATURE_TYPE = Progress
    PT = AB
    -> METADATA_VALUE_MAPPER_5 [LOOKUP_TABLE_INPUT]
Note: METADATA_VALUE_MAPPER_5 [METADATA_VALUE_MAPPER] / [Linked] / User Parameters: / ATT_TO_MAP: progress_code / ERROR_NOT_MAPPED: YES / ENGLISH_REFRESH: YES / FRENCH_REFRESH: YES / CODE_REFRESH: YES
METADATA_VALUE_MAPPER_5
    ATT_TO_MAP = progress_code
    CODE_REFRESH = YES
    ENGLISH_REFRESH = YES
    ERROR_NOT_MAPPED = YES
    FRENCH_REFRESH = YES
    -> METADATA_VALUE_MAPPER_6 [DATA_INPUT]
Note: Reading SpatialRepresentation
LOOKUP_TABLES_READER_10
    CSV_ENCODING = utf-8
    CSV_PATH = $(IN_CSV_LOOKUP_TABLES_DIR)
    FEATURE_TYPE = SpatialRepresentation
    PT = AB
    -> METADATA_VALUE_MAPPER_6 [LOOKUP_TABLE_INPUT]
Note: METADATA_VALUE_MAPPER_6 [METADATA_VALUE_MAPPER] / [Linked] / User Parameters: / ATT_TO_MAP: spatial_representation_type / ERROR_NOT_MAPPED: YES / ENGLISH_REFRESH: YES / FRENCH_REFRESH: YES / CODE_REFRESH: YES
METADATA_VALUE_MAPPER_6
    ATT_TO_MAP = spatial_representation_type
    CODE_REFRESH = YES
    ENGLISH_REFRESH = YES
    ERROR_NOT_MAPPED = YES
    FRENCH_REFRESH = YES
    -> METADATA_VALUE_MAPPER_4 [DATA_INPUT]
Note: ReadingSpatialRef
LOOKUP_TABLES_READER_11
    CSV_ENCODING = utf-8
    CSV_PATH = $(IN_CSV_LOOKUP_TABLES_DIR)
    FEATURE_TYPE = SpatialRef
    PT = AB
    -> METADATA_VALUE_MAPPER_4 [LOOKUP_TABLE_INPUT]
Note: METADATA_VALUE_MAPPER_4 [METADATA_VALUE_MAPPER] / [Linked] / User Parameters: / ATT_TO_MAP: spatialref{}.projection_name / ERROR_NOT_MAPPED: NO / ENGLISH_REFRESH: YES / FRENCH_REFRESH: NO / CODE_REFRESH: NO
METADATA_VALUE_MAPPER_4
    ATT_TO_MAP = spatialref{}.projection_name
    CODE_REFRESH = NO
    ENGLISH_REFRESH = YES
    ERROR_NOT_MAPPED = NO
    FRENCH_REFRESH = NO
    -> METADATA_VALUE_MAPPER_7 [DATA_INPUT]
Note: Reading Codespace
LOOKUP_TABLES_READER_12
    CSV_ENCODING = utf-8
    CSV_PATH = $(IN_CSV_LOOKUP_TABLES_DIR)
    FEATURE_TYPE = Codespace
    PT = AB
    -> METADATA_VALUE_MAPPER_7 [LOOKUP_TABLE_INPUT]
Note: METADATA_VALUE_MAPPER_7 [METADATA_VALUE_MAPPER] / [Linked] / User Parameters: / ATT_TO_MAP: spatialref{}.projection_system / ERROR_NOT_MAPPED: NO / ENGLISH_REFRESH: YES / FRENCH_REFRESH: NO / CODE_REFRESH: NO
METADATA_VALUE_MAPPER_7
    ATT_TO_MAP = spatialref{}.projection_system
    CODE_REFRESH = NO
    ENGLISH_REFRESH = YES
    ERROR_NOT_MAPPED = NO
    FRENCH_REFRESH = NO
    -> METADATA_VALUE_MAPPER_9 [DATA_INPUT]
Note: Reading Keyword
LOOKUP_TABLES_READER_13
    CSV_ENCODING = utf-8
    CSV_PATH = $(IN_CSV_LOOKUP_TABLES_DIR)
    FEATURE_TYPE = Keyword
    PT = AB
    -> METADATA_VALUE_MAPPER_9 [LOOKUP_TABLE_INPUT]
Note: METADATA_VALUE_MAPPER_9 [METADATA_VALUE_MAPPER] / [Linked] / User Parameters: / ATT_TO_MAP: iso_topic{}.topic_value / ERROR_NOT_MAPPED: NO / ENGLISH_REFRESH: YES / FRENCH_REFRESH: NO / CODE_REFRESH: NO
METADATA_VALUE_MAPPER_9
    ATT_TO_MAP = iso_topic{}.topic_value
    CODE_REFRESH = NO
    ENGLISH_REFRESH = YES
    ERROR_NOT_MAPPED = NO
    FRENCH_REFRESH = NO
    -> METADATA_VALUE_MAPPER_10 [DATA_INPUT]
Note: Reading Country
LOOKUP_TABLES_READER_14
    CSV_ENCODING = utf-8
    CSV_PATH = $(IN_CSV_LOOKUP_TABLES_DIR)
    FEATURE_TYPE = Country
    PT = AB
    -> METADATA_VALUE_MAPPER_10 [LOOKUP_TABLE_INPUT]
Note: METADATA_VALUE_MAPPER_10 [METADATA_VALUE_MAPPER] / [Linked] / User Parameters: / ATT_TO_MAP: contacts{}.country / ERROR_NOT_MAPPED: NO / ENGLISH_REFRESH: YES / FRENCH_REFRESH: NO / CODE_REFRESH: NO
METADATA_VALUE_MAPPER_10
    ATT_TO_MAP = contacts{}.country
    CODE_REFRESH = NO
    ENGLISH_REFRESH = YES
    ERROR_NOT_MAPPED = NO
    FRENCH_REFRESH = NO
    -> METADATA_VALUE_MAPPER_8 [DATA_INPUT]
Note: Reading Email
LOOKUP_TABLES_READER_18
    CSV_ENCODING = utf-8
    CSV_PATH = $(IN_CSV_LOOKUP_TABLES_DIR)
    FEATURE_TYPE = Email
    PT = YT
    -> METADATA_VALUE_MAPPER_8 [LOOKUP_TABLE_INPUT]
Note: METADATA_VALUE_MAPPER_8 [METADATA_VALUE_MAPPER] / [Linked] / User Parameters: / ATT_TO_MAP: contacts{}.email / ERROR_NOT_MAPPED: NO / ENGLISH_REFRESH: YES / FRENCH_REFRESH: NO / CODE_REFRESH: NO
Note: Maps contacts{}.email to HNAP standards
METADATA_VALUE_MAPPER_8
    ATT_TO_MAP = contacts{}.email
    CODE_REFRESH = NO
    ENGLISH_REFRESH = YES
    ERROR_NOT_MAPPED = NO
    FRENCH_REFRESH = NO
    -> METADATA_VALUE_MAPPER_ERROR_MANAGER

Bookmark: Managin error
Note: Creates list of errors found and not corrected in mapping
METADATA_VALUE_MAPPER_ERROR_MANAGER
    ERROR_OUTPUT -> VariableRetriever_8
    DATA_OUTPUT -> MORE_INFO_MANAGER

Bookmark: Data prepartion for medadata section
Note: Tests the more_info{}.link list for valid attribute values and filters them out where missing
MORE_INFO_MANAGER
    -> AttributeExposer_5
AttributeExposer_5
    ATTR_LIST = resources{}
    -> ListCopier
ListCopier
    DEST_LIST = distributionList
    SRC_LIST = resources{}
    -> GMD_SECTION_DATA_EXTRACTION
Note: Creates lists and removes duplicates for GMD_Section
GMD_SECTION_DATA_EXTRACTION
    -> REMOVE_BROKEN_URL_WMS_ESRI_REST

Bookmark: Data cleanup. Dropping broken web services
REMOVE_BROKEN_URL_WMS_ESRI_REST
    -> WMS_REST_LANGUAGE_FORMATTER
    FAULTY_URL_OUTPUT -> VariableRetriever_2
VariableRetriever_2
    SCOPE = Global
    VALUE_ATTR = _timestamp
    VARNAME = _timestamp
    -> MAP_SERVICE_URL_ERROR (writer XLSXW_1)
MAP_SERVICE_URL_ERROR (writer XLSXW_1)
    attributes: id string(200), url string(200), format string(200), _url_failure_message string(200), _timestamp string(200)

Bookmark: HNAP Rules- 1 web service per language.
Note: Formats WMS and ESRI REST resources to add French versions and formats French and English versions with valid supporting attributes
WMS_REST_LANGUAGE_FORMATTER
    -> DUPLICATE_SERVICE_REMOVER
Note: Removes duplicate WMS or ESRI REST resources where they exist, that would otherwise invalidate the dataset
DUPLICATE_SERVICE_REMOVER
    -> AttributeExposer_6

Bookmark: Configuring publishing info
Note: Reading PyCSW_config
LOOKUP_TABLES_READER_15
    CSV_ENCODING = utf-8
    CSV_PATH = $(IN_CSV_LOOKUP_TABLES_DIR)
    FEATURE_TYPE = PyCSW_config
    PT = AB
    -> PYCSW_URL_MAPPER [PYCSW_CONFIG]
PYCSW_URL_MAPPER
    FORCED_PYCSW_URL = $(FORCED_PYCSW_URL)
    PROVIDER = $(P-T_ABBR)
    -> AttributeExposer_3
AttributeExposer_3
    ATTR_LIST = search_criteria_pycsw,csw_url
    -> METADATA_DELTA_FINDER
METADATA_DELTA_FINDER
    ABSTRACT_ATT_NEW = notes
    ABSTRACT_ATT_REF = MD_Metadata.identificationInfo.MD_DataIdentification.abstract.CharacterString
    CSW_FILTER = @Value(search_criteria_pycsw)
    CUSTOM_CSW_CKAN_URL = @Value(csw_url)
    DATESTAMP_ATT_NEW = record_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    -> AttributeExposer
AttributeExposer
    ATTR_LIST = PyCSW_Transaction,id
    -> AttributeFilter
AttributeFilter
    ATTR_NAME = PyCSW_Transaction
    ATTR_VALUES = <Empty>,<Missing>,<Null>,<Unfiltered>,No change,Update,Insert,Delete
    <EMPTY> -> Terminator
    <MISSING> -> Terminator
    <NULL> -> Terminator
    <UNFILTERED> -> Terminator
    No change -> Tester
    Update -> AWS_TRANSLATE
    Insert -> AWS_TRANSLATE
    Delete -> AttributeKeeper
Terminator
    MESSAGE = ERROR: Unknown _event value from Metadata_Delta
Tester
    BOOL_OP = OR
    COMPOSITE_TEST = 1
    TEST_CLAUSE = TEST $(PYCSW_OVERWRITE) = YES
    TEST_MODE = TEST
    PASSED -> AttributeCreator
    FAILED -> StatisticsCalculator
Note: Reset to update
AttributeCreator
    ATTR_TABLE = SET_TO PyCSW_Transaction = Update
    -> AWS_TRANSLATE
AttributeKeeper
    KEEP_ATTRS = id
    -> VariableRetriever_3
VariableRetriever_3
    SCOPE = Global
    VALUE_ATTR = _timestamp
    VARNAME = _timestamp
    -> DELETED_RECORDS (writer XLSXW_1)
DELETED_RECORDS (writer XLSXW_1)
    attributes: id string(200), _timestamp string(200)
Creator_3
    GEOMTYPE = Geometry Object
    NUM = 1
    CREATED -> StatisticsCalculator
StatisticsCalculator
    COMPUTE_HISTOGRAM = NO
    COUNT_ATTR = _count
    PREPEND_ATTR_NAME_CHOICE = For multiple results only
    STATS_ATTRS = id
    SUMMARY -> AttributeCreator_2
AttributeCreator_2
    ATTR_TABLE = SET_TO _real_count = @Evaluate(@Value(_count)-1)
    -> StatisticsCalculator_Summary
StatisticsCalculator_Summary: Logger
    LOG_FEATURE = NONE
    MAXFEATS = 20
    MESSAGE:
      ************************
      **** Unchanged Report ****
      ************************

      @Value(_real_count) features were unchanged

      ************************
      ************************
      ************************
    SEVERITY = INFO

Bookmark: Language Translation
AWS_TRANSLATE
    ACTIVATE_TRANSLATION = $(ACTIVATE_TRANSLATION)
    ATTR_2_Translate = notes,title,sector
    ATTR_LIST_2_Translate = tags{}.display_name,resources{}.name
    MODE = English-->French
    -> XML_PUBLISHER_NG_2
    TRANSLATION_PROBLEM -> VariableRetriever_5
VariableRetriever_5
    SCOPE = Global
    VALUE_ATTR = _timestamp
    VARNAME = _timestamp
    -> translation_problems (writer XLSXW_1)
translation_problems (writer XLSXW_1)
    attributes: id auto(20)

Bookmark: XML CREATION AND WRITING
Note: Extracts and maps attributes to values required by the XML root template or sub-templates, compliles the templates to a single XML file, and publishes the XML to the PyCSW, or to a local folder. / NOTE: The publication method is defaulted to 'Auto', which will read the method attribute set in the CREATE transformer. Can override to 'Local', 'Insert' or 'Update' by selecting option in pubished parameter 'METHOD_SELECT'.
Note: Excel config file to map AB attributes to those required by XML templates
XML_PUBLISHER_NG_2
    FEATURE_TYPE = Config_AB
    IN_CSV_LOOKUP_TABLES_DIR = $(IN_CSV_LOOKUP_TABLES_DIR)
    LOCAL_WRITER = $(LOCAL_WRITER)
    P-T_ABBR = $(P-T_ABBR)
    TEMPLATE_GMD_CITEDRESPONSIBLEPARTY = $(IN_GMD_XML_TEMPLATE_DIR)\GMD_CITEDRESPONSIBLEPARTY.xml
    TEMPLATE_GMD_CONTACT = $(IN_GMD_XML_TEMPLATE_DIR)\GMD_CONTACT.xml
    TEMPLATE_GMD_DISTRIBUTIONFORMAT = $(IN_GMD_XML_TEMPLATE_DIR)\GMD_DISTRIBUTIONFORMAT.xml
    TEMPLATE_GMD_DISTRIBUTOR = $(IN_GMD_XML_TEMPLATE_DIR)\GMD_DISTRIBUTOR.xml
    TEMPLATE_GMD_KEYWORDS = $(IN_GMD_XML_TEMPLATE_DIR)\GMD_KEYWORDS.xml
    TEMPLATE_GMD_MDMETADATA = $(IN_GMD_XML_TEMPLATE_DIR)\GMD_MDMETADATA.xml
    TEMPLATE_GMD_REFERENCESYSTEMINFO = $(IN_GMD_XML_TEMPLATE_DIR)\GMD_REFERENCESYSTEMINFO.xml
    TEMPLATE_GMD_RESOURCEMAINTENANCE = $(IN_GMD_XML_TEMPLATE_DIR)\GMD_RESOURCEMAINTENANCE.xml
    TEMPLATE_GMD_TOPICCATEGORY = $(IN_GMD_XML_TEMPLATE_DIR)\GMD_TOPICCATEGORY.xml
    TEMPLATE_GMD_TRANSFEROPTIONS = $(IN_GMD_XML_TEMPLATE_DIR)\GMD_TRANSFEROPTIONS.xml
    LOCAL -> text_line (writer TEXTLINE_2)
    INSERT_PASSED -> text_line (writer TEXTLINE_3)
    UPDATE_PASSED -> text_line (writer TEXTLINE_3)
    INSERT_FAILED -> text_line (writer TEXTLINE_1)
    UPDATE_FAILED -> text_line (writer TEXTLINE_1)
