FME workspace PEI_PROD.fmw
Title: PEI_PROD
Description: Description 
This workbench read and trasform all the metadata for the provinces of Manitoba (MB) and Saskatchewan (SK).
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
DCAT_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the DCAT_READER. This file is used when the parameter: DCAT_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
METADATA_OVERWRITE: Enable the overwite of the PyCSW.  Can take two values: Yes: Overwrite the contentof the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: C:\Data\PT_Harvester\QC\LOG\QC.log
OUT_JSON_LOCAL_DIR: Source directory to output JSON files. Defined as: C:\Data\PT_Harvester\QC\JSON_LOCAL
OUT_XLS_NOTIFICATION: Source directory to output excel files. Defined as: C:\Data\PT_Harvester\QC\XLS
OUT_XML_FAILED_DIR: Source directory to output failed XML files. Defined as: C:\Data\PT_Harvester\QC\XML_FAILED
OUT_XML_LOCAL_DIR: Source directory to output Local Source XML files. Defined as: C:\Data\PT_Harvester\QC\XML_LOCAL
OUT_XML_PASSED_DIR: Source directory to output passedXML files. Defined as: C:\Data\PT_Harvester\QC\XML_PASSED
URL_VALIDATION : Indicates to validate or not created URL. (Should be Yes for prod)
VALIDATE_INSERT_PCT :Indicates to valide insert percentage. 75 % or less insert/update record  (Should be Yes for prod)

Parameters:
- ACTIVATE_GEO = Yes
- ACTIVATE_NON_GEO = Yes
- ACTIVATE_TRANSLATION = Yes
- CATALOGUE_READER_SELECT = Yes
- FORCED_PYCSW_URL =
- IN_FFS_TESTING_FILE =
- LOCAL_SOURCE_METADATA_DELTA_FINDER = No
- LOCAL_WRITER = No
- METADATA_OVERWRITE = NO   # METADATA OVERWRITE
- IN_OUT_WORKING_DIR = $(FME_SHAREDRESOURCE_DATA)\PT_Harvester
- SAMPLE_SIZE = 0
- URL_VALIDATION = Yes
- VALIDATE_INSERT_PCT_JSON = Yes
- VALIDATE_INSERT_PCT_XML = Yes
- IN_GMD_XML_TEMPLATE_DIR = $(IN_OUT_WORKING_DIR)\XML_TEMPLATES
- IN_TBS_JSON_TEMPLATE_DIR = $(IN_OUT_WORKING_DIR)\JSON_TEMPLATES
- LOG_FILE = $(IN_OUT_WORKING_DIR)\$(P-T_ABBR)\LOG\$(P-T_ABBR).log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- IN_CSV_LOOKUP_TABLES_DIR = $(IN_OUT_WORKING_DIR)\LOOKUP_TABLES
- FME_SHAREDRESOURCE_DATA = C:\Data   # FME Flow Data Directory

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(IN_OUT_WORKING_DIR)
- TEXTLINE_4: TEXTLINE to $(OUT_JSON_LOCAL_DIR)

TestFilter_4
    DEFAULT_VALUE = <UNFILTERED>
    PASSED_TEST_GROUP_OUTPUT = FIRST
    TEST_LIST = "BOOL_OP,OR,COMPOSITE_TEST,""""""1"""""",TEST_CLAUSE,CASE_INSENSITIVE_TEST $(ACTIVATE_NON_GEO) = yes",ACTIVATE_NON_GEO
    ACTIVATE_NON_GEO -> BulkAttributeRemover_3
Note: Removing unnecessary attributes
BulkAttributeRemover_3
    ATTR_EXP = DCAT_[P<pipe>S]_
    -> TestFilter_2
UNKNOWN_MIME_TYPE_NoneGeo (writer XLSXW_1)
    attributes: _unknown_mime_type string(8), _url_validation string(8), id string(8)

Bookmark: DCAT metadata reader
Creator
    GEOMTYPE = Geometry Object
    NUM = 1
    CREATED -> Tester
Tester
    BOOL_OP = OR
    TEST_CLAUSE = CASE_INSENSITIVE_TEST $(CATALOGUE_READER_SELECT) = Yes
    TEST_MODE = CASE_INSENSITIVE_TEST
    PASSED -> DCAT_Reader_PEI
    FAILED -> FeatureReader [INITIATOR]
DCAT_Reader_PEI
    IN_CSV_LOOKUPTABLES_DIR = \LOOKUP_TABLES
    -> Junction_4
FeatureReader
    ATTR_ACCUM_MODE = Only Use Result
    CLIP_TO_ENVELOPE = NO
    COMBINE_GEOM = Use Result
    DATASET = $(IN_FFS_TESTING_FILE)
    FFS_USE_SEARCH_ENVELOPE = NO
    FORMAT = FFS
    INITIATOR_FIRST_OUTPUT = default
    INTERACT = NONE
    ORDER_RESULTS = No
    OUTPUT_ADD_SCHEMA_ATTRIBUTES = NO
    OUTPUT_FEATURES_DISPLAY = Schema and Data Features
    <OTHER> -> Junction_4
Junction_4
    -> ATTRIBUTE_VALUE_TEXT_CLEANER_2

Bookmark: Attributes manager
Note: Nettoyage des attributs
ATTRIBUTE_VALUE_TEXT_CLEANER_2
    -> DEFAULT_ATTRIBUTE_MAPPER_NG_2
Note: Ajout des attributs valeurs par défaut
DEFAULT_ATTRIBUTE_MAPPER_NG_2
    FEATURE_TYPE = Default_PEI
    IN_CSV_LOOKUP_TABLES_DIR = $(IN_CSV_LOOKUP_TABLES_DIR)
    P-T_ABBR = $(P-T_ABBR)
    -> ATTRIBUTE_MANAGER_NG_2
Note: Extraction des attributs à partir du modèle de PEI
ATTRIBUTE_MANAGER_NG_2
    IN_YAML_TEXT:
      id_pei_original:
          action: attribute_overwrite
          attr2set: DCAT_P_identifier

      data_type:
         action: attribute_overwrite
         attr2set: DCAT_S_attributes.hubType
      title:
          action: attribute_overwrite
          attr2set: DCAT_P_title
      notes:
          action: attribute_overwrite
          attr2set: identificationInfo.MD_DataIdentification.abstract.CharacterString
      licence:
          action: attribute_overwrite
          attr2set: DCAT_P_license
      publication_date:
        action: attribute_overwrite
        attr2set: DCAT_P_modified

      record_last_modified:
         action: attribute_overwrite
         attr2set: DCAT_P_modified
      landing_page:
         action: attribute_overwrite
         attr2set: DCAT_P_landingPage

      update_frequency:
         action: attribute_overwrite
         attr2set: metadataMaintenance.MD_MaintenanceInformation.maintenanceAndUpdateFrequency.MD_MaintenanceFrequencyCode

      contact_role:
        action: attribute_overwrite
        attr2set: contact.CI_ResponsibleParty.role.CI_RoleCode

      contact_email:
        action: attribute_overwrite
        attr2set: contact.CI_ResponsibleParty.contactInfo.CI_Contact.address.CI_Address.electronicMailAddress.CharacterString

      east_bound:
        action: attribute_overwrite
        attr2set: identificationInfo.MD_DataIdentification.extent.EX_Extent.geographicElement.EX_GeographicBoundingBox.eastBoundLongitude.Decimal


      west_bound:
        action: attribute_overwrite
        attr2set: identificationInfo.MD_DataIdentification.extent.EX_Extent.geographicElement.EX_GeographicBoundingBox.westBoundLongitude.Decimal

      south_bound:
        action: attribute_overwrite
        attr2set: identificationInfo.MD_DataIdentification.extent.EX_Extent.geographicElement.EX_GeographicBoundingBox.southBoundLatitude.Decimal

      north_bound:
        action: attribute_overwrite
        attr2set: identificationInfo.MD_DataIdentification.extent.EX_Extent.geographicElement.EX_GeographicBoundingBox.northBoundLatitude.Decimal

      sys_ref:
        action: attribute_overwrite
        attr2set: referenceSystemInfo.MD_ReferenceSystem.referenceSystemIdentifier.RS_Identifier.code.CharacterString

      sys_ref_codespace:
        action: attribute_overwrite
        attr2set: referenceSystemInfo.MD_ReferenceSystem.referenceSystemIdentifier.RS_Identifier.codeSpace.CharacterString

      sys_ref_version:
        action: attribute_overwrite
        attr2set: referenceSystemInfo.MD_ReferenceSystem.referenceSystemIdentifier.RS_Identifier.version.CharacterString
    -> ATTRIBUTE_MANAGER_NG_3
Note: Attribut en backup lorsque les premiers sont nuls
ATTRIBUTE_MANAGER_NG_3
    IN_YAML_TEXT:
      notes:
          action: attribute_not_null
          attr2set: DCAT_S_attributes.snippet
    -> ATTRIBUTE_MANAGER_NG_6
Note: Valeur par défaut en dernier lieu
ATTRIBUTE_MANAGER_NG_6
    IN_YAML_TEXT:
      licence:
          action: attribute_not_null
          attr2set: default_licence

      update_frequency:
          action: attribute_not_null
          attr2set: default_updated_frequency

      progress_code:
          action: attribute_not_null
          attr2set: default_progress_code


      contact_role:
        action: attribute_not_null
        attr2set: default_contact_role

      contact_email:
        action: attribute_not_null
        attr2set: default_contact_email


      east_bound:
        action: attribute_not_null
        attr2set: default_east


      west_bound:
        action: attribute_not_null
        attr2set: default_west

      south_bound:
        action: attribute_not_null
        attr2set: default_south

      north_bound:
        action: attribute_not_null
        attr2set: default_north

      sys_ref:
        action: attribute_not_null
        attr2set: default_projection_name

      sys_ref_codespace:
        action: attribute_not_null
        attr2set: default_reference_system

      sys_ref_version:
        action: attribute_not_null
        attr2set: default_projection_system_version

      data_collection_start_date:
        action: attribute_not_null
        attr2set: default_data_collection_start_date
    -> AttributeExposer_25
Note: Transfert des attributs en liste vers le bon format de liste / Keyword / Resources
PythonCaller_8
    PYTHONSOURCE:
      import fme
      import fmeobjects
      from Python.FME_utils import FME_utils

      # Template Function interface:
      # When using this function, make sure its name is set as the value of
      # the 'Class or Function to Process Features' transformer parameter
      def FeatureProcessor(feature):

          max_index=FME_utils.max_index_attribute_list(feature,'DCAT_P_keyword{}')
          for j in range(max_index+1):
              feature.setAttribute('tags{%i}.value'%(j),feature.getAttribute('DCAT_P_keyword{%i}'%(j)))
    PYTHONSYMBOL = FeatureProcessor
    -> ATTRIBUTE_UNEXPOSER_3
Note: Les ID de PEI sont pas bons. On met la landing page en référence
ATTRIBUTE_UNEXPOSER_3
    -> AttributeExposer_27
PEI_TopicExtractor
    FEATURE_TYPE_KEYWORD_TOPIC = topic_keyword_pei
    FEATURE_TYPE_MANUAL_TOPIC = Manual_topic_pei
    IN_LOOKUP_TABLE_DIR = $(IN_CSV_LOOKUP_TABLES_DIR)
    P-T_ABBR = $(P-T_ABBR)
    -> AttributeExposer_14
    Unknown_topic -> unknown_topic (writer XLSXW_1)
unknown_topic (writer XLSXW_1)
    attributes: id string(200), id_pei_original string(200)

Bookmark: Valeur conditionnelle du secteur
AttributeExposer_25
    ATTR_TABLE = DCAT_S_attributes.metadata.metadata.mdContact.rpOrgName,,DCAT_P_publisher.name,,DCAT_S_attributes.metadata.metadata.dataIdInfo.idPurp,,id,
    -> AttributeCreator_2
AttributeCreator_2
    ATTR_TABLE = SET_TO sector (varchar(200)) = FME_CONDITIONAL:DEFAULT_VALUE'@Value(DCAT_P_publisher.name)'BOOL_OP;OR;COMPOSITE_TEST;1;TEST @Value(DCAT_S_attributes.metadata.metadata.mdContact.rpOrgName) != _FME_BLANK_STRING_'@Value(DCAT_S_attributes.metadata.metadata.mdContact.rpOrgName)'BOOL_OP;OR;COMPOSITE_TEST;1;CASE_INSENSITIVE_TEST @Value(DCAT_S_attributes.metadata.metadata.dataIdInfo.idPurp) CONTAINS Taxation and Property Records'Taxation and Property Records'FME_NUM_CONDITIONS3___
    -> AttributeExposer_26

Bookmark: Valeur conditionnelle de la date
AttributeExposer_26
    ATTR_TABLE = identificationInfo.MD_DataIdentification.citation.CI_Citation.date.CI_Date.date.Date,,identificationInfo.MD_DataIdentification.citation.CI_Citation.date.CI_Date.dateType.CI_DateTypeCode,,DCAT_P_issued,
    -> AttributeCreator_5
AttributeCreator_5
    ATTR_TABLE = SET_TO creation_date (varchar(200)) = FME_CONDITIONAL:DEFAULT_VALUE'@Value(DCAT_P_issued)'BOOL_OP;OR;COMPOSITE_TEST;1;CASE_INSENSITIVE_TEST @Value(identificationInfo.MD_DataIdentification.citation.CI_Citation.date.CI_Date.dateType.CI_DateTypeCode) = creation'@Value(identificationInfo.MD_DataIdentification.citation.CI_Citation.date.CI_Date.date.Date)'FME_NUM_CONDITIONS2___
    -> PythonCaller_8

Bookmark: License filtering
AttributeExposer_27
    ATTR_TABLE = id,,title,,description,,licence,,record_last_modified,,landing_page,,update_frequency,,contact_role,,contact_email,,east_bound,,west_bound,,south_bound,,north_bound,,sys_ref,,sys_ref_codespace,,sys_ref_version,,sector,,creation_date,,publication_date,,data_collection_start_date,,spatial_representation_type,,iso_topic{}.topic_value,,progress_code,
    -> LICENSE_FILTER_NG
LICENSE_FILTER_NG
    FEATURE_TYPE = License_$(P-T_ABBR)
    IN_CSV_LOOKUP_TABLES_DIR = $(IN_CSV_LOOKUP_TABLES_DIR)
    LICENSE_ATT = @Value(licence)
    P-T_ABBR = $(P-T_ABBR)
    LICENSE_FILTER_PASSED -> AttributeExposer
    UNKNOWN_LICENSE -> AttributeExposer_12
AttributeExposer_12
    ATTR_TABLE = landing_page,
    -> UNKNOWN_LICENCE (writer XLSXW_1)
UNKNOWN_LICENCE (writer XLSXW_1)
    attributes: license_id string(200), landing_page string(200)

Bookmark: Generate new unique id from metadata DCAT_S_id
AttributeExposer
    ATTR_TABLE = id_pei_original,
    -> DuplicateFilter
DuplicateFilter
    INPUT_ORDERED_CHOICE_LOOKUP = NO
    KEYATTR = id_pei_original
    INPUT_ORDERED_CHOICE = No
    UNIQUE -> UNIQUE_ID_CREATOR
    DUPLICATE -> Terminator
UNIQUE_ID_CREATOR
    UNIQUE_ATT = @Value(id_pei_original)
    -> AttributeRemover
Note: Generate new uuid (overwrite attribute id) from DCAT_P_id_layer since some metadata have the same id with _# suffixes
AttributeRemover
    REMOVE_ATTRS = temp_id,UNIQUE_ATT
    -> PEI_TopicExtractor
Note: If there is a duplicate id, terminate program and change the solution
Terminator
    MESSAGE = Translation Terminated

Bookmark: Date conversion
AttributeExposer_14
    ATTR_TABLE = creation_date,,publication_date,
    -> DateTimeConverter
DateTimeConverter
    DATETIME_ATTR = creation_date publication_date
    OUT_FORMAT = %Y-%m-%d
    PASSTHROUGH = YES
    REPAIR_INPUT = YES
    -> Junction_2
    <REJECTED> -> AttributeRemover_2
AttributeRemover_2
    REMOVE_ATTRS = fme_rejection_code
    -> Junction_2
Junction_2
    -> AttributeExposer_6

Bookmark: Gestion des ressources
AttributeExposer_6
    ATTR_TABLE = id,,title,,description,,licence,,record_last_modified,,landing_page,,update_frequency,,contact_role,,contact_email,,east_bound,,west_bound,,south_bound,,north_bound,,sys_ref,,sys_ref_codespace,,sys_ref_version,,sector,,creation_date,,publication_date,,data_collection_start_date,,spatial_representation_type,,iso_topic{}.topic_value,,progress_code,,resources{}.url,,resources{}.name,
    -> GEOPORTAL_WEBLINK_ADDER_NG
Note: On construit manuellement la liste des ressources pour PEI. Beaucoup de données non géo ne devant pas être dans ESRI. On met le lien vers la métadonées, les données et le service web d'éléments lors que présent
Note: Ajouter le lien vers la métadonnée complète
GEOPORTAL_WEBLINK_ADDER_NG
    FEATURE_TYPE = GeoportalWeblink_PEI
    IN_CSV_LOOKUP_TABLES_DIR = $(IN_CSV_LOOKUP_TABLES_DIR)
    P-T_ABBR = $(P-T_ABBR)
    URL_VALIDATION = $(URL_VALIDATION)
    WEBLINK_WILDCARD = @Value(id_pei_original)/about
    -> AttributeExposer_2
AttributeExposer_2
    ATTR_TABLE = id_pei_original,
    -> GEOPORTAL_WEBLINK_ADDER_NG_2
Note: Ajouter le lien vers ArcGis hub
GEOPORTAL_WEBLINK_ADDER_NG_2
    FEATURE_TYPE = ArcGisHub-link
    IN_CSV_LOOKUP_TABLES_DIR = $(IN_CSV_LOOKUP_TABLES_DIR)
    P-T_ABBR = $(P-T_ABBR)
    URL_VALIDATION = $(URL_VALIDATION)
    WEBLINK_WILDCARD = @Value(id_pei_original)/explore
    -> AttributeExposer_16
AttributeExposer_16
    ATTR_TABLE = DCAT_P_distribution{}.accessURL,
    -> ListSearcher
ListSearcher
    ATTR_VALUE = https://gis.princeedwardisland.ca/server/rest/services
    CASE = CASE_SENSITIVE
    INDEX_ATTR = _list_index
    LIST_ATTR = DCAT_P_distribution{}.accessURL
    MATCHTYPE = REGULAR_EXPRESSION_ENCODED
    PREFIX = _bonService
    FOUND -> PythonCaller
    NOT_FOUND -> GEO_NONE_GEO_SELECTOR
PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass



          def input(self,feature):
              try:
                  config_res={}
                  config_res['format']='ESRI REST'
                  config_res['format_version']='unknown'
                  config_res['protocol']='ESRI:REST'
                  config_res['transfer_option_description_language']='eng'
                  config_res['transfer_option_description_language_other_lang']='eng'
                  config_res['url']=feature.getAttribute('_bonServiceaccessURL')
                  config_res['name']=feature.getAttribute('DCAT_P_title')




                  # Count the number of ressouces{} in the attribute list
                  max_index = FME_utils.max_index_attribute_list(feature, "resources{}")
                  max_index += 1  # Add one ressources

                  #print ('Index maxiamle')
                  #print (max_index)

                  for key, value in config_res.items():
                      # Add attribute to the FME feature
                      resources_name = "resources{%d}.%s"%(max_index, key)  # Set the attribute name
                      feature.setAttribute(resources_name, value)  # Set the attribute

                  self.pyoutput(feature)
              except:
                  pass
          def close(self):
              pass
    PYTHONSYMBOL = FeatureProcessor
    -> GEO_NONE_GEO_SELECTOR

Bookmark: Geo non-geo selector
Note: On recherche Feature Layer dans data type ou [Lattitude,Longitude] dans DCAT_S_attributes.fields{}.alias:
GEO_NONE_GEO_SELECTOR
    YAML_DIRECTIVES:
      data_type:
        domain: [Feature Layer]
        spatial_type: no_overwrite
        not_found: no_log
        search_type: equals
      DCAT_S_attributes.fields{}.alias:
        domain: [Lattitude,Longitude,the_geom]
        spatial_type: no_overwrite
        not_found: no_log
        search_type: contains
    GEOSPATIAL -> SPATIAL_TYPE_MAPPER_NG [DATA_INPUT]
    NONE_GEOSPATIAL -> MANUAL_GEOSPATIAL_SETTER_NG [DATA_INPUT]
SPATIAL_TYPE_MAPPER_NG
    FEATURE_TYPE = SpatialType_$(P-T_ABBR)
    IN_CSV_LOOKUP_TABLES_DIR = $(IN_OUT_WORKING_DIR)\LOOKUP_TABLES
    P-T_ABBR = $(P-T_ABBR)
    DATA_OUTPUT_FAILED -> AttributeExposer_5
    DATA_OUTPUT_PASSED -> TestFilter
AttributeExposer_5
    ATTR_TABLE = id,,title,,notes,
    -> SPATIAL_TYPE_NOT_MAPPED (writer XLSXW_1)
SPATIAL_TYPE_NOT_MAPPED (writer XLSXW_1)
    attributes: id string(20), title string(80), notes string(80)
MANUAL_GEOSPATIAL_SETTER_NG
    FEATURE_TYPE = UnmappedGeoData_$(P-T_ABBR)
    IN_CSV_LOOKUP_TABLES_DIR = $(IN_OUT_WORKING_DIR)\LOOKUP_TABLES
    P-T_ABBR = $(P-T_ABBR)
    GEOSPATIAL -> TestFilter
    NON-GEOSPATIAL -> TestFilter_4
    UNMAPPED_DATA -> UNMAPPED_DATA (writer XLSXW_1)
UNMAPPED_DATA (writer XLSXW_1)
    attributes: id string(200), notes string(200), title string(200)

Bookmark: Geo metadata processing
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @LowerCase($(ACTIVATE_GEO)) = yes",GEO_ACTIVATE
    GEO_ACTIVATE -> BulkAttributeRemover_2
Note: Removing unnecessary attributes
BulkAttributeRemover_2
    ATTR_EXP = DCAT_[P<pipe>S]_
    -> TestFilter_5
DELETEDRECORDS (writer XLSXW_1)
    attributes: id string(200), title string(200)
TRANSLATION_ERRORS (writer XLSXW_1)
    attributes: id string(20), title string(20)

Bookmark: Samples or full content
TestFilter_5
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction_8
    SAMPLES FEATURES -> Sampler_2
Sampler_2
    MODE = ORIGINAL
    RATE = $(SAMPLE_SIZE)
    SAMPLE_TYPE_MULTIPLIER = -1
    SAMPLE_MODE = No
    SAMPLE_TYPE_LONG = First N Features
    SAMPLED -> Junction_8

Bookmark: Metadata Value Mapping - GEO
Junction_8
    -> METADATA_VALUE_MAPPER_NG [DATA_INPUT]
METADATA_VALUE_MAPPER_NG
    ATT_TO_MAP = sys_ref
    CODE_REFRESH = NO
    ENGLISH_REFRESH = YES
    ERROR_NOT_MAPPED = YES
    FEATURE_TYPE = SpatialRef
    FRENCH_REFRESH = NO
    IN_CSV_LOOKUP_TABLES_DIR = $(IN_CSV_LOOKUP_TABLES_DIR)
    P-T_ABBR = $(P-T_ABBR)
    -> METADATA_VALUE_MAPPER_NG_2 [DATA_INPUT]
Note: Topic (categfory)
METADATA_VALUE_MAPPER_NG_2
    ATT_TO_MAP = iso_topic{}.topic_value
    CODE_REFRESH = NO
    ENGLISH_REFRESH = YES
    ERROR_NOT_MAPPED = YES
    FEATURE_TYPE = Topic
    FRENCH_REFRESH = NO
    IN_CSV_LOOKUP_TABLES_DIR = $(IN_CSV_LOOKUP_TABLES_DIR)
    P-T_ABBR = $(P-T_ABBR)
    -> METADATA_VALUE_MAPPER_NG_3 [DATA_INPUT]
Note: Role
METADATA_VALUE_MAPPER_NG_3
    ATT_TO_MAP = contact_role
    CODE_REFRESH = YES
    ENGLISH_REFRESH = YES
    ERROR_NOT_MAPPED = YES
    FEATURE_TYPE = Role
    FRENCH_REFRESH = YES
    IN_CSV_LOOKUP_TABLES_DIR = $(IN_CSV_LOOKUP_TABLES_DIR)
    P-T_ABBR = $(P-T_ABBR)
    -> METADATA_VALUE_MAPPER_NG_4 [DATA_INPUT]
Note: Update
METADATA_VALUE_MAPPER_NG_4
    ATT_TO_MAP = update_frequency
    CODE_REFRESH = YES
    ENGLISH_REFRESH = YES
    ERROR_NOT_MAPPED = YES
    FEATURE_TYPE = Update
    FRENCH_REFRESH = YES
    IN_CSV_LOOKUP_TABLES_DIR = $(IN_CSV_LOOKUP_TABLES_DIR)
    P-T_ABBR = $(P-T_ABBR)
    -> METADATA_VALUE_MAPPER_NG_5 [DATA_INPUT]
Note: Progress
METADATA_VALUE_MAPPER_NG_5
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUP_TABLES_DIR)
    P-T_ABBR = $(P-T_ABBR)
    -> METADATA_VALUE_MAPPER_NG_7 [DATA_INPUT]
Note: SpatialRepresentation
METADATA_VALUE_MAPPER_NG_7
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUP_TABLES_DIR)
    P-T_ABBR = $(P-T_ABBR)
    -> METADATA_FORMAT_MAPPER_NG [DATA_INPUT]
Note: Format
METADATA_FORMAT_MAPPER_NG
    ATT_TO_MAP = resources{}.format
    ERROR_NOT_MAPPED = YES
    FEATURE_TYPE = Format
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_Geo (writer XLSXW_1)
    -> METADATA_VALUE_MAPPER_ERROR_MANAGER
UNKNOWN_MIME_TYPE_Geo (writer XLSXW_1)
    attributes: _unknown_mime_type string(8), _url_validation string(8), id string(8)
METADATA_VALUE_MAPPER_ERROR_MANAGER
    ERROR_OUTPUT -> GEO_ATTRIBUTE_MAPPING_ERRORS (writer XLSXW_1)
    DATA_OUTPUT -> WMS_REST_LANGUAGE_FORMATTER
WMS_REST_LANGUAGE_FORMATTER
    -> GMD_SECTION_DATA_EXTRACTION
GEO_ATTRIBUTE_MAPPING_ERRORS (writer XLSXW_1)
    attributes: error string(200), id string(200)

Bookmark: HNAP RULES
GMD_SECTION_DATA_EXTRACTION
    -> AttributeExposer_3
AttributeExposer_3
    ATTR_TABLE = projectionList{},
    -> AttributeRemover_3
Note: On enlève liste de projection, on prend sys_ref
AttributeRemover_3
    LIST_ATTRS = projectionList{}
    -> AttributeExposer_4

Bookmark: Metadata_delta_finder
AttributeExposer_4
    ATTR_TABLE = search_criteria_pycsw,,record_last_modified,
    -> AttributeCreator
AttributeCreator
    ATTR_TABLE = SET_TO csw_url (varchar(200)) = $(FORCED_PYCSW_URL)
    -> METADATA_DELTA_FINDER_GEN
METADATA_DELTA_FINDER_GEN
    ATTR_DATE_MODIFIED = record_last_modified
    CSW_FILTER = @Value(search_criteria_pycsw)
    LOCAL_SOURCE = $(LOCAL_SOURCE_METADATA_DELTA_FINDER)
    METADATA_OVERWRITE = $(METADATA_OVERWRITE)
    METADATA_TYPE = XML-HNAP
    SOURCE_DIRECTORY = $(OUT_XML_LOCAL_DIR)
    SOURCE_URL = @Value(csw_url)
    VALIDATE_INSERT_PCT = $(VALIDATE_INSERT_PCT_XML)
    YAML_FILE = $(IN_CSV_LOOKUP_TABLES_DIR)\$(P-T_ABBR)\metadata_delta_finder_$(P-T_ABBR)_geo.yaml
    Statistics -> StatisticsCalculator_Summary_2
    Update -> Junction
    Insert -> Junction
    Delete -> AttributeExposer_19
StatisticsCalculator_Summary_2: Logger
    LOG_FEATURE = NONE
    MAXFEATS = 20
    MESSAGE:
      ************************
      **** Unchanged Report ****
      ************************

      @Value(_real_count) features were unchanged

      ************************
      ************************
      ************************
    SEVERITY = INFO
AttributeExposer_19
    ATTR_TABLE = id,,title,
    -> DELETEDRECORDS (writer XLSXW_1)
Junction
    -> AWS_TRANSLATE_2

Bookmark: AWS Translation
AWS_TRANSLATE_2
    ACTIVATE_TRANSLATION = $(ACTIVATE_TRANSLATION)
    ATTR_2_TRANSLATE = notes,title
    ATTR_LIST_2_TRANSLATE = tags{}.value,resources{}.name
    MODE = English-->French
    -> XML_PUBLISHER_NG
    TRANSLATION_PROBLEM -> AttributeExposer_20
AttributeExposer_20
    ATTR_TABLE = id,,title,
    -> TRANSLATION_ERRORS (writer XLSXW_1)

Bookmark: XML CREATION AND WRITING
XML_PUBLISHER_NG
    FEATURE_TYPE = Config_$(P-T_ABBR)
    IN_CSV_LOOKUP_TABLES_DIR = $(IN_CSV_LOOKUP_TABLES_DIR)
    LOCAL_WRITER = $(LOCAL_WRITER)
    P-T_ABBR = $(P-T_ABBR)
    TEMPLATE_GMD_CITEDRESPONSIBLEPARTY = $(IN_GMD_XML_TEMPLATE_DIR)/GMD_CITEDRESPONSIBLEPARTY.xml
    TEMPLATE_GMD_CONTACT = $(IN_GMD_XML_TEMPLATE_DIR)/GMD_CONTACT.xml
    TEMPLATE_GMD_DISTRIBUTIONFORMAT = $(IN_GMD_XML_TEMPLATE_DIR)/GMD_DISTRIBUTIONFORMAT.xml
    TEMPLATE_GMD_DISTRIBUTOR = $(IN_GMD_XML_TEMPLATE_DIR)/GMD_DISTRIBUTOR.xml
    TEMPLATE_GMD_KEYWORDS = $(IN_GMD_XML_TEMPLATE_DIR)/GMD_KEYWORDS.xml
    TEMPLATE_GMD_MDMETADATA = $(IN_GMD_XML_TEMPLATE_DIR)/GMD_MDMETADATA.xml
    TEMPLATE_GMD_REFERENCESYSTEMINFO = $(IN_GMD_XML_TEMPLATE_DIR)/GMD_REFERENCESYSTEMINFO.xml
    TEMPLATE_GMD_RESOURCEMAINTENANCE = $(IN_GMD_XML_TEMPLATE_DIR)/GMD_RESOURCEMAINTENANCE.xml
    TEMPLATE_GMD_TOPICCATEGORY = $(IN_GMD_XML_TEMPLATE_DIR)/GMD_TOPICCATEGORY.xml
    TEMPLATE_GMD_TRANSFEROPTIONS = $(IN_GMD_XML_TEMPLATE_DIR)/GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    InvalidMetadata -> invalid_metadata (writer XLSXW_1)
    UPDATE_FAILED -> text_line (writer TEXTLINE_2)
Note: Writes XML to a local folder without publishing to PyCSW, and without the PyCSW transaction headers and footers
text_line (writer TEXTLINE_3)
    attributes: text_line_data buffer
text_line (writer TEXTLINE_1)
    attributes: text_line_data buffer
text_line (writer TEXTLINE_2)
    attributes: text_line_data buffer
invalid_metadata (writer XLSXW_1)
    attributes: id auto(20)

Bookmark: Samples or full content
TestFilter_2
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction_6
    SAMPLES FEATURES -> Sampler_3
Sampler_3
    MODE = ORIGINAL
    RATE = $(SAMPLE_SIZE)
    SAMPLE_TYPE_MULTIPLIER = -1
    SAMPLE_MODE = No
    SAMPLE_TYPE_LONG = First N Features
    SAMPLED -> Junction_6

Bookmark: Non-geo metadata processing
Junction_6
    -> METADATA_VALUE_MAPPER_NG_10 [DATA_INPUT]
Note: Adjusting update frequency value
METADATA_VALUE_MAPPER_NG_10
    ATT_TO_MAP = update_frequency
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUP_TABLES_DIR)
    P-T_ABBR = $(P-T_ABBR)
    -> METADATA_FORMAT_MAPPER_NG_2 [DATA_INPUT]
Note: Creates list of errors found and not corrected in mapping
METADATA_VALUE_MAPPER_ERROR_MANAGER_2
    ERROR_OUTPUT -> METADATA_MAPPING_ERRORS_NON_GEO (writer XLSXW_1)
    DATA_OUTPUT -> AttributeExposer_13
DELETED_RECORDS_NONE_GEO (writer XLSXW_1)
    attributes: id auto(20), title auto(20)
Note: Translates specific items from English to French
AWS_TRANSLATE_3
    ACTIVATE_TRANSLATION = $(ACTIVATE_TRANSLATION)
    ATTR_2_TRANSLATE = notes,title
    ATTR_LIST_2_TRANSLATE = tags{}.value,resources{}.name
    MODE = English-->French
    -> JSON_PUBLISHER_NG
    TRANSLATION_PROBLEM -> AttributeExposer_21
AttributeExposer_21
    ATTR_TABLE = id,,title,
    -> TRANSLATION_PROBLEMS_NONE_GEO (writer XLSXW_1)
TRANSLATION_PROBLEMS_NONE_GEO (writer XLSXW_1)
    attributes: id auto(20), title auto(20)
METADATA_MAPPING_ERRORS_NON_GEO (writer XLSXW_1)
    attributes: error string(200), id string(200)

Bookmark: Format mapper
Note: resources{}.format
METADATA_FORMAT_MAPPER_NG_2
    ATT_TO_MAP = resources{}.format
    ERROR_NOT_MAPPED = YES
    FEATURE_TYPE = Format_TBS
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_NoneGeo (writer XLSXW_1)
    -> AttributeExposer_7

Bookmark: TOPICS value mapper from iso_topic{}.topic_value list attributes
AttributeExposer_7
    ATTR_TABLE = iso_topic{}.topic_value,
    -> ListCopier_2
ListCopier_2
    DEST_LIST = topics
    SRC_LIST = iso_topic{}
    -> METADATA_VALUE_MAPPER_NG_12 [DATA_INPUT]
METADATA_VALUE_MAPPER_NG_12
    ATT_TO_MAP = topics{}.topic_value
    CODE_REFRESH = NO
    ENGLISH_REFRESH = YES
    ERROR_NOT_MAPPED = YES
    FEATURE_TYPE = Topic_TBS
    FRENCH_REFRESH = NO
    IN_CSV_LOOKUP_TABLES_DIR = $(IN_CSV_LOOKUP_TABLES_DIR)
    P-T_ABBR = $(P-T_ABBR)
    -> AttributeExposer_8
AttributeExposer_8
    ATTR_TABLE = topics{}.topic_value,
    -> ListDuplicateRemover
ListDuplicateRemover
    SRC_LIST = topics{}.topic_value
    -> AttributeExposer_10

Bookmark: SUBJECTS value mapper from iso_topic{}.topic_value list attributes
AttributeExposer_10
    ATTR_TABLE = iso_topic{}.topic_value,
    -> ListCopier_3
ListCopier_3
    DEST_LIST = subjects
    SRC_LIST = iso_topic{}
    -> METADATA_VALUE_MAPPER_NG_13 [DATA_INPUT]
METADATA_VALUE_MAPPER_NG_13
    ATT_TO_MAP = subjects{}.topic_value
    CODE_REFRESH = NO
    ENGLISH_REFRESH = YES
    ERROR_NOT_MAPPED = YES
    FEATURE_TYPE = Subject_TBS
    FRENCH_REFRESH = NO
    IN_CSV_LOOKUP_TABLES_DIR = $(IN_CSV_LOOKUP_TABLES_DIR)
    P-T_ABBR = $(P-T_ABBR)
    -> AttributeExposer_9
AttributeExposer_9
    ATTR_TABLE = subjects{}.topic_value,
    -> ListDuplicateRemover_2
ListDuplicateRemover_2
    SRC_LIST = subjects{}.topic_value
    -> METADATA_VALUE_MAPPER_ERROR_MANAGER_2

Bookmark: metadata delta finder
AttributeExposer_13
    ATTR_TABLE = search_criteria_pycsw,,csw_url,,record_last_modified,,id,
    -> METADATA_DELTA_FINDER_GEN_2
METADATA_DELTA_FINDER_GEN_2
    ATTR_DATE_MODIFIED = record_last_modified
    LOCAL_SOURCE = Yes
    METADATA_OVERWRITE = $(METADATA_OVERWRITE)
    METADATA_TYPE = JSON-CKANExtCa
    SOURCE_DIRECTORY = $(OUT_JSON_LOCAL_DIR)
    VALIDATE_INSERT_PCT = $(VALIDATE_INSERT_PCT_JSON)
    YAML_FILE = $(IN_CSV_LOOKUP_TABLES_DIR)\$(P-T_ABBR)\metadata_delta_finder_$(P-T_ABBR)_non_geo.yaml
    Statistics -> StatisticsCalculator_Summary_3
    Update -> Junction_7
    Insert -> Junction_7
    Delete -> AttributeExposer_22
StatisticsCalculator_Summary_3: Logger
    LOG_FEATURE = NONE
    MAXFEATS = 20
    MESSAGE:
      ************************
      **** NoneGeo Features: Unchanged Report ****
      ************************

      @Value(_real_count) features were unchanged

      ************************
      ************************
      ************************
    SEVERITY = INFO
AttributeExposer_22
    ATTR_TABLE = id,,title,
    -> DELETED_RECORDS_NONE_GEO (writer XLSXW_1)
Junction_7
    -> AWS_TRANSLATE_3

Bookmark: JSON creation and writing
JSON_PUBLISHER_NG
    FEATURE_TYPE = Config_JSON_$(P-T_ABBR)
    IN_CSV_LOOKUP_TABLES_DIR = $(IN_CSV_LOOKUP_TABLES_DIR)
    JSON_RESOURCE_TEMPLATE = $(IN_TBS_JSON_TEMPLATE_DIR)\TBS_RESOURCES_TEMPLATE_NG.json
    JSON_ROOT_TEMPLATE = $(IN_TBS_JSON_TEMPLATE_DIR)\TBS_ROOT_TEMPLATE_NG.json
    Keywords_EN = tags{}.value
    Keywords_FR = tags{}.value_fr
    P-T_ABBR = $(P-T_ABBR)
    Subject_LIST = subjects{}.topic_value
    Topic_LIST = topics{}.topic_value
    OUTPUT_LOCAL -> AttributeExposer_11
AttributeExposer_11
    ATTR_TABLE = json_file,,id,
    -> AttributeCreator_6
AttributeCreator_6
    ATTR_TABLE = SET_TO text_line_data (varchar(200)) = @Value(json_file)
    -> text_line (writer TEXTLINE_4)
text_line (writer TEXTLINE_4)
    attributes: text_line_data buffer
