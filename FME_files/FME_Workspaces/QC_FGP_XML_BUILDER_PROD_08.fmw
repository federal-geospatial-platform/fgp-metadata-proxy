FME workspace QC_FGP_XML_BUILDER_PROD_08.fmw
Title: QC_FGP_XML_BUILDER
Description: Description 
This workbench read and trasform all the metadata for the province of Québec (QC)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
P_T_ABBR: Two letter abbreviation code of the province or terrirtory (ex.: ON, QC, ...).
METADATA_OVERWRITE: Enable the overwite of the PyCSW.  Can take two values: Yes: Overwrite the contentof the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: C:\Data\PT_Harvester\QC\LOG\QC.log
OUT_JSON_LOCAL_DIR: Source directory to output JSON files. Defined as: C:\Data\PT_Harvester\QC\JSON_LOCAL
OUT_XLS_NOTIFICATION: Source directory to output excel files. Defined as: C:\Data\PT_Harvester\QC\XLS
OUT_XML_FAILED_DIR: Source directory to output failed XML files. Defined as: C:\Data\PT_Harvester\QC\XML_FAILED
OUT_XML_LOCAL_DIR: Source directory to output Local Source XML files. Defined as: C:\Data\PT_Harvester\QC\XML_LOCAL
OUT_XML_PASSED_DIR: Source directory to output passedXML files. Defined as: C:\Data\PT_Harvester\QC\XML_PASSED
SAMPLE_SIZE: Number of features to process. Zero (0) means process all the features. A number n greater than 0 means sample or process only the first n features.
URL_VALIDATION : Indicates to validate or not created URL. (Should be Yes for prod)
History: Unknown,Unknown,Original version,01/04/2022,Daniel Pilon,Code refactoring
Startup Python:
      import sys
      import fme
      try:
          if fme.macroValues['FME_SHAREDRESOURCE_DATA']:
              new_path='%s\PT_Harvester\Python'%(fme.macroValues['FME_SHAREDRESOURCE_DATA'])

              print ('Ajout de %s dans le path '%(new_path))
              sys.path += [new_path]


      except:
          raise

Parameters:
- ACTIVATE_GEO = Yes
- ACTIVATE_NON_GEO = yes
- ACTIVATE_TRANSLATION = No
- CATALOGUE_READER_SELECT = Yes
- FORCED_PYCSW_URL = https://pycsw.ddr-stage.services.geo.ca/pycsw?
- IN_FFS_TESTING_FILE =
- LOCAL_SOURCE_METADATA_DELTA_FINDER = No
- LOCAL_WRITER = Yes
- P-T_ABBR = QC
- METADATA_OVERWRITE = NO
- IN_OUT_WORKING_DIR = C:\Data\PT_Harvester
- SAMPLE_SIZE = 0
- URL_VALIDATION = No
- IN_CSV_LOOKUP_TABLES_DIR = $(IN_OUT_WORKING_DIR)\LOOKUP_TABLES   # DEFAULT_IN_CSV_LOOKUP_TABLES_DIR
- IN_GMD_XML_TEMPLATE_DIR = $(IN_OUT_WORKING_DIR)\XML_TEMPLATES
- IN_TBS_JSON_TEMPLATE_DIR = $(IN_OUT_WORKING_DIR)\\JSON_TEMPLATES
- LOG_FILE = $(IN_OUT_WORKING_DIR)\$(P-T_ABBR)\LOG\$(P-T_ABBR).log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- FME_SHAREDRESOURCE_DATA = C:\Data   # FME Server Resource Data

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(OUT_XLS_NOTIFICATION_DIR)
- TEXTLINE_4: TEXTLINE to $(OUT_JSON_LOCAL_DIR)

Junction_4
    -> QC_PROJECTION_GEOEXTENTS_EXTRACTOR
Junction
    -> METADATA_VALUE_MAPPER_NG_4 [DATA_INPUT]
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer

Bookmark: Reading QC Geoportal datasets
Creator
    GEOMTYPE = Geometry Object
    NUM = 1
    CREATED -> Tester_3
Tester_3
    BOOL_OP = OR
    COMPOSITE_TEST = 1
    TEST_CLAUSE = TEST $(CATALOGUE_READER_SELECT) = Yes
    TEST_MODE = TEST
    PASSED -> Catalogue_Reader
    FAILED -> FeatureReader [INITIATOR]
Note: Reading QC CKAN-API
Catalogue_Reader: Catalogue Reader
    CUSTOM_CSW_LIST_NAME = DefaultNoList{}
    CUSTOM_URL = https://www.donneesquebec.ca/recherche/api/action
    SOURCE_URL = Manuel
    Résultats -> ATTRIBUTE_VALUE_TEXT_CLEANER
Note: Read CKAN data strored in the FFS file
FeatureReader
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> ATTRIBUTE_VALUE_TEXT_CLEANER

Bookmark: Filtering and convertion to inhouse model.
Note: Basic cleaning of the different attributes
ATTRIBUTE_VALUE_TEXT_CLEANER
    -> AttributeExposer_3
AttributeExposer_3
    ATTR_LIST = license_id
    -> LICENSE_FILTER_NG
Note: Filter the records accordint to the type of license
LICENSE_FILTER_NG
    FEATURE_TYPE = License_QC
    IN_CSV_LOOKUP_TABLES_DIR = $(IN_CSV_LOOKUP_TABLES_DIR)
    LICENSE_ATT = @Value(license_id)
    P-T_ABBR = $(P-T_ABBR)
    LICENSE_FILTER_PASSED -> QC_DATE_FORMATTER
    UNKNOWN_LICENSE -> LICENSE_ID_NOT_MAPPED (writer XLSXW_1)
Note: Formats required date values to HNAP requirements
QC_DATE_FORMATTER
    -> DEFAULT_ATTRIBUTE_MAPPER_NG
LICENSE_ID_NOT_MAPPED (writer XLSXW_1)
    attributes: license_id auto(20), id auto(20)

Bookmark: Default value
Note: Sets default attribute values
DEFAULT_ATTRIBUTE_MAPPER_NG
    FEATURE_TYPE = Default_QC
    IN_CSV_LOOKUP_TABLES_DIR = $(IN_CSV_LOOKUP_TABLES_DIR)
    P-T_ABBR = $(P-T_ABBR)
    -> ATTRIBUTE_MANAGER_NG
ATTRIBUTE_MANAGER_NG
    IN_YAML_TEXT:
      author:
          action: attribute_not_null
          attr2set: organization.title

      update_frequency:
          action: attribute_not_null
          attr2set: default_update_frequency

      progress_code:
          action: attribute_overwrite
          attr2set: update_frequency

      contacts{0}.name:
         action: attribute_overwrite
         attr2set: author

      contacts{0}.email:
         action: attribute_overwrite
         attr2set: author_email

      sector:
          action: attribute_overwrite
          attr2set: organization.title

      location:
          action: attribute_overwrite
          attr2set: ext_spatial

      tags{0}.display_name:
          action: attribute_not_null
          attr2set: default_tag

      notes:
           action: attribute_not_null
           attr2set: title

      groups{}.name:
          action: attribute_not_null
          attr2set: default_topic_subject
    -> RESOURCES_VALIDATOR

Bookmark: Attribute Validation
Note: Validates url, name and format on resources{} list items
RESOURCES_VALIDATOR
    -> FORMAT_VALIDATOR
Note: Verfication if URL is valid WMS call for WMS formats
FORMAT_VALIDATOR
    -> AttributeExposer_6

Bookmark: Email format
AttributeExposer_6
    ATTR_LIST = default_contact_email
    -> EMAIL_FORMAT_TESTER
Note: Tests for and corrects missing '@' in email addresses and email separated by a comma delimiter
EMAIL_FORMAT_TESTER
    DEFAULT_CONTACT_EMAIL = @Value(default_contact_email)
    -> QC_MISSING_EMAIL_MAPPER

Bookmark: QC Missing eMail Mapper
Note: Add default_contact_email when contact email is missing
QC_MISSING_EMAIL_MAPPER: QC_MISSING_EMAIL_SETTER
    DATA_OUTPUT_PASSED -> AttributeExposer_8

Bookmark: Qdd QC Geoportal Weblink
AttributeExposer_8
    ATTR_LIST = id
    -> GEOPORTAL_WEBLINK_ADDER_NG
Note: Validate web link
GEOPORTAL_WEBLINK_ADDER_NG
    FEATURE_TYPE = GeoportalWeblink_QC
    IN_CSV_LOOKUP_TABLES_DIR = $(IN_CSV_LOOKUP_TABLES_DIR)
    P-T_ABBR = $(P-T_ABBR)
    URL_VALIDATION = $(URL_VALIDATION)
    WEBLINK_WILDCARD = @Value(id)
    -> SECTOR_MAPPER_NG

Bookmark: Sector Mapper
SECTOR_MAPPER_NG
    FEATURE_TYPE = Sector_QC
    IN_CSV_LOOKUP_TABLES_DIR = $(IN_CSV_LOOKUP_TABLES_DIR)
    P-T_ABBR = $(P-T_ABBR)
    PUBLISHED_OUTPUT -> GEO_NONE_GEO_SELECTOR
    UNMAPPED_OUTPUT -> SECTORS_NOT_MAPPED (writer XLSXW_1)
SECTORS_NOT_MAPPED (writer XLSXW_1)
    attributes: sector auto(20), id auto(20)

Bookmark: spatial data type management
Note: Differenciate Geo and None Geo records based on atrribute values and CV files
GEO_NONE_GEO_SELECTOR
    CSV_FILE_NAME = GeoSpatialValidation
    CSV_PATH = $(IN_CSV_LOOKUP_TABLES_DIR)
    CSV_PROVINCE = $(P-T_ABBR)
    YAML_DIRECTIVES:
      resources{}.format:
        domain: lookup_table_format
        spatial_type: overwrite
        not_found: log
        search_type: equals
      #
      tags{}.display_name:
        domain: [Photographie aérienne,Toponyme,Toponymie,photogrammétrie,GPS,cartographie]
        spatial_type: no_overwrite
        not_found: no_log
        search_type: contains
    GEOSPATIAL -> SPATIAL_TYPE_MAPPER_NG [DATA_INPUT]
    NONE_GEOSPATIAL -> MANUAL_GEOSPATIAL_SETTER_NG [DATA_INPUT]
    LOG_ERROR -> GEOSPATIAL_FORMAT_NOT_MAPPED (writer XLSXW_1)
Note: Uses algorithm to determine spatial_representation_type of dataset
SPATIAL_TYPE_MAPPER_NG
    FEATURE_TYPE = UUID_Spatial_QC
    IN_CSV_LOOKUP_TABLES_DIR = $(IN_CSV_LOOKUP_TABLES_DIR)
    P-T_ABBR = $(P-T_ABBR)
    DATA_OUTPUT_FAILED -> AttributeExposer_5
    DATA_OUTPUT_PASSED -> TestFilter_3
AttributeExposer_5
    ATTR_LIST = id,title,notes
    -> SPATIALTYPE_NOT_MAPPED (writer XLSXW_1)
SPATIALTYPE_NOT_MAPPED (writer XLSXW_1)
    attributes: notes auto(20), title auto(20), id auto(20)
MANUAL_GEOSPATIAL_SETTER_NG
    FEATURE_TYPE = UnmappedGeoData_QC
    IN_CSV_LOOKUP_TABLES_DIR = $(IN_CSV_LOOKUP_TABLES_DIR)
    P-T_ABBR = $(P-T_ABBR)
    GEOSPATIAL -> TestFilter_3
    NON-GEOSPATIAL -> TestFilter_4
    UNMAPPED_DATA -> UNMAPPED_DATA (writer XLSXW_1)
Note: Test non sesible à la case
TestFilter_3
    DEFAULT_VALUE = <UNFILTERED>
    TEST_LIST = "BOOL_OP,OR,COMPOSITE_TEST,""""""1"""""",TEST_CLAUSE,CASE_INSENSITIVE_TEST $(ACTIVATE_GEO) = yes",ACTIVATE_GEO
    ACTIVATE_GEO -> TestFilter
UNMAPPED_DATA (writer XLSXW_1)
    attributes: notes auto(20), title auto(20), id auto(20)
Note: Test non sesible à la case
TestFilter_4
    DEFAULT_VALUE = <UNFILTERED>
    TEST_LIST = "BOOL_OP,OR,COMPOSITE_TEST,""""""1"""""",TEST_CLAUSE,CASE_INSENSITIVE_TEST $(ACTIVATE_NON_GEO) = yes",ACTIVATE_NON_GEO
    ACTIVATE_NON_GEO -> TestFilter_2
GEOSPATIAL_FORMAT_NOT_MAPPED (writer XLSXW_1)
    attributes: format string(8), id string(8)

Bookmark: Samples or full content
TestFilter
    DEFAULT_VALUE = SAMPLES FEATURES
    TEST_LIST = "BOOL_OP,OR,COMPOSITE_TEST,""""""1"""""",TEST_CLAUSE,TEST $(SAMPLE_SIZE) = 0",ALL FEATURES
    ALL FEATURES -> Junction_4
    SAMPLES FEATURES -> Sampler
Sampler
    RATE = $(SAMPLE_SIZE)
    SAMPLE_MODE = No
    SAMPLE_TYPE_LONG = First N Features
    SAMPLED -> Junction_4

Bookmark: Projection and GeoExtents Management
Note: Extracts projection values and bounding box coordinates from url, wms or esri rest, where they exist. Missing projection values are set to unknown
QC_PROJECTION_GEOEXTENTS_EXTRACTOR
    DATA_OUTPUT -> GEO_EXTENTS_MAPPER_NG
Note: Sets geoextents not created in previous transformer based on lookup table values
GEO_EXTENTS_MAPPER_NG
    FEATURE_TYPE = Coord_QC
    IN_CSV_LOOKUP_TABLES_DIR = $(IN_CSV_LOOKUP_TABLES_DIR)
    LATITUDE_MAX = 64
    LATITUDE_MIN = 44
    LONGITUDE_MAX = -56
    LONGITUDE_MIN = -80
    P-T_ABBR = $(P-T_ABBR)
    EXTENT_DEFINED -> METADATA_VALUE_MAPPER_NG [DATA_INPUT]
    UNKNOWN_EXTENT -> GEO_EXTENTS_NOT_MAPPED (writer XLSXW_1)
GEO_EXTENTS_NOT_MAPPED (writer XLSXW_1)
    attributes: location string(20), id auto(20)

Bookmark: Attribute value mapper
Note: Maps update cycle to HNAP standards
METADATA_VALUE_MAPPER_NG
    ATT_TO_MAP = update_frequency
    CODE_REFRESH = YES
    ENGLISH_REFRESH = YES
    ERROR_NOT_MAPPED = YES
    FEATURE_TYPE = Update
    FRENCH_REFRESH = YES
    IN_CSV_LOOKUP_TABLES_DIR = $(IN_CSV_LOOKUP_TABLES_DIR)
    P-T_ABBR = $(P-T_ABBR)
    -> METADATA_VALUE_MAPPER_NG_2 [DATA_INPUT]
Note: Maps progress code to HNAP standards
METADATA_VALUE_MAPPER_NG_2
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUP_TABLES_DIR)
    P-T_ABBR = $(P-T_ABBR)
    -> METADATA_VALUE_MAPPER_NG_3 [DATA_INPUT]
Note: Maps progress code to HNAP standards
METADATA_VALUE_MAPPER_NG_3
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUP_TABLES_DIR)
    P-T_ABBR = $(P-T_ABBR)
    -> METADATA_FORMAT_MAPPER_NG [DATA_INPUT]
Note: Resources.format
METADATA_FORMAT_MAPPER_NG
    ATT_TO_MAP = resources{}.format
    ERROR_NOT_MAPPED = YES
    FEATURE_TYPE = Format
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    -> METADATA_VALUE_MAPPER_ERROR_MANAGER

Bookmark: Mapping error list creator
Note: Creates list of errors found and not corrected in mapping
METADATA_VALUE_MAPPER_ERROR_MANAGER
    ERROR_OUTPUT -> METADATA_MAPPING_ERRORS_GEO (writer XLSXW_1)
    DATA_OUTPUT -> URL_CHARACTER_ENCODER
METADATA_MAPPING_ERRORS_GEO (writer XLSXW_1)
    attributes: error string(200), id string(200), _element_index string(200)

Bookmark: URL Character Encoder
Note: URL's containing {} will not validate. UTF8 value is substituted where they exist.
URL_CHARACTER_ENCODER
    DATA_OUTPUT -> QC_WMS_URL_SETTER [DATA_INPUT]

Bookmark: Samples or full content
TestFilter_2
    DEFAULT_VALUE = SAMPLES FEATURES
    TEST_LIST = "BOOL_OP,OR,COMPOSITE_TEST,""""""1"""""",TEST_CLAUSE,TEST $(SAMPLE_SIZE) = 0",ALL FEATURES
    ALL FEATURES -> Junction
    SAMPLES FEATURES -> Sampler_2
Sampler_2
    RATE = $(SAMPLE_SIZE)
    SAMPLE_MODE = No
    SAMPLE_TYPE_LONG = First N Features
    SAMPLED -> Junction

Bookmark: Non-geospatial processing
METADATA_VALUE_MAPPER_NG_4
    ATT_TO_MAP = update_frequency
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUP_TABLES_DIR)
    P-T_ABBR = $(P-T_ABBR)
    -> AttributeExposer
AttributeExposer
    ATTR_LIST = groups{}.name
    -> ListCopier_2
ListCopier_2
    DEST_LIST = topics
    SRC_LIST = groups{}
    -> METADATA_VALUE_MAPPER_NG_5 [DATA_INPUT]
METADATA_VALUE_MAPPER_NG_5
    ATT_TO_MAP = topics{}.name
    CODE_REFRESH = NO
    ENGLISH_REFRESH = YES
    ERROR_NOT_MAPPED = YES
    FEATURE_TYPE = Topic_TBS
    FRENCH_REFRESH = NO
    IN_CSV_LOOKUP_TABLES_DIR = $(IN_CSV_LOOKUP_TABLES_DIR)
    P-T_ABBR = $(P-T_ABBR)
    -> AttributeExposer_2
AttributeExposer_2
    ATTR_LIST = topics{}.name
    -> ListDuplicateRemover
ListDuplicateRemover
    SRC_LIST = topics{}.name
    -> AttributeExposer_10
AttributeExposer_10
    ATTR_LIST = groups{}.name
    -> ListCopier_3
ListCopier_3
    DEST_LIST = subjects
    SRC_LIST = groups{}
    -> METADATA_VALUE_MAPPER_NG_6 [DATA_INPUT]
METADATA_VALUE_MAPPER_NG_6
    ATT_TO_MAP = subjects{}.name
    CODE_REFRESH = NO
    ENGLISH_REFRESH = YES
    ERROR_NOT_MAPPED = YES
    FEATURE_TYPE = Subject_TBS
    FRENCH_REFRESH = NO
    IN_CSV_LOOKUP_TABLES_DIR = $(IN_CSV_LOOKUP_TABLES_DIR)
    P-T_ABBR = $(P-T_ABBR)
    -> AttributeExposer_13
AttributeExposer_13
    ATTR_LIST = subjects{}.name
    -> ListDuplicateRemover_2
ListDuplicateRemover_2
    SRC_LIST = subjects{}.name
    -> METADATA_FORMAT_MAPPER_NG_2 [DATA_INPUT]
Note: Format
METADATA_FORMAT_MAPPER_NG_2
    ATT_TO_MAP = resources{}.format
    ERROR_NOT_MAPPED = YES
    FEATURE_TYPE = Format_TBS
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    -> METADATA_VALUE_MAPPER_ERROR_MANAGER_2
Note: Creates list of errors found and not corrected in mapping
METADATA_VALUE_MAPPER_ERROR_MANAGER_2
    ERROR_OUTPUT -> METADATA_MAPPING_ERRORS_NON_GEO (writer XLSXW_1)
    DATA_OUTPUT -> METADATA_DELTA_FINDER_NG_2
METADATA_DELTA_FINDER_NG_2
    ABSTRACT_ATT_NEW = notes
    ABSTRACT_ATT_REF = notes_translated.fr
    DATESTAMP_ATT_NEW = record_last_modified
    DATESTAMP_ATT_REF = federated_date_modified
    ID_ATT_NEW = id
    ID_ATT_REF = id
    LOCAL_SOURCE = Yes
    LOCAL_SOURCE_DIR = $(OUT_JSON_LOCAL_DIR)
    LOCAL_SOURCE_FORMAT = JSON
    METADATA_OVERWRITE = $(METADATA_OVERWRITE)
    RES_FORMAT_ATT_NEW = resources{}.format
    RES_FORMAT_ATT_REF = resources{}.format
    RES_NAME_ATT_NEW = resources{}.name
    RES_NAME_ATT_REF = resources{}.name_translated.fr
    RES_URL_ATT_NEW = resources{}.url
    RES_URL_ATT_REF = resources{}.url
    TITLE_ATT_NEW = title
    TITLE_ATT_REF = title_translated.fr
    Statistics -> StatisticsCalculator_Summary_3
    Update -> Junction_6
    Insert -> Junction_6
    Delete -> AttributeExposer_11
Note: Log statistics
StatisticsCalculator_Summary_3: Logger
    LOG_FEATURE = NONE
    MAXFEATS = 20
    MESSAGE:
      ************************
      **** NoneGeo Features: Unchanged Report ****
      ************************

      @Value(_real_count) features were unchanged

      ************************
      ************************
      ************************
    SEVERITY = INFO
Junction_6
    -> AWS_TRANSLATE_2
Note: Translates specific items from French to English
AWS_TRANSLATE_2
    ACTIVATE_TRANSLATION = $(ACTIVATE_TRANSLATION)
    ATTR_2_TRANSLATE = notes,title
    ATTR_LIST_2_TRANSLATE = tags{}.display_name,resources{}.name
    MODE = French-->English
    -> JSON_PUBLISHER_NG
    TRANSLATION_PROBLEM -> AttributeExposer_12
JSON_PUBLISHER_NG
    FEATURE_TYPE = JSON_CONFIG_QC
    IN_CSV_LOOKUP_TABLES_DIR = $(IN_CSV_LOOKUP_TABLES_DIR)
    JSON_RESOURCE_TEMPLATE = $(IN_TBS_JSON_TEMPLATE_DIR)\TBS_RESOURCES_TEMPLATE_NG.json
    JSON_ROOT_TEMPLATE = $(IN_TBS_JSON_TEMPLATE_DIR)\TBS_ROOT_TEMPLATE_NG.json
    Keywords_EN = tags{}.display_name_en
    Keywords_FR = tags{}.display_name
    P-T_ABBR = $(P-T_ABBR)
    Subject_LIST = subjects{}.name
    Topic_LIST = topics{}.name
    OUTPUT_LOCAL -> AttributeExposer_4
AttributeExposer_4
    ATTR_LIST = json_file,id
    -> AttributeCreator_6
AttributeCreator_6
    ATTR_TABLE = SET_TO text_line_data = @Value(json_file)
    -> text_line (writer TEXTLINE_4)
text_line (writer TEXTLINE_4)
    attributes: text_line_data buffer
AttributeExposer_12
    ATTR_LIST = id,title
    -> translation_problems_NONE_GEO (writer XLSXW_1)
translation_problems_NONE_GEO (writer XLSXW_1)
    attributes: id auto(20), title auto(20)
AttributeExposer_11
    ATTR_LIST = id,title
    -> DELETED_RECORDS_NONE_GEO (writer XLSXW_1)
Note: Log deleted features
DELETED_RECORDS_NONE_GEO (writer XLSXW_1)
    attributes: id auto(20), title auto(20)
METADATA_MAPPING_ERRORS_NON_GEO (writer XLSXW_1)
    attributes: error string(200), id string(200), _element_index string(200)

Bookmark: QC_WMS_URL_SETTER
LOOKUP_TABLES_READER_NG
    CSV_ENCODING = utf-8
    CSV_PATH = $(IN_CSV_LOOKUP_TABLES_DIR)
    FEATURE_TYPE = WMS_URL_QC
    PT = $(P-T_ABBR)
    -> QC_WMS_URL_SETTER [LOOKUP_TABLE_INPUT]
QC_WMS_URL_SETTER
    -> REMOVE_BROKEN_URL_WMS_ESRI_REST

Bookmark: Data cleanup. Dropping broken web services
Note: Tests WMS/ESRI_REST resource URL's and removes them where broken
REMOVE_BROKEN_URL_WMS_ESRI_REST
    URL_VALIDATION = Yes
    -> WMS_REST_LANGUAGE_FORMATTER
    FAULTY_URL_OUTPUT -> MAP_SERVICE_URL_ERROR (writer XLSXW_1)
MAP_SERVICE_URL_ERROR (writer XLSXW_1)
    attributes: id auto(20), format string(8), url auto(20), _url_failure_message auto(20)

Bookmark: HNAP Rules- 1 web service per language.
Note: Formats WMS and ESRI REST resources to add French versions and formats French and English versions with valid supporting attributes
WMS_REST_LANGUAGE_FORMATTER
    -> DUPLICATE_SERVICE_REMOVER
Note: Removes duplicate WMS or ESRI REST resources where they exist, that would otherwise invalidate the dataset
DUPLICATE_SERVICE_REMOVER
    -> RESOURCE_NAME_UNDERSCORE_REMOVER

Bookmark: Data preparation for metadata section
Note: Removes all underscores from resources{}.name attributes. Long compounded names joined by underscores in this field can cause display formatting issues when published to the FGP.
RESOURCE_NAME_UNDERSCORE_REMOVER
    DATA_OUTPUT -> AttributeExposer_9
AttributeExposer_9
    ATTR_LIST = resources{}
    -> ListCopier
ListCopier
    DEST_LIST = distributionList
    SRC_LIST = resources{}
    -> GMD_SECTION_DATA_EXTRACTION
Note: Creates lists and removes duplicates for GMD_Section
GMD_SECTION_DATA_EXTRACTION
    -> MORE_INFO_MANAGER
Note: Tests the more_info{}.link list for valid attribute values and filters them out where missing
MORE_INFO_MANAGER
    -> MAP_RESOURCE_ATTRIBUTION_REMOVER_NG
MAP_RESOURCE_ATTRIBUTION_REMOVER_NG
    FEATURE_TYPE = MAP_RES_REMOVE_QC
    IN_CSV_LOOKUP_TABLES_DIR = $(IN_CSV_LOOKUP_TABLES_DIR)
    P-T_ABBR = $(P-T_ABBR)
    -> PythonCaller

Bookmark: Pregenrate formating for ressources description
PythonCaller
    NEW_ATTRIBUTES = resources{}.description_temp
    PYTHONSOURCE:
      import fme
      import fmeobjects
      # Template Function interface:
      # When using this function, make sure its name is set as the value of
      # the 'Class or Function to Process Features' transformer parameter
      def processFeature(feature):
          lang=feature.getAttribute('transfer_option_description_language')

          for i in range(len(feature.getAttribute('resources{}.url'))):
              format=feature.getAttribute('resources{%i}.format'%(i))
              restype=feature.getAttribute('resources{%i}.format_resourceType_en'%(i))

              feature.setAttribute('resources{%i}.description_temp'%(i),'%s;%s;%s'%(restype,format,lang))
    PYTHONSYMBOL = processFeature
    -> AttributeCreator

Bookmark: Configuring publishing info
AttributeCreator
    ATTR_TABLE = SET_TO csw_url = $(FORCED_PYCSW_URL)
    -> AttributeExposer_7
AttributeExposer_7
    ATTR_LIST = search_criteria_pycsw,csw_url
    -> METADATA_DELTA_FINDER_NG
METADATA_DELTA_FINDER_NG
    ABSTRACT_ATT_NEW = notes
    ABSTRACT_ATT_REF = MD_Metadata.identificationInfo.MD_DataIdentification.abstract.PT_FreeText.textGroup.LocalisedCharacterString
    CSW_FILTER = @Value(search_criteria_pycsw)
    CUSTOM_CSW_CKAN_URL = @Value(csw_url)
    DATESTAMP_ATT_NEW = record_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    METADATA_OVERWRITE = $(METADATA_OVERWRITE)
    RES_FORMAT_ATT_NEW = resources{}.description_temp
    RES_FORMAT_ATT_REF = MD_Metadata.distributionInfo.MD_Distribution.transferOptions{}.MD_DigitalTransferOptions.onLine.CI_OnlineResource.description.CharacterString
    RES_NAME_ATT_NEW = resources{}.name
    RES_NAME_ATT_REF = MD_Metadata.distributionInfo.MD_Distribution.transferOptions{}.MD_DigitalTransferOptions.onLine.CI_OnlineResource.name.PT_FreeText.textGroup.LocalisedCharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.PT_FreeText.textGroup.LocalisedCharacterString
    Statistics -> StatisticsCalculator_Summary_2
    Update -> Junction_5
    Insert -> Junction_5
    Delete -> AttributeExposer_15
Note: Log statistics
StatisticsCalculator_Summary_2: Logger
    LOG_FEATURE = NONE
    MAXFEATS = 20
    MESSAGE:
      ************************
      **** Geo Features: Unchanged Report ****
      ************************

      @Value(_real_count) features were unchanged

      ************************
      ************************
      ************************
    SEVERITY = INFO
Junction_5
    -> AWS_TRANSLATE
AttributeExposer_15
    ATTR_LIST = id,title
    -> DELETED_RECORDS_GEO (writer XLSXW_1)
Note: Log deleted features
DELETED_RECORDS_GEO (writer XLSXW_1)
    attributes: id auto(20), title auto(20)

Bookmark: Language Translation
Note: Translates specific items from French to English
AWS_TRANSLATE
    ACTIVATE_TRANSLATION = $(ACTIVATE_TRANSLATION)
    ATTR_2_TRANSLATE = notes,title
    ATTR_LIST_2_TRANSLATE = tags{}.display_name,resources{}.name
    MODE = French-->English
    -> XML_PUBLISHER_NG
    TRANSLATION_PROBLEM -> AttributeExposer_14
AttributeExposer_14
    ATTR_LIST = id,title
    -> translation_problems_GEO (writer XLSXW_1)
translation_problems_GEO (writer XLSXW_1)
    attributes: id auto(20), title auto(20)

Bookmark: XML CREATION AND WRITING
Note: CSV config file to map QC attributes to those required by XML templates
XML_PUBLISHER_NG
    FEATURE_TYPE = Config_QC
    IN_CSV_LOOKUP_TABLES_DIR = $(IN_CSV_LOOKUP_TABLES_DIR)
    LOCAL_WRITER = $(LOCAL_WRITER)
    P-T_ABBR = $(P-T_ABBR)
    TEMPLATE_GMD_CITEDRESPONSIBLEPARTY = $(IN_GMD_XML_TEMPLATE_DIR)\GMD_CITEDRESPONSIBLEPARTY.xml
    TEMPLATE_GMD_CONTACT = $(IN_GMD_XML_TEMPLATE_DIR)\GMD_CONTACT.xml
    TEMPLATE_GMD_DISTRIBUTIONFORMAT = $(IN_GMD_XML_TEMPLATE_DIR)\GMD_DISTRIBUTIONFORMAT.xml
    TEMPLATE_GMD_DISTRIBUTOR = $(IN_GMD_XML_TEMPLATE_DIR)\GMD_DISTRIBUTOR.xml
    TEMPLATE_GMD_KEYWORDS = $(IN_GMD_XML_TEMPLATE_DIR)\GMD_KEYWORDS.xml
    TEMPLATE_GMD_MDMETADATA = $(IN_GMD_XML_TEMPLATE_DIR)\GMD_MDMETADATA.xml
    TEMPLATE_GMD_REFERENCESYSTEMINFO = $(IN_GMD_XML_TEMPLATE_DIR)\GMD_REFERENCESYSTEMINFO.xml
    TEMPLATE_GMD_RESOURCEMAINTENANCE = $(IN_GMD_XML_TEMPLATE_DIR)\GMD_RESOURCEMAINTENANCE.xml
    TEMPLATE_GMD_TOPICCATEGORY = $(IN_GMD_XML_TEMPLATE_DIR)\GMD_TOPICCATEGORY.xml
    TEMPLATE_GMD_TRANSFEROPTIONS = $(IN_GMD_XML_TEMPLATE_DIR)\GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    InvalidMetadata -> invalid_metadata (writer XLSXW_1)
    UPDATE_FAILED -> text_line (writer TEXTLINE_2)
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
invalid_metadata (writer XLSXW_1)
    attributes: id auto(20)

FME custom transformer GEOSPATIAL_DATA_VALIDATOR
Description 
This custom transformer fan out the metadata records between three types of metadata (GeoSpatial, Non GeoSpatial and Unknown).  In order to determine the type of metadta record, the transformer is using two strategies: firstly by checking if the format has been published in the FGP (if positive it is a GeoSpatial record); secondly by checking the content of a list of keywords againts the content of an attribute in the metadata record (if there is a match it is a GeoSpatial record) 
Input Ports 
LOOKUP_TABLE_INPUT: Input information from the lookup table
DATA_INPUT: The input metadata records to process.
Output Ports 
GEOSPATIAL: Output port for all gepspatial metadata record
NON-GEOSPATIAL: Output port for all non geospatial metadata record
UNKNOWN_FORMAT: Output port for metadata record that cannot be mapped to geospatial or non geospatial
Parameters 
KEYWORD_SEARCH: List of keywords used to determine if a metadata record is geospatial.  If more than one keyword is needed, separate each keyword with a vertical bar "|"
LIST_SEARCH_ATTRIBITE: Name of the attribute in plain text (ex.: tag{}.display_name) used to search for a string match from the KEYWORD_SEARCH parameter

Parameters:
- KEYWORD_SEARCH =
- LIST_SEARCH_ATTRIBUTE =

LOOKUP_TABLE_INPUT (input)
    -> AttributeExposer_2
INPUT (input)
    -> AttributeExposer
UNKNOWN_FORMAT (output)
GEOSPATIAL (output)
NON-GEOSPATIAL (output)

Bookmark: Excel file validation
Note: Exposes attributes from lookup table
AttributeExposer_2
    ATTR_LIST = fgp_publish,format,spatial_type
    -> Tester_2
Note: Tests for value in required fields
Tester_2
    BOOL_OP = OR
    COMPOSITE_TEST = 1 OR 2
    TEST_CLAUSE:
      TEST fgp_publish ATTRIBUTE_HAS_A_VALUE ""
      TEST format ATTRIBUTE_HAS_A_VALUE ""
    TEST_MODE = TEST
    PASSED -> DuplicateFilter
    FAILED -> Terminator
Terminator
    MESSAGE = Missing values in fgp_publish or format attributes, Geospatial lookup table, GEOSPATIAL_DATA_VALIDATOR transformer.  Translation terminated.
Note: Tests for duplicates of 'format' attribute
DuplicateFilter
    INPUT_ORDERED_CHOICE = No
    KEYATTR = format
    UNIQUE -> Tester
    DUPLICATE -> Terminator_2
Terminator_2
    MESSAGE = Duplicate feature @Value(format) found in format attribute in Geospatial lookup table, GEOSPATIAL_DATA_VALIDATOR transformer.  Translation terminated.
Note: Validates 'spatial_type' attribute format.
Tester
    BOOL_OP = OR
    COMPOSITE_TEST = 1 OR 2 OR 3 OR 4
    TEST_CLAUSE:
      TEST @Value(spatial_type) = a-grid
      TEST @Value(spatial_type) = b-vector
      TEST @Value(spatial_type) = c-textTable
      TEST spatial_type NOT_ATTRIBUTE_HAS_A_VALUE ""
    TEST_MODE = TEST
    PASSED -> StringCaseChanger_2
    FAILED -> Terminator_3
Terminator_3
    MESSAGE = spatial_type attribute value @Value(spatial_type) from Geospatial lookup table is invalid in GEOSPATIAL_DATA_VALIDATOR transformer.  Value must be 'a-grid', 'b-vector','c-textTable' or value must be empty.  Translation terminated.
Note: Putting format and fgp_publish in lower case
StringCaseChanger_2
    ATTRCHOICE = Selected Attributes
    ATTRLIST = fgp_publish format
    CHANGE_TYPE = lowercase
    -> FeatureMerger [SUPPLIER]

Bookmark: Geospatial Data Validator
Note: Exposes attributes from incoming data
AttributeExposer
    ATTR_LIST = resources{}.format,tags{}.display_name,id,resources{}.url,resources{}.name,notes,title,resources{}.fgp_publish
    -> UUIDGenerator
Note: Creates unique ID for rejoining data
UUIDGenerator
    UUID_ATTR = _uuid
    -> AttributeRenamer
    -> ListElementCounter
Note: Rename 'id' to 'original_id' as not to conflict with resources{}.id when resources{} list is exploded
AttributeRenamer
    ATTR_TABLE = RENAME_SET_DEFAULT id > orig_id
    -> AttributeKeeper
Note: Retains _uuid, original_id and resources{} list only
AttributeKeeper
    KEEP_ATTRS = notes,title,orig_id,_uuid
    KEEP_LIST = resources{}
    -> ListExploder
Note: Explodes resources{} list
ListExploder
    ATTR_ACCUM_MODE = Merge List Attributes
    ATTR_CONFLICT_RES = Use List Attribute Values
    INDEX_ATTR = _element_index
    LIST_ATTR = resources{}
    ELEMENTS -> Tester_3
    <REJECTED> -> Cloner
Tester_3
    BOOL_OP = OR
    COMPOSITE_TEST = 1
    TEST_CLAUSE = TEST @LowerCase(@Value(fgp_publish)) = oui
    TEST_MODE = TEST
    PASSED -> StringCaseChanger
    FAILED -> AttributeRemover_3
AttributeRemover_3
    REMOVE_ATTRS = fgp_publish
    -> StringCaseChanger
Note: Putting format in lowercasse
StringCaseChanger
    ATTRCHOICE = Selected Attributes
    ATTRLIST = format
    CHANGE_TYPE = lowercase
    -> FeatureMerger [REQUESTOR]
Note: Joins lookup table and feature data on value 'format'
FeatureMerger
    ATTR_ACCUM_MODE = Merge Supplier
    ATTR_CONFLICT_RES = Use Requestor
    IGNORE_NULLS = No
    JOIN_KEYS = @Value(format) @Value(format) AUTO
    MERGE_TYPE = Attributes Only
    PROCESS_DUPS = NO
    REJECT_NULL_MISSING_KEYS = No
    SUPPLIERS_FIRST = No
    MERGED -> FeatureMerger_2 [SUPPLIER]
    UNMERGED_REQUESTOR -> AttributeRenamer_2
    <REJECTED> -> Terminator_4
Terminator_4
    MESSAGE = Process failed at Feature Merger, GEOSPATIAL_DATA_VALIDATOR transformer.  Translation terminated.
Note: Rename 'orignal_id' back to 'id'
AttributeRenamer_2
    ATTR_TABLE = RENAME_SET_DEFAULT orig_id > id
    -> Logger
Logger
    LOG_FEATURE = LOG_ONLY
    MAXCOORDS = 20
    MAXFEATS = 20
    MESSAGE = Attribute value @Value(format) missing from Geospatial lookup table in GEOSPATIAL_DATA_VALIDATOR transformer.  See PROCESS_REPORT_MANUAL_TASKS.xls file in XLS directory for details.
    SEVERITY = WARN
    LOGGED -> AttributeKeeper_2
Note: Retains 'id' and 'format' for unmapped output file
AttributeKeeper_2
    KEEP_ATTRS = id,format
    -> UNKNOWN_FORMAT (output)
Cloner
    COPIES = 1
    COPYATT = _copynum
Note: Compter le nombre de ressource avec la vaidation
ListElementCounter
    CNT_ATTR = _nb_res_avant
    LIST_NAME = resources{}
    -> AttributeRemover
Note: Removes resources{} list
AttributeRemover
    LIST_ATTRS = resources{}
    -> FeatureMerger_2 [REQUESTOR]
Note: Rejoins data on _uuid attribute and rebuilds resources{} list
FeatureMerger_2
    ATTR_ACCUM_MODE = Merge Supplier
    ATTR_CONFLICT_RES = Use Requestor
    IGNORE_NULLS = No
    JOIN_KEYS = @Value(_uuid) @Value(_uuid) AUTO
    LIST_NAME = resources
    MERGE_TYPE = Attributes Only
    PROCESS_DUPS = NO
    REJECT_NULL_MISSING_KEYS = No
    SUPPLIERS_FIRST = No
    MERGED -> ListElementCounter_2
    <REJECTED> -> Terminator_5
ListElementCounter_2
    CNT_ATTR = _nb_res_apres
    LIST_NAME = resources{}
    -> Tester_4
Note: Uniquement les entités ayant le même nombre de ressource avant/apres / Si le nombre change, cela indique que des formats sont inconnus
Tester_4
    BOOL_OP = OR
    COMPOSITE_TEST = 1
    TEST_CLAUSE = TEST @Value(_nb_res_avant) = @Value(_nb_res_apres)
    TEST_MODE = TEST
    PASSED -> ListSearcher_2
Note: Searches resources{}.fgp_publish list for value 'Oui' for publishing
ListSearcher_2
    ATTR_VALUE = oui
    INDEX_ATTR = _list_index
    LIST_ATTR = resources{}.fgp_publish
    MATCHTYPE = REGULAR_EXPRESSION_ENCODED
    FOUND -> AttributeRemover_4
    NOT_FOUND -> ListSearcher
Note: Secondary list search. Searches on tags{}.display_name for BC and QC data and resources{}.contains_geographic_markers for ON data. LIST_SEARCH_ATTRIBUTE is the list attribute to be searched, KEYWORD_SEARCH represents the value(s).
ListSearcher
    ATTR_VALUE = $(KEYWORD_SEARCH)
    INDEX_ATTR = _list_index
    LIST_ATTR = $(LIST_SEARCH_ATTRIBUTE)
    MATCHTYPE = REGULAR_EXPRESSION_ENCODED
    FOUND -> AttributeRemover_4
    NOT_FOUND -> AttributeRemover_2
Note: Attribute cleanup
AttributeRemover_4
    LIST_ATTRS = resources{}._element_index resources{}._uuid resources{}.fgp_publish
    REMOVE_ATTRS = _element_index,format,_list_index,fgp_publish,_uuid
    -> ATTRIBUTE_UNEXPOSER
ATTRIBUTE_UNEXPOSER
    -> GEOSPATIAL (output)
Note: Attribute cleanup
AttributeRemover_2
    LIST_ATTRS = resources{}._element_index resources{}._uuid resources{}.fgp_publish
    REMOVE_ATTRS = _uuid,_element_index,format,fgp_publish
    -> ATTRIBUTE_UNEXPOSER_2
ATTRIBUTE_UNEXPOSER_2
    -> NON-GEOSPATIAL (output)
Terminator_5
    MESSAGE = Process failed at Feature Merger_2, GEOSPATIAL_DATA_VALIDATOR transformer.  Translation terminated.

FME custom transformer MAP_RESOURCE_ATTRIBUTION_REMOVER
Description 
This transformer tests if the ressources{}.url from the metadata records are present in the lookup table, if yes then it sets the xlink_role and protocol attributes
Input Ports 
URL: URL from the lookup table.
INPUT: Input metadata records to process.
Output Ports 
OUTPUT: The process output metdata records.
Parameters 
NONE

URL (input)
    -> AttributeExposer_2
AttributeExposer_2
    ATTR_LIST = url
    -> AttributeCreator
Note: Sorting order
AttributeCreator
    ATTR_TABLE = SET_TO _type = A
    -> Sorter
Input (input)
    -> AttributeExposer
AttributeExposer
    ATTR_LIST = resources{}.url
    -> ListElementCounter
Note: Count number of ressources{} occurrences
ListElementCounter
    CNT_ATTR = _element_count
    LIST_NAME = resources{}
    -> AttributeCreator_2
Note: Sorting order
AttributeCreator_2
    ATTR_TABLE = SET_TO _type = B
    -> Sorter
Note: Sort lookup table entry firstly. Metadata records secondly.
Sorter
    SORT_PARM = _type ALPHA ASCENDING
    SORTED -> PythonCaller
Note: Check if URL from the ressources{}.url is present in the looup table and set some attributes
PythonCaller
    PYTHONSOURCE:
      import fme
      import fmeobjects
      # Template Function interface:
      # When using this function, make sure its name is set as the value of
      # the 'Class or Function to Process Features' transformer parameter

      class FeatureProcessor(object):
          def __init__(self):
              self.url=[]

          def input(self,feature):
              # If the url of the ressources is present in the lookup table set some attributes

              if feature.getAttribute('_type')=='A':
                  #Adding URL from the llokup tablein the list
                  self.url.append(feature.getAttribute('url'))

              else:

                  if int(feature.getAttribute('_element_count'))>0:
                      for i in range(int(feature.getAttribute('_element_count'))):
                          url=feature.getAttribute('resources{%d}.url'%(i))
                          if url in self.url:
                              feature.setAttribute('resources{%d}.xlink_role'%(i),'')
                              feature.setAttribute('resources{%d}.protocol'%(i),'HTTPS')

                  # Release the feature
                  self.pyoutput(feature)

          def close(self):
              pass
    PYTHONSYMBOL = FeatureProcessor
    -> ATTRIBUTE_UNEXPOSER
ATTRIBUTE_UNEXPOSER
    -> Output (output)
Output (output)
