FME workspace QC_FGP_XML_BUILDER_DEV_08.fmw
Title: QC_FGP_XML_BUILDER
Description: Description 
This workbench read and trasform all the metadata for the province of Québec (QC)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
P_T_ABBR: Two letter abbreviation code of the province or terrirtory (ex.: ON, QC, ...).
PYCSW_CKAN_OVERWRITE: Enable the overwite of the PyCSW.  Can take two values: Yes: Overwrite the contentof the PyCSW; No: Do no overwrite the content of the PyCSW.
ROOT_IN_DIR: Root input directory used to define the following private parameters:
IN_CSV_LOOKUP_TABLES_DIR: Source directory of the root of the lookup table files. Defined as: $(ROOT_IN_DIR)\LOOKUP_TABLES
IN_GMD_XML_TEMPLATES_DIR: Source directory of the root XML templates. Defined as: $(ROOT_IN_DIR)\XML_TEMPLATES
INJSON_TEMPLATE_DIR: Source directory of the root JSON templates. Defined as: $(ROOT_IN_DIR)\JSON_TEMPLATES
ROOT_OUT_DIR: Root output root directory used to define the following private parameters:
LOG_FILE: Output log file. Defined as: $(ROOT_OUT_DIR)\$(P-T_ABBR)\LOG\$(P-T_ABBR).log
OUT_JSON_LOCAL_DIR: Source directory to output JSON files. Defined as: $(ROOT_OUT_DIR)\$(P-T_ABBR)\JSON_LOCAL
OUT_XLS_NOTIFICATION: Source directory to output excel files. Defined as: $(ROOT_OUT_DIR)\$(P-T_ABBR)\XLS
OUT_XML_FAILED_DIR: Source directory to output failed XML files. Defined as: $(ROOT_OUT_DIR)\$(P-T_ABBR)\XML_FAILED
OUT_XML_LOCAL_DIR: Source directory to output Local Source XML files. Defined as: $(ROOT_OUT_DIR)\$(P-T_ABBR)\XML_LOCAL
OUT_XML_PASSED_DIR: Source directory to output passedXML files. Defined as: $(ROOT_OUT_DIR)\$(P-T_ABBR)\XML_PASSED
SAMPLE_SIZE: Number of features to process. Zero (0) means process all the features. A number n greater than 0 means sample or process only the first n features.
Startup Python:
      import sys
      import fme
      try:
          if fme.macroValues['FME_SHAREDRESOURCE_DATA']:
              new_path='%s\PT_Harvester\Python'%(fme.macroValues['FME_SHAREDRESOURCE_DATA'])

              print ('Ajout de %s dans le path '%(new_path))
              sys.path += [new_path]


      except:
          raise

Parameters:
- ACTIVATE_GEO = Yes
- ACTIVATE_NON_GEO = Yes
- ACTIVATE_TRANSLATION = No
- CATALOGUE_READER_SELECT = Yes
- FORCED_PYCSW_URL = https://pycsw.ddr-stage.services.geo.ca/pycsw?
- IN_FFS_TESTING_FILE = $(FME_MF_DIR)post_catalogue_reader.ffs
- LOCAL_SOURCE_METADATA_DELTA_FINDER = Yes
- LOCAL_WRITER = Yes
- P-T_ABBR = QC
- PYCSW_CKAN_OVERWRITE = YES
- ROOT_IN_DIR =
- ROOT_OUT_DIR =
- SAMPLE_SIZE = 0
- URL_VALIDATION = No
- IN_CSV_LOOKUP_TABLES_DIR = $(ROOT_IN_DIR)\FME_files\LOOKUP_TABLES   # DEFAULT_IN_CSV_LOOKUP_TABLES_DIR
- IN_GMD_XML_TEMPLATE_DIR = $(ROOT_IN_DIR)\XML_TEMPLATES
- LOG_FILE = $(ROOT_OUT_DIR)\$(P-T_ABBR)\LOG\$(P-T_ABBR).log
- OUT_JSON_LOCAL_DIR = $(ROOT_OUT_DIR)\$(P-T_ABBR)\JSON_LOCAL
- OUT_XLS_NOTIFICATION_DIR = $(ROOT_OUT_DIR)\$(P-T_ABBR)\XLS
- OUT_XML_FAILED_DIR = $(ROOT_OUT_DIR)\$(P-T_ABBR)\XML_FAILED
- OUT_XML_LOCAL_DIR = $(ROOT_OUT_DIR)\$(P-T_ABBR)\XML_LOCAL
- OUT_XML_PASSED_DIR = $(ROOT_OUT_DIR)\$(P-T_ABBR)\XML_PASSED
- IN_TBS_JSON_TEMPLATE_DIR = $(ROOT_IN_DIR)\JSON_TEMPLATES
- FME_SHAREDRESOURCE_DATA = C:\Data   # FME Server Resource Data

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(OUT_XLS_NOTIFICATION_DIR)
- TEXTLINE_4: TEXTLINE to $(OUT_JSON_LOCAL_DIR)

Recorder_2
    COMPRESSION_LEVEL = 6
    CREATE_SPATIAL_INDEX = No
    MODE = RECORD_PASS_THROUGH
    RECFILE = $(FME_MF_DIR)post_qc_missing_mapper.ffs
    STORE_SCANNED_METADATA = No
    STORE_SCANNED_SCHEMA = No
Player [off]
    FEAT_TYPE_ATTR = fme_feature_type
    RECFILE = $(FME_MF_DIR)post_qc_missing_mapper.ffs
    PLAYED_BACK -> AttributeExposer_8
AttributeExposer_8
    ATTR_LIST = id
    -> GEOPORTAL_WEBLINK_ADDER_NG
Note: Validate web link
GEOPORTAL_WEBLINK_ADDER_NG
    FEATURE_TYPE = GeoportalWeblink_QC
    IN_CSV_LOOKUP_TABLES_DIR = $(IN_CSV_LOOKUP_TABLES_DIR)
    P-T_ABBR = $(P-T_ABBR)
    URL_VALIDATION = $(URL_VALIDATION)
    WEBLINK_WILDCARD = @Value(id)
    -> QC_SECTOR_MAPPER_AND_FILTER
Recorder_5
    COMPRESSION_LEVEL = 6
    CREATE_SPATIAL_INDEX = No
    MODE = RECORD_PASS_THROUGH
    RECFILE = $(FME_MF_DIR)post_qc_sector_mapper_and_fileter.ffs
    STORE_SCANNED_METADATA = No
    STORE_SCANNED_SCHEMA = No
Player_4 [off]
    FEAT_TYPE_ATTR = fme_feature_type
    RECFILE = $(FME_MF_DIR)post_qc_sector_mapper_and_fileter.ffs
    PLAYED_BACK -> GEO_NONE_GEO_SELECTOR
Junction_4
    -> QC_PROJECTION_GEOEXTENTS_EXTRACTOR
Recorder_3
    COMPRESSION_LEVEL = 6
    CREATE_SPATIAL_INDEX = No
    MODE = RECORD_PASS_THROUGH
    RECFILE = $(FME_MF_DIR)post_qc_projection_geoextents_extractor.ffs
    STORE_SCANNED_METADATA = No
    STORE_SCANNED_SCHEMA = No
Junction
    -> AttributeExposer_2
Player_2 [off]
    FEAT_TYPE_ATTR = fme_feature_type
    RECFILE = $(FME_MF_DIR)post_qc_projection_geoextents_extractor.ffs
    PLAYED_BACK -> GEO_EXTENTS_MAPPER_NG
Recorder_4
    COMPRESSION_LEVEL = 6
    CREATE_SPATIAL_INDEX = No
    MODE = RECORD_PASS_THROUGH
    RECFILE = $(FME_MF_DIR)pre_pycsw_url_mapper.ffs
    STORE_SCANNED_METADATA = No
    STORE_SCANNED_SCHEMA = No
Player_3 [off]
    FEAT_TYPE_ATTR = fme_feature_type
    RECFILE = $(FME_MF_DIR)pre_pycsw_url_mapper.ffs
    PLAYED_BACK -> PYCSW_URL_MAPPER_NG
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer

Bookmark: Reading QC Geoportal datasets
Creator
    GEOMTYPE = Geometry Object
    NUM = 1
    CREATED -> Tester_3
Tester_3
    BOOL_OP = OR
    COMPOSITE_TEST = 1
    TEST_CLAUSE = TEST $(CATALOGUE_READER_SELECT) = Yes
    TEST_MODE = TEST
    PASSED -> Catalogue_Reader
    FAILED -> FeatureReader [INITIATOR]
Note: Reading QC CKAN-API
Catalogue_Reader: Catalogue Reader
    CUSTOM_CSW_LIST_NAME = DefaultNoList{}
    CUSTOM_URL = https://www.donneesquebec.ca/recherche/api/action
    IDENTIFIANT = 1dad27d7-5111-49bb-8809-a8d3e86ad9ce
    SOURCE_URL = Manuel
    Résultats -> BulkAttributeRenamer
    Résultats -> Recorder
Note: Read CKAN data strored in the FFS file
FeatureReader
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> ATTRIBUTE_VALUE_TEXT_CLEANER

Bookmark: Data extraction
Recorder
    COMPRESSION_LEVEL = 6
    CREATE_SPATIAL_INDEX = No
    MODE = RECORD_PASS_THROUGH
    RECFILE = $(FME_MF_DIR)post_catalogue_reader.ffs
    STORE_SCANNED_METADATA = No
    STORE_SCANNED_SCHEMA = No
BulkAttributeRenamer
    ATTRCHOICE = All Attributes
    CASE_DISP = YES
    MODE_CHOICE = RENAME
    PATTERN_ACTION_DISP = REMOVEPREFIX
    REPLACE_STR = result.
    -> ATTRIBUTE_VALUE_TEXT_CLEANER

Bookmark: Filtering and convertion to inhouse model.
Note: Basic cleaning of the different attributes
ATTRIBUTE_VALUE_TEXT_CLEANER
    -> QC_ATTRIBUTE_MAPPER
Note: Exposes and sets attribute names extracted from CKAN-API
QC_ATTRIBUTE_MAPPER
    -> AttributeExposer_3
AttributeExposer_3
    ATTR_LIST = license_id
    -> LICENSE_FILTER_NG
Note: Filter the records accordint to the type of license
LICENSE_FILTER_NG
    FEATURE_TYPE = License_QC
    IN_CSV_LOOKUP_TABLES_DIR = $(IN_CSV_LOOKUP_TABLES_DIR)
    LICENSE_ATT = @Value(license_id)
    P-T_ABBR = $(P-T_ABBR)
    LICENSE_FILTER_PASSED -> QC_DATE_FORMATTER
    UNKNOWN_LICENSE -> LICENSE_ID_NOT_MAPPED (writer XLSXW_1)
Note: Formats required date values to HNAP requirements
QC_DATE_FORMATTER
    -> RESOURCES_VALIDATOR
LICENSE_ID_NOT_MAPPED (writer XLSXW_1)
    attributes: license_id auto(20), id auto(20)

Bookmark: Attribute Validation
Note: Validates url, name and format on resources{} list items
RESOURCES_VALIDATOR
    -> FORMAT_VALIDATOR
Note: Verfication if URL is valid WMS call for WMS formats
FORMAT_VALIDATOR
    -> DEFAULT_ATTRIBUTE_MAPPER_NG

Bookmark: Default value
Note: Sets default attribute values
DEFAULT_ATTRIBUTE_MAPPER_NG
    FEATURE_TYPE = Default_QC
    IN_CSV_LOOKUP_TABLES_DIR = $(IN_CSV_LOOKUP_TABLES_DIR)
    P-T_ABBR = $(P-T_ABBR)
    -> AttributeExposer_6

Bookmark: Email format
AttributeExposer_6
    ATTR_LIST = default_contact_email
    -> EMAIL_FORMAT_TESTER
Note: Tests for and corrects missing '@' in email addresses and email separated by a comma delimiter
EMAIL_FORMAT_TESTER
    DEFAULT_CONTACT_EMAIL = @Value(default_contact_email)
    -> QC_MISSING_EMAIL_MAPPER

Bookmark: QC Missing eMail Mapper
Note: Add default_contact_email when contact email is missing
QC_MISSING_EMAIL_MAPPER: QC_MISSING_EMAIL_SETTER
    DATA_OUTPUT_PASSED -> AttributeExposer_8
    DATA_OUTPUT_PASSED -> Recorder_2

Bookmark: Sector Mapper
Note: Reading Sector_QC
LOOKUP_TABLES_READER_4
    CSV_ENCODING = utf-8
    CSV_PATH = $(IN_CSV_LOOKUP_TABLES_DIR)
    FEATURE_TYPE = Sector_QC
    PT = QC
    -> QC_SECTOR_MAPPER_AND_FILTER [LOOKUP_TABLE_INPUT]
Note: Maps sector values and filters for publishing by referencing lookup table. Creates graphic thumbnail output
QC_SECTOR_MAPPER_AND_FILTER
    OUTPUT_SECTOR_PASSED -> GEO_NONE_GEO_SELECTOR
    OUTPUT_SECTOR_PASSED -> Recorder_5
    UNKNOWN_SECTOR -> SECTORS_NOT_MAPPED (writer XLSXW_1)
SECTORS_NOT_MAPPED (writer XLSXW_1)
    attributes: sector auto(20), id auto(20)

Bookmark: spatial data type management
Note: Differenciate Geo and None Geo records based on atrribute values and CV files
GEO_NONE_GEO_SELECTOR
    CSV_FILE_NAME = GeoSpatialValidation
    CSV_PATH = $(IN_CSV_LOOKUP_TABLES_DIR)
    CSV_PROVINCE = $(P-T_ABBR)
    YAML_DIRECTIVES:
      resources{}.format:
        domain: lookup_table_format
        spatial_type: overwrite
        not_found: log
        search_type: equals
      #
      tags{}.display_name:
        domain: [Photographie aérienne,Toponyme,Toponymie,photogrammétrie,GPS,cartographie]
        spatial_type: no_overwrite
        not_found: no_log
        search_type: contains
    GEOSPATIAL -> Tester_7
    NONE_GEOSPATIAL -> Tester_6
    LOG_ERROR -> GEOSPATIAL_FORMAT_NOT_MAPPED (writer XLSXW_1)
Note: Uses algorithm to determine spatial_representation_type of dataset
SPATIAL_TYPE_MAPPER_NG
    FEATURE_TYPE = UUID_Spatial_QC
    IN_CSV_LOOKUP_TABLES_DIR = $(IN_CSV_LOOKUP_TABLES_DIR)
    P-T_ABBR = $(P-T_ABBR)
    DATA_OUTPUT_FAILED -> SPATIALTYPE_NOT_MAPPED (writer XLSXW_1)
    DATA_OUTPUT_PASSED -> TestFilter
SPATIALTYPE_NOT_MAPPED (writer XLSXW_1)
    attributes: notes auto(20), title auto(20), id auto(20)
GEOSPATIAL_FORMAT_NOT_MAPPED (writer XLSXW_1)
    attributes: format string(8)

Bookmark: Fork Geo and None Geo
Note: Process Geospatial features
Tester_7
    BOOL_OP = OR
    COMPOSITE_TEST = 1
    TEST_CLAUSE = TEST @UpperCase($(ACTIVATE_GEO)) = YES
    TEST_MODE = TEST
    PASSED -> SPATIAL_TYPE_MAPPER_NG [DATA_INPUT]
Note: Process none Geospatial features
Tester_6
    BOOL_OP = OR
    COMPOSITE_TEST = 1
    TEST_CLAUSE = TEST @UpperCase($(ACTIVATE_NON_GEO)) = YES
    TEST_MODE = TEST
    PASSED -> TestFilter_2

Bookmark: Samples or full content
TestFilter
    DEFAULT_VALUE = SAMPLES FEATURES
    TEST_LIST = "BOOL_OP,OR,COMPOSITE_TEST,""""""1"""""",TEST_CLAUSE,TEST $(SAMPLE_SIZE) = 0",ALL FEATURES
    ALL FEATURES -> Junction_4
    SAMPLES FEATURES -> Sampler
Sampler
    RATE = $(SAMPLE_SIZE)
    SAMPLE_MODE = No
    SAMPLE_TYPE_LONG = First N Features
    SAMPLED -> Junction_4

Bookmark: Projection and GeoExtents Management
Note: Extracts projection values and bounding box coordinates from url, wms or esri rest, where they exist. Missing projection values are set to unknown
QC_PROJECTION_GEOEXTENTS_EXTRACTOR
    DATA_OUTPUT -> GEO_EXTENTS_MAPPER_NG
    DATA_OUTPUT -> Recorder_3
Note: Sets geoextents not created in previous transformer based on lookup table values
GEO_EXTENTS_MAPPER_NG
    FEATURE_TYPE = Coord_QC
    IN_CSV_LOOKUP_TABLES_DIR = $(IN_CSV_LOOKUP_TABLES_DIR)
    LATITUDE_MAX = 64
    LATITUDE_MIN = 44
    LONGITUDE_MAX = -56
    LONGITUDE_MIN = -80
    P-T_ABBR = $(P-T_ABBR)
    EXTENT_DEFINED -> METADATA_VALUE_MAPPER_NG [DATA_INPUT]
    UNKNOWN_EXTENT -> GEO_EXTENTS_NOT_MAPPED (writer XLSXW_1)
GEO_EXTENTS_NOT_MAPPED (writer XLSXW_1)
    attributes: location string(20), id auto(20)

Bookmark: Samples or full content
TestFilter_2
    DEFAULT_VALUE = SAMPLES FEATURES
    TEST_LIST = "BOOL_OP,OR,COMPOSITE_TEST,""""""1"""""",TEST_CLAUSE,TEST $(SAMPLE_SIZE) = 0",ALL FEATURES
    ALL FEATURES -> Junction
    SAMPLES FEATURES -> Sampler_2
Sampler_2
    RATE = $(SAMPLE_SIZE)
    SAMPLE_MODE = No
    SAMPLE_TYPE_LONG = First N Features
    SAMPLED -> Junction

Bookmark: Non-geospatial processing
AttributeExposer_2
    ATTR_LIST = author,author_email,groups{}.name,id,license_id,metadata_created,metadata_modified,notes,organization.title,resources{}.id,resources{}.name,resources{}.url,tags{}.display_name,temporal,title,update_frequency
    -> QC_TBS_ATTRIBUTE_VALUE_MAPPER
Note: Reading Format_TBS_QC
LOOKUP_TABLES_READER_16
    CSV_ENCODING = utf-8
    CSV_PATH = $(IN_CSV_LOOKUP_TABLES_DIR)
    FEATURE_TYPE = Format_TBS_QC
    PT = QC
    -> QC_TBS_ATTRIBUTE_VALUE_MAPPER [LOOKUP_TABLE_FORMAT]
Note: Reading ResourceType_TBS_QC
LOOKUP_TABLES_READER_17
    CSV_ENCODING = utf-8
    CSV_PATH = $(IN_CSV_LOOKUP_TABLES_DIR)
    FEATURE_TYPE = ResourceType_TBS_QC
    PT = QC
    -> QC_TBS_ATTRIBUTE_VALUE_MAPPER [LOOKUP_TABLE_TYPE]
Note: Reading UpdateFrequency_TBS_QC
LOOKUP_TABLES_READER_18
    CSV_ENCODING = utf-8
    CSV_PATH = $(IN_CSV_LOOKUP_TABLES_DIR)
    FEATURE_TYPE = UpdateFrequency_TBS_QC
    PT = QC
    -> QC_TBS_ATTRIBUTE_VALUE_MAPPER [LOOKUP_TABLE_FREQUENCY]
Note: Reading SubjectNTopic_TBS_QC
LOOKUP_TABLES_READER_19
    CSV_ENCODING = utf-8
    CSV_PATH = $(IN_CSV_LOOKUP_TABLES_DIR)
    FEATURE_TYPE = SubjectNTopic_TBS_QC
    PT = QC
    -> QC_TBS_ATTRIBUTE_VALUE_MAPPER [LOOKUP_TABLE_SUBJECT_TOPIC]
QC_TBS_ATTRIBUTE_VALUE_MAPPER
    -> AttributeExposer_12
    UNKNOWN_FORMAT -> format_new_values_tbs (writer XLSXW_1)
    UNKNOWN_FREQUENCY -> update_frequency_new_values_tbs (writer XLSXW_1)
    UNKNOWN_TYPE -> restype_new_values_tbs (writer XLSXW_1)
    UNKNOWN_SUBJECT -> subject_new_values_tbs (writer XLSXW_1)
AttributeExposer_12
    ATTR_LIST = tags{}
    -> ListElementCounter_2
AttributeCreator_7
    ATTR_TABLE = SET_TO _env_ckan_tbs = @UpperCase(STAGING)
    -> AttributeFilter_2
AttributeFilter_2
    ATTR_NAME = _env_ckan_tbs
    ATTR_VALUES = <Empty>,<Missing>,<Null>,<Unfiltered>,PROD,STAGING
    PROD -> AttributeCreator_8
    STAGING -> AttributeCreator_9
AttributeCreator_8
    ATTR_TABLE = SET_TO _url_ckan_api = https://open.canada.ca/data/api/action
    -> AttributeExposer_5
AttributeCreator_9
    ATTR_TABLE = SET_TO _url_ckan_api = https://staging.open.canada.ca/data/api/action
    -> AttributeExposer_5
AttributeExposer_5
    ATTR_LIST = tbs_owner_org_id
    -> METADATA_DELTA_FINDER_NG_2
METADATA_DELTA_FINDER_NG_2
    ABSTRACT_ATT_NEW = notes
    ABSTRACT_ATT_REF = notes_translated.fr
    DATESTAMP_ATT_NEW = record_last_modified
    DATESTAMP_ATT_REF = federated_date_modified
    ID_ATT_NEW = id
    ID_ATT_REF = id
    LOCAL_SOURCE = Yes
    LOCAL_SOURCE_DIR = $(OUT_JSON_LOCAL_DIR)
    LOCAL_SOURCE_FORMAT = JSON
    PYCSW_CKAN_OVERWRITE = $(PYCSW_CKAN_OVERWRITE)
    RES_FORMAT_ATT_NEW = resources{}.format_tbs
    RES_FORMAT_ATT_REF = resources{}.format
    RES_NAME_ATT_NEW = resources{}.name
    RES_NAME_ATT_REF = resources{}.name_translated.fr
    RES_URL_ATT_NEW = resources{}.url
    RES_URL_ATT_REF = resources{}.name_translated.fr
    TITLE_ATT_NEW = title
    TITLE_ATT_REF = title_translated.fr
    Statistics -> StatisticsCalculator_Summary_3
    Update -> Junction_6
    Insert -> Junction_6
    Delete -> DELETED_RECORDS_NONE_GEO (writer XLSXW_1)
Note: Log statistics
StatisticsCalculator_Summary_3: Logger
    LOG_FEATURE = NONE
    MAXFEATS = 20
    MESSAGE:
      ************************
      **** NoneGeo Features: Unchanged Report ****
      ************************

      @Value(_real_count) features were unchanged

      ************************
      ************************
      ************************
    SEVERITY = INFO
Junction_6
    -> AWS_TRANSLATE_2
Note: Translates specific items from French to English
AWS_TRANSLATE_2
    ACTIVATE_TRANSLATION = $(ACTIVATE_TRANSLATION)
    ATTR_2_Translate = notes,title,sector
    ATTR_LIST_2_Translate = tags{}.display_name,resources{}.name
    MODE = French-->English
    -> AttributeExposer_11
    TRANSLATION_PROBLEM -> translation_problems_NONE_GEO (writer XLSXW_1)
AttributeExposer_11
    ATTR_LIST = tags{}.display_name,resources{}.name,p-t_entity_en,p-t_entity_fr,sector
    -> ListRenamer_2
ListRenamer_2
    LEAVE_ORIG = No
    LIST_ACTION = Rename
    LIST_COMPONENT_NAMES = resources{},resources{},name,name_fr
    LIST_NAME = resources{}.name
    -> AttributeCreator_5
AttributeCreator_5
    ATTR_TABLE:
      SET_TO nom_organisation_fr = @Value(sector)
      SET_TO nom_organisation_en = @Value(sector)
    -> PythonCaller_2
PythonCaller_2
    PYTHONSOURCE:
      import fme
      import fmeobjects
      # Template Function interface:
      # When using this function, make sure its name is set as the value of
      # the 'Class or Function to Process Features' transformer parameter
      def processFeature(feature):
          for i in range(len(feature.getAttribute('resources{}.url'))):
              feature.setAttribute('resources{%d}.language_list'%(i),'["fr"]')
    PYTHONSYMBOL = processFeature
    -> VariableRetriever_8
VariableRetriever_8
    SCOPE = Global
    VALUE_ATTR = _timestamp
    VARNAME = _timestamp
    -> JSON_PUBLISHER_NG
JSON_PUBLISHER_NG
    FEATURE_TYPE = JSON_CONFIG_QC
    IN_CSV_LOOKUP_TABLES_DIR = $(IN_CSV_LOOKUP_TABLES_DIR)
    JSON_RESOURCE_TEMPLATE = $(IN_TBS_JSON_TEMPLATE_DIR)\TBS_RESOURCES_TEMPLATE.json
    JSON_ROOT_TEMPLATE = $(IN_TBS_JSON_TEMPLATE_DIR)\TBS_ROOT_TEMPLATE.json
    Keywords_EN = tags{}.display_name_en
    Keywords_FR = tags{}.display_name
    P-T_ABBR = $(P-T_ABBR)
    Subject_LIST = _list{}.TBS_subject
    Topic_LIST = _list{}.TBS_topic
    OUTPUT_LOCAL -> AttributeExposer_4
AttributeExposer_4
    ATTR_LIST = json_file,id
    -> AttributeCreator_6
AttributeCreator_6
    ATTR_TABLE = SET_TO text_line_data = @Value(json_file)
    -> text_line (writer TEXTLINE_4)
text_line (writer TEXTLINE_4)
    attributes: text_line_data buffer
translation_problems_NONE_GEO (writer XLSXW_1)
    attributes: id auto(20)
Note: Log deleted features
DELETED_RECORDS_NONE_GEO (writer XLSXW_1)
    attributes: id auto(20)
format_new_values_tbs (writer XLSXW_1)
    attributes: id string(20), format string(20)
update_frequency_new_values_tbs (writer XLSXW_1)
    attributes: update_frequency string(20), id string(20)
restype_new_values_tbs (writer XLSXW_1)
    attributes: id string(20), restype string(20)
subject_new_values_tbs (writer XLSXW_1)
    attributes: name string(20), id string(20)

Bookmark: Attribute value mapper
Note: This section utilizes mulitple instances of the METADATA_VALUE_MAPPER to correct values to valid English values and to add the valid French equivalents and RI_CODES where applicable. It can be utilized for mulitple metadata items by accessing custom look up tables applicable to specific items. / Turn the error mapping options and the data items to be mapped on or off by clicking on the transformer and selecting yes/no. / - ERROR_NOT_MAPPED: enables mapping of data item values that cannot be found in the lookup tables. / - ENGLISH_REFRESH: enables updating of English attribute values. / - FRENCH_REFRESH: enables updating of French attribute values. / - CODE_REFRESH: enables updating of RI_CODE values. / Enter the attribute key name by clicking on the transformer and selecting the drop down menu next to the 'att_to_map' text box and selecting the 'Open text editor...' option. Explicitly enter the attribute key name in the text editor (ie: contacts{}.role). / IMPORTANT: Do not select the 'Attribute Value' option from the drop down menu to select the attribute key name.
Note: Maps update cycle to HNAP standards
METADATA_VALUE_MAPPER_NG
    ATT_TO_MAP = update_frequency
    CODE_REFRESH = YES
    ENGLISH_REFRESH = YES
    ERROR_NOT_MAPPED = YES
    FEATURE_TYPE = Update
    FRENCH_REFRESH = YES
    IN_CSV_LOOKUP_TABLES_DIR = $(IN_CSV_LOOKUP_TABLES_DIR)
    P-T_ABBR = $(P-T_ABBR)
    -> METADATA_VALUE_MAPPER_NG_2 [DATA_INPUT]
Note: Maps progress code to HNAP standards
METADATA_VALUE_MAPPER_NG_2
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUP_TABLES_DIR)
    P-T_ABBR = $(P-T_ABBR)
    -> METADATA_VALUE_MAPPER_NG_3 [DATA_INPUT]
Note: Maps progress code to HNAP standards
METADATA_VALUE_MAPPER_NG_3
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUP_TABLES_DIR)
    P-T_ABBR = $(P-T_ABBR)
    -> METADATA_FORMAT_MAPPER_NG [DATA_INPUT]

Bookmark: Format value mapper
Note: This section utilizes the METADATA_FORMAT_MAPPER to correct data format values to valid data format values and to associate and add the French and English 'Resource Type' attribute to each data format type. It accesses a custom look up table applicable to data formats. / Turn the error mapping options and the data items to be mapped on or off by clicking on the transformer and selecting yes/no. / - ERROR_NOT_MAPPED: enables mapping of data item values that cannot be found in the lookup tables. / - REAL_VALUE_REFRESH: enables updating of data format attribute values. / - RES_TYPE_FR_REFRESH: enables mapping of French resource types. / - RES_TYPE_EN_REFRESH: enables mapping of English resource types. / Enter the attribute key name by clicking on the transformer and selecting the drop down menu next to the 'att_to_map' text box and selecting the 'Open text editor...' option. Explicitly enter the attribute key name in the text editor (ie: resources{}.format). / IMPORTANT: Do not select the 'Attribute Value' option from the drop down menu to select the attribute key name.
METADATA_FORMAT_MAPPER_NG
    ATT_TO_MAP = resources{}.format
    ERROR_NOT_MAPPED = YES
    FEATURE_TYPE = Format
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    -> METADATA_VALUE_MAPPER_ERROR_MANAGER

Bookmark: Mapping error list creator
Note: Creates list of errors found and not corrected in mapping
METADATA_VALUE_MAPPER_ERROR_MANAGER
    ERROR_OUTPUT -> METADATA_MAPPING_ERRORS (writer XLSXW_1)
    DATA_OUTPUT -> URL_CHARACTER_ENCODER
METADATA_MAPPING_ERRORS (writer XLSXW_1)
    attributes: error string(200), id string(200), _element_index string(200)

Bookmark: URL Character Encoder
Note: URL's containing {} will not validate. UTF8 value is substituted where they exist.
URL_CHARACTER_ENCODER
    DATA_OUTPUT -> QC_WMS_URL_SETTER [DATA_INPUT]

Bookmark: QC_WMS_URL_SETTER
QC_WMS_URL_SETTER
    FEATURE_TYPE = WMS_URL_QC
    IN_CSV_LOOKUP_TABLES_DIR = $(IN_CSV_LOOKUP_TABLES_DIR)
    P-T_ABBR = $(P-T_ABBR)
    -> REMOVE_BROKEN_URL_WMS_ESRI_REST

Bookmark: Data cleanup. Dropping broken web services
Note: Tests WMS/ESRI_REST resource URL's and removes them where broken
REMOVE_BROKEN_URL_WMS_ESRI_REST
    -> WMS_REST_LANGUAGE_FORMATTER
    FAULTY_URL_OUTPUT -> MAP_SERVICE_URL_ERROR (writer XLSXW_1)
MAP_SERVICE_URL_ERROR (writer XLSXW_1)
    attributes: id auto(20), format string(8), url auto(20), _url_failure_message auto(20)

Bookmark: HNAP Rules- 1 web service per language.
Note: Formats WMS and ESRI REST resources to add French versions and formats French and English versions with valid supporting attributes
WMS_REST_LANGUAGE_FORMATTER
    -> DUPLICATE_SERVICE_REMOVER
Note: Removes duplicate WMS or ESRI REST resources where they exist, that would otherwise invalidate the dataset
DUPLICATE_SERVICE_REMOVER
    -> RESOURCE_NAME_UNDERSCORE_REMOVER

Bookmark: Data preparation for metadata section
Note: Removes all underscores from resources{}.name attributes. Long compounded names joined by underscores in this field can cause display formatting issues when published to the FGP.
RESOURCE_NAME_UNDERSCORE_REMOVER
    DATA_OUTPUT -> AttributeExposer_9
AttributeExposer_9
    ATTR_LIST = resources{}
    -> ListCopier
ListCopier
    DEST_LIST = distributionList
    SRC_LIST = resources{}
    -> GMD_SECTION_DATA_EXTRACTION
Note: Creates lists and removes duplicates for GMD_Section
GMD_SECTION_DATA_EXTRACTION
    -> MORE_INFO_MANAGER
Note: Tests the more_info{}.link list for valid attribute values and filters them out where missing
MORE_INFO_MANAGER
    -> MAP_RESOURCE_ATTRIBUTION_REMOVER_NG
MAP_RESOURCE_ATTRIBUTION_REMOVER_NG
    FEATURE_TYPE = MAP_RES_REMOVE_QC
    IN_CSV_LOOKUP_TABLES_DIR = $(IN_CSV_LOOKUP_TABLES_DIR)
    P-T_ABBR = $(P-T_ABBR)
    -> PythonCaller
    -> Recorder_4

Bookmark: Adjusting number of tags
ListElementCounter_2
    CNT_ATTR = _element_count_tags
    LIST_NAME = tags{}
    -> Tester_5
Tester_5
    BOOL_OP = OR
    COMPOSITE_TEST = 1
    TEST_CLAUSE = TEST @Value(_element_count_tags) = 0
    TEST_MODE = TEST
    PASSED -> AttributeCreator_10
    FAILED -> Junction_2
AttributeCreator_10
    ATTR_TABLE = SET_TO tags{0}.display_name = données ouvertes
    -> Junction_2
Junction_2
    -> AttributeCreator_7

Bookmark: Configuring publishing info
PYCSW_URL_MAPPER_NG
    FEATURE_TYPE = PyCSW_config
    FORCED_PYCSW_URL = $(FORCED_PYCSW_URL)
    IN_CSV_LOOKUP_TABLES_DIR = $(IN_CSV_LOOKUP_TABLES_DIR)
    P-T_ABBR = $(P-T_ABBR)
    -> PythonCaller
AttributeExposer_7
    ATTR_LIST = search_criteria_pycsw,csw_url
    -> METADATA_DELTA_FINDER_NG
METADATA_DELTA_FINDER_NG
    ABSTRACT_ATT_NEW = notes
    ABSTRACT_ATT_REF = MD_Metadata.identificationInfo.MD_DataIdentification.abstract.PT_FreeText.textGroup.LocalisedCharacterString
    CSW_FILTER = @Value(search_criteria_pycsw)
    CUSTOM_CSW_CKAN_URL = @Value(csw_url)
    DATESTAMP_ATT_NEW = record_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    PYCSW_CKAN_OVERWRITE = $(PYCSW_CKAN_OVERWRITE)
    RES_FORMAT_ATT_NEW = resources{}.description_temp
    RES_FORMAT_ATT_REF = MD_Metadata.distributionInfo.MD_Distribution.transferOptions{}.MD_DigitalTransferOptions.onLine.CI_OnlineResource.description.CharacterString
    RES_NAME_ATT_NEW = resources{}.name
    RES_NAME_ATT_REF = MD_Metadata.distributionInfo.MD_Distribution.transferOptions{}.MD_DigitalTransferOptions.onLine.CI_OnlineResource.name.PT_FreeText.textGroup.LocalisedCharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.PT_FreeText.textGroup.LocalisedCharacterString
    Statistics -> StatisticsCalculator_Summary_2
    Update -> Junction_5
    Insert -> Junction_5
    Delete -> DELETED_RECORDS_GEO (writer XLSXW_1)
Note: Log statistics
StatisticsCalculator_Summary_2: Logger
    LOG_FEATURE = NONE
    MAXFEATS = 20
    MESSAGE:
      ************************
      **** Geo Features: Unchanged Report ****
      ************************

      @Value(_real_count) features were unchanged

      ************************
      ************************
      ************************
    SEVERITY = INFO
Junction_5
    -> AWS_TRANSLATE
Note: Log deleted features
DELETED_RECORDS_GEO (writer XLSXW_1)
    attributes: id auto(20)

Bookmark: Pregenrate formating for ressources description
PythonCaller
    NEW_ATTRIBUTES = resources{}.description_temp
    PYTHONSOURCE:
      import fme
      import fmeobjects
      # Template Function interface:
      # When using this function, make sure its name is set as the value of
      # the 'Class or Function to Process Features' transformer parameter
      def processFeature(feature):
          lang=feature.getAttribute('transfer_option_description_language')

          for i in range(len(feature.getAttribute('resources{}.url'))):
              format=feature.getAttribute('resources{%i}.format'%(i))
              restype=feature.getAttribute('resources{%i}.format_resourceType_en'%(i))

              feature.setAttribute('resources{%i}.description_temp'%(i),'%s;%s;%s'%(restype,format,lang))
    PYTHONSYMBOL = processFeature
    -> AttributeExposer_7

Bookmark: Language Translation
Note: Translates specific items from French to English
AWS_TRANSLATE
    ACTIVATE_TRANSLATION = $(ACTIVATE_TRANSLATION)
    ATTR_2_Translate = notes,title,sector
    ATTR_LIST_2_Translate = tags{}.display_name,resources{}.name
    MODE = French-->English
    -> XML_PUBLISHER_NG
    TRANSLATION_PROBLEM -> translation_problems_GEO (writer XLSXW_1)
translation_problems_GEO (writer XLSXW_1)
    attributes: id auto(20)

Bookmark: XML CREATION AND WRITING
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
Note: CSV config file to map QC attributes to those required by XML templates
XML_PUBLISHER_NG
    FEATURE_TYPE = Config_QC
    IN_CSV_LOOKUP_TABLES_DIR = $(IN_CSV_LOOKUP_TABLES_DIR)
    LOCAL_WRITER = $(LOCAL_WRITER)
    P-T_ABBR = $(P-T_ABBR)
    TEMPLATE_GMD_CITEDRESPONSIBLEPARTY = $(IN_GMD_XML_TEMPLATE_DIR)\GMD_CITEDRESPONSIBLEPARTY.xml
    TEMPLATE_GMD_CONTACT = $(IN_GMD_XML_TEMPLATE_DIR)\GMD_CONTACT.xml
    TEMPLATE_GMD_DISTRIBUTIONFORMAT = $(IN_GMD_XML_TEMPLATE_DIR)\GMD_DISTRIBUTIONFORMAT.xml
    TEMPLATE_GMD_DISTRIBUTOR = $(IN_GMD_XML_TEMPLATE_DIR)\GMD_DISTRIBUTOR.xml
    TEMPLATE_GMD_KEYWORDS = $(IN_GMD_XML_TEMPLATE_DIR)\GMD_KEYWORDS.xml
    TEMPLATE_GMD_MDMETADATA = $(IN_GMD_XML_TEMPLATE_DIR)\GMD_MDMETADATA.xml
    TEMPLATE_GMD_REFERENCESYSTEMINFO = $(IN_GMD_XML_TEMPLATE_DIR)\GMD_REFERENCESYSTEMINFO.xml
    TEMPLATE_GMD_RESOURCEMAINTENANCE = $(IN_GMD_XML_TEMPLATE_DIR)\GMD_RESOURCEMAINTENANCE.xml
    TEMPLATE_GMD_TOPICCATEGORY = $(IN_GMD_XML_TEMPLATE_DIR)\GMD_TOPICCATEGORY.xml
    TEMPLATE_GMD_TRANSFEROPTIONS = $(IN_GMD_XML_TEMPLATE_DIR)\GMD_TRANSFEROPTIONS.xml
    LOCAL -> text_line (writer TEXTLINE_3)
    INSERT_PASSED -> text_line (writer TEXTLINE_1) [off]
    UPDATE_PASSED -> text_line (writer TEXTLINE_1) [off]
    INSERT_FAILED -> text_line (writer TEXTLINE_2) [off]
    UPDATE_FAILED -> text_line (writer TEXTLINE_2) [off]

FME custom transformer Catalogue Reader
Description
This Custom Transformer enables to read a CKAN or a CSW server and extract the requested metadata records.  Once the metadata records are extracted, they are transformed from their hierarchcal structure (JSON for CKAN and XML for CSW) into a flattened FME attribute and list features.  The parameters allow great flexibility on how the CKAN or CSW server are requested.
Note: No modification other then the JSON/XML flattening is performed on the metadata records read from the CKAN/CSW server.
Input Ports
Input: One feature to signal the start of the metadata server extraction.    
Output Ports
Résultats: The features resulting from the CKAN or the CSW server extraction.  One output feature for each metadata record read.
Métadonnées invalides: Used to output ID not found in the CKAN or CSW server. On ly used when the parameter IDENTIFIANT is used.
UUID_invalide: Used when the ID is not a valid UUID. On ly used when the parameter IDENTIFIANT is used.
Parameters
SOURCE_URL: The source URL (web address) of the target CKAN or CSW server. There are 6 pre-defined source url and one user defined address (drop down bix):
FGP-STAGING_INTERNE: Address of the external internal FGP staging server;
FGP-STAGING-EXTERNE:Address of the internal internal FGP staging server;
FGP-PROD_INTERNE: Address of the internal FGP production server ;
FGP-PROD-EXTERNE: Address of the externall FGP production server;
OPENDATA-STAGING: Address of the Open Data staging server;
OPENDATA-PROD: Address of the Open Data production server;
PYCSW-INTERNAL: Address of the internal PYCSW server;
CUSTOM-CSW/CKAN: Custom URL address of a CKAN or CSW server to be supplied by the user in the CUSTOM_URL parameter.
CUSTOM_URL: The address of the server to be used when CUSTOM-CSW/CKAN option is choosen with SOURCE_URL parameter. 
CKAN_FILER: String to be used with CKAN server to filter the result. Ex.: fq=collection:fgp where fq is the CKAN reserved word for filtering, collection is a the name of a key in the JSON document and fgp is the requested value for the filtering;
CUSTOM_CSW_SCHEMA: Drop down box specifying the output schema to use to generate the metadata records (default: http://www.iso tc211.org/2005/ gmd). Used with CSW server.
CUSTOM_CSW_VERSION: Drop down box specifying the version of the CSW server to use (default: 2.0.2)
CUSTOM_URL_CSW_TYPENAMES: Dropdown box specifying which entities must be queried from the information model (default: gmd:MD_Met adata). Used with CSW server.
CUSTOM_CSW_LIST_NAME: Dropdown box specifying the name of the FME list attribute used to explode the list attribute . (fefault MD_Metadata{}) Used with CSW server.
IDENTIFIANT:  UUID identifying the ID of the metadata record to extract from the server. Used with CSW and CKAN server.
CUSTOM_URL_BY_ID_ATT_NAME: Not used any more.
CSW_ANY_TEXT_FILTER: A string to be used to filter the metadata records.  Any string canbe used.  can filter any field of the metadata record.  Used with CSW server. 
Note:  For more information on the use of the parameters of the CSW server, refer to the official OGC documentation  OGC PDF documentation.

Parameters:
- SOURCE_URL =
- CUSTOM_URL =
- CKAN_FILTER =
- CUSTOM_CSW_SCHEMA = http://www.isotc211.org/2005/gmd
- CUSTOM_CSW_VERSION = 2.0.2   # 2.0.2 CUSTOM_CSW_VERSION
- CUSTOM_URL_CSW_TYPENAMES = gmd:MD_Metadata
- CUSTOM_CSW_LIST_NAME = MD_Metadata{}
- IDENTIFIANT =
- CUSTOM_URL_BY_ID_ATT_NAME =
- CSW_ANYTEXT_FILTER =

Input (input)
    -> AttributeCreator_20
Note: All or By ID getRecords
TestFilter_2
    DEFAULT_VALUE = By ID
    TEST_LIST = "BOOL_OP,OR,COMPOSITE_TEST,""""""1"""""",TEST_CLAUSE,TEST @Value(_id) = """,All
    All -> AttributeCreator_30
    By ID -> Logger_3
Note: Add "AllRecords" attribute
AttributeCreator_30
    ATTR_TABLE = SET_TO _type_requete = -AllRecords
    -> TestFilter
UUID_invalide (output)
Note: CKAN or CSW
TestFilter
    DEFAULT_VALUE = CKAN
    TEST_LIST = "BOOL_OP,OR,COMPOSITE_TEST,""""""1"""""",TEST_CLAUSE,CASE_INSENSITIVE_TEST @LowerCase(@Value(root_url)) CONTAINS csw",CSW
    CSW -> AttributeCreator_23
    CKAN -> AttributeCreator_24
Note: Junction_5 : Input
Junction_7
    -> Junction_8
Note: Junction_2 : Output
Junction_8
    -> Junction_4
Junction_4
    -> Métadonnées_non_trouvées (output)
Métadonnées_non_trouvées (output)
Junction
    -> AttributeExposer
Note: Expose some attributes in order to remove them
AttributeExposer
    ATTR_LIST = _toto,_creation_instance
    -> AttributeRemover_2
Note: Remove unneeded attributes
AttributeRemover_2
    REMOVE_ATTRS = ErreurUUID,_csw_constraint,_csw_constraint_language,_csw_list_name,_csw_output_schema,_csw_search_criteria,_csw_typenames,_csw_version,_element_index,_id,_response_body,_status_code,_status_code_description,_type_requete,root_url,_creation_instance,_toto,_OpenMapsFilter,help,success
    -> ATTRIBUTE_UNEXPOSER
ATTRIBUTE_UNEXPOSER
    -> Résultats (output)
Résultats (output)

Bookmark: Assignation de paramètres
Note: Transfert de tous les paramètres en attributs
AttributeCreator_20
    ATTR_TABLE:
      SET_TO _csw_constraint
      SET_TO _csw_constraint_language = FILTER
      SET_TO _csw_list_name = $(CUSTOM_CSW_LIST_NAME)
      SET_TO _csw_output_schema = $(CUSTOM_CSW_SCHEMA)
      SET_TO _csw_typenames = $(CUSTOM_URL_CSW_TYPENAMES)
      SET_TO _csw_version = $(CUSTOM_CSW_VERSION)
      SET_TO _id = $(IDENTIFIANT)
      SET_TO root_url = $(SOURCE_URL)
    -> Tester_15
Note: Custom URL ou valeur
Tester_15
    BOOL_OP = OR
    COMPOSITE_TEST = 1
    TEST_CLAUSE = TEST $(CUSTOM_URL) != ""
    TEST_MODE = TEST
    PASSED -> AttributeCreator_21
    FAILED -> TestFilter_2
Note: Reset root_url attribute
AttributeCreator_21
    ATTR_TABLE = SET_TO root_url = $(CUSTOM_URL)
    -> TestFilter_2

Bookmark: Traitement pour requete By ID
Logger_3
    LOG_FEATURE = LOG_ONLY
    MAXCOORDS = 20
    MAXFEATS = 20
    MESSAGE = La présence d'un attribut "Identifiant" bypass le tri par attribut "provider".
    SEVERITY = WARN
    LOGGED -> PythonCaller_1
Note: Vérifier que le UUID est valide
PythonCaller_1
    NEW_ATTRIBUTES = ErreurUUID
    PYTHONSOURCE:
      import fme
      import fmeobjects
      from uuid import UUID
      # Template Function interface:
      # When using this function, make sure its name is set as the value of
      # the 'Class or Function to Process Features' transformer parameter
      def processFeature(feature):
          """Validate if a UUID is valid

          Parameters
          ----------
          feature: FME Feature object
              FME feature to process

          Returns
          -------
          None
          """

          uuid4 = feature.getAttribute('_id')
          if uuid4 is not None and uuid4 != "":
              try:
                  val = UUID(uuid4, version=4)
                  pass  # UUID valid
              except ValueError:
                  # UUID is not valid
                  feature.setAttribute("ErreurUUID","OUI")
          else:
              pass  # There is no UUID to validate
    PYTHONSYMBOL = processFeature
    -> Tester_17
Tester_17
    BOOL_OP = OR
    COMPOSITE_TEST = 1
    TEST_CLAUSE = TEST @Value(ErreurUUID) = OUI
    TEST_MODE = TEST
    PASSED -> UUID_invalide (output)
    FAILED -> AttributeCreator_26
Note: Add "ById" attribute
AttributeCreator_26
    ATTR_TABLE = SET_TO _type_requete = -ByID
    -> TestFilter

Bookmark: Define CSW specific parameters
Note: CSW request
AttributeCreator_23
    ATTR_TABLE = SET_TO _type_requete = CSW@Value(_type_requete)
    -> Tester_22
Junction_6
    -> PythonCaller_2

Bookmark: Manage AnyTestFilter
Tester_22
    BOOL_OP = OR
    COMPOSITE_TEST = 1
    TEST_CLAUSE = TEST $(CSW_ANYTEXT_FILTER) = ""
    TEST_MODE = TEST
    PASSED -> AttributeCreator_29
    FAILED -> AttributeCreator_27
AttributeCreator_29
    ATTR_TABLE = SET_TO _csw_search_criteria
    -> Junction_6
AttributeCreator_27
    ATTR_TABLE:
      SET_TO _csw_search_criteria = &constraintlanguage=CQL_TEXT&constraint=apiso%3AAnyText%20like%20$(CSW_ANYTEXT_FILTER)
      SET_TO _csw_constraint_language = CQL_TEXT
      SET_TO _csw_constraint = apiso%3AAnyText%20like%20$(CSW_ANYTEXT_FILTER)
    -> Junction_6

Bookmark: Manage CSW call
Note: HTTP call for reading the CSW server and retreive the JSON records
PythonCaller_2
    NEW_ATTRIBUTES = _response_body _status_code _status_code_description
    PYTHONSOURCE = from Python.Catalogue_Reader import ManageHttpCall
    PYTHONSYMBOL = ManageHttpCall
    -> TestFilter_3
Note: Test if error duing the CKAN server extraction
TestFilter_3
    DEFAULT_VALUE = Other Error
    TEST_LIST = "BOOL_OP,OR,COMPOSITE_TEST,""""""1"""""",TEST_CLAUSE,TEST @Value(_status_code) = 200",200 OK,"BOOL_OP,OR,COMPOSITE_TEST,""""""1"""""",TEST_CLAUSE,TEST @Value(_status_code) = 404",404 Not found
    200 OK -> XMLFlattener
    404 Not found -> Junction_7
    Other Error -> Terminator_3
XMLFlattener
    ATTRIBUTE_XML = _response_body
    EMBEDDED_EXPRESSIONS = SearchResults GetRecordByIdResponse
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    NEW_ATTRIBUTES = SearchResults.numberOfRecordsReturned
    XML_SOURCE_TYPE = Attribute with XML document
    -> Tester
    <REJECTED> -> Terminator_4
Note: 2 or more records returned
Tester
    BOOL_OP = OR
    COMPOSITE_TEST = 1
    TEST_CLAUSE = TEST @Value(SearchResults.numberOfRecordsReturned) >= 2
    TEST_MODE = TEST
    PASSED -> ListExploder_3
    FAILED -> BulkAttributeRenamer
Note: Créer une entité par métadonnées
Note: 0 or 1 record returned
ListExploder_3
    ATTR_ACCUM_MODE = Prefix List Attributes
    INCOMING_PREFIX = temp_name_.
    INDEX_ATTR = _element_index
    LIST_ATTR = $(CUSTOM_CSW_LIST_NAME)
    ELEMENTS -> StringReplacer
    <REJECTED> -> Terminator_5
StringReplacer
    CASE = NO
    FIND_TEXT = {}
    NO_MATCH = _FME_NO_OP_
    REGEXP = NO
    SRC_ATTRS = _csw_list_name
    -> BulkAttributeRenamer
BulkAttributeRenamer
    ATTRCHOICE = All Attributes
    CASE_DISP = NO
    MODE_CHOICE = RENAME
    PATTERN_ACTION_DISP = STRINGREPLACE
    REPLACE_PATTERN = temp_name_
    REPLACE_STR = @Value(_csw_list_name)
    -> Junction
Terminator_5
    MESSAGE:
      Error during list exploder of the XML document
      Translation Terminated
Terminator_4
    MESSAGE = Translation Terminated.  Error during XML flattenning.
Terminator_3
    MESSAGE = Translation Terminated. Status Code: @Value(_status_code); description: @Value(_status_code_description)

Bookmark: Define CKAN specific parameters
Note: CKAN request
AttributeCreator_24
    ATTR_TABLE = SET_TO _type_requete = CKAN@Value(_type_requete)
    -> Tester_21
Note: OPenMaps ou autreCKAN
Tester_21
    BOOL_OP = OR
    COMPOSITE_TEST = 1
    TEST_CLAUSE = TEST $(CKAN_FILTER) != ""
    TEST_MODE = TEST
    PASSED -> AttributeCreator_28
    FAILED -> Junction_3
AttributeCreator_28
    ATTR_TABLE = SET_TO _OpenMapsFilter = &$(CKAN_FILTER)
    -> Junction_3
Junction_3
    -> AttributeCreator_18
Note: CKAN Filter parameters
AttributeCreator_18
    ATTR_TABLE = SET_TO _OpenMapsFilter = $(CKAN_FILTER)
    -> PythonCaller_3

Bookmark: Manage CKAN call
Note: HTTP call for reading the CKAN server and retreive the JSON records
PythonCaller_3
    NEW_ATTRIBUTES = _response_body _status_code _status_code_description
    PYTHONSOURCE = from Python.Catalogue_Reader import ManageHttpCall
    PYTHONSYMBOL = ManageHttpCall
    -> TestFilter_4
Note: Test if error duing the CKAN server extraction
TestFilter_4
    DEFAULT_VALUE = Other Error
    TEST_LIST = "BOOL_OP,OR,COMPOSITE_TEST,""""""1"""""",TEST_CLAUSE,TEST @Value(_status_code) = 200",200 OK,"BOOL_OP,OR,COMPOSITE_TEST,""""""1"""""",TEST_CLAUSE,TEST @Value(_status_code) = 404",404 Not found
    200 OK -> JSONFlattener_4
    404 Not found -> Junction_4
    Other Error -> Terminator [off]
Note: Flattening the JSON records
JSONFlattener_4
    ERROR_LIST_ATTR = _json_error
    JSON_DOCUMENT = @Value(_response_body)
    READ_FROM_FILE = NO
    RECURSIVE = Yes
    -> AttributeExposer_3
    <REJECTED> -> Terminator_2
AttributeExposer_3
    ATTR_LIST = help,success,results{}
    -> Junction
Terminator_2
    MESSAGE = Translation Terminated.  Error during JSON flattenning.
Terminator
    MESSAGE = Translation Terminated. Status Code: @Value(_status_code); description: @Value(_status_code_description)

FME custom transformer PYCSW_URL_MAPPER_NG
Description
This Custom Transformer is used to set the address (URL) of the PyCSW server to be used.  The address will change depending if the Workbench is run on a desktop or on FME Server.  It's lso possible to overwrite this value by setting the published parameter: FORCED_PYCSW_URL.  The URL address are stored in the CSV file to read.
Input Ports
INPUT: The input features to process.
Output Ports
OUTPUT: The output processed features.
Parameters
FORCED_PYCSW_URL: Use to overwrite or force the value ot the PyCSW YRL to use.
FEATURE_TYPE: Name of the CSV file to read (without .csv extension);
IN_CSV_LOOKUP_TABLES_DIR: Name of the directory path containing the CSV file to read;
P-T_ABBR: Two letters abbreviation of the province or the territory.

Parameters:
- FORCED_PYCSW_URL =
- FEATURE_TYPE =
- IN_CSV_LOOKUP_TABLES_DIR =
- P-T_ABBR =

INPUT (input)
    -> Tester_4
Note: Tests for selection of local pycsw
Tester_4
    BOOL_OP = OR
    COMPOSITE_TEST = 1
    TEST_CLAUSE = TEST $(FORCED_PYCSW_URL) = ""
    TEST_MODE = TEST
    PASSED -> AttributeCreator
    FAILED -> AttributeCreator_4
Note: Overwrite PyCSW URL
AttributeCreator_4
    ATTR_TABLE = SET_TO csw_url = $(FORCED_PYCSW_URL)
    -> Junction
AttributeCreator
    ATTR_TABLE = SET_TO _pt = $(P-T_ABBR)
    -> FeatureMerger [REQUESTOR]
Note: Read CSV file
LOOKUP_TABLES_READER_NG
    CSV_ENCODING = utf-8
    CSV_PATH = $(IN_CSV_LOOKUP_TABLES_DIR)
    FEATURE_TYPE = $(FEATURE_TYPE)
    PT = $(P-T_ABBR)
    -> AttributeExposer
AttributeExposer
    ATTR_LIST = url_fmeserver,url_desktop,pt
    -> FeatureMerger [SUPPLIER]
FeatureMerger
    ATTR_ACCUM_MODE = Merge Supplier
    ATTR_CONFLICT_RES = Use Requestor
    IGNORE_NULLS = No
    JOIN_KEYS = @Value(_pt) @Value(pt) AUTO
    MERGE_TYPE = Attributes Only
    PROCESS_DUPS = NO
    REJECT_NULL_MISSING_KEYS = No
    SUPPLIERS_FIRST = No
    MERGED -> AttributeCreator_5
    UNMERGED_REQUESTOR -> Terminator
    <REJECTED> -> Terminator
Note: Create attribute from FME_HOME parameter
AttributeCreator_5
    ATTR_TABLE = SET_TO fme_home = $(FME_HOME_USERTYPED)
    -> Tester_5
Note: Tests if FME_HOME contains 'FMEServer'
Tester_5
    BOOL_OP = OR
    COMPOSITE_TEST = 1
    TEST_CLAUSE = CASE_INSENSITIVE_TEST @Value(fme_home) CONTAINS FMEServer
    TEST_MODE = CASE_INSENSITIVE_TEST
    PASSED -> AttributeCreator_6
    FAILED -> AttributeCreator_7
Note: Sets Server PyCSW URL
AttributeCreator_6
    ATTR_TABLE = SET_TO csw_url = @Value(url_fmeserver)
    -> Junction
Note: Sets desktop PyCSW URL
AttributeCreator_7
    ATTR_TABLE = SET_TO csw_url = @Value(url_desktop)
    -> Junction
Junction
    -> AttributeRemover
Note: Attribute cleanup
AttributeRemover
    REMOVE_ATTRS = fme_home,url_fmeserver,pt,url_desktop,_pt
    -> ATTRIBUTE_UNEXPOSER
Note: Unexpose all attributes
ATTRIBUTE_UNEXPOSER
    -> OUTPUT (output)
OUTPUT (output)
Terminator
    MESSAGE = ERROR: Unknown provider: $(P-T_ABBR)

Bookmark: PYCSW_URL_MAPPER
Note: Failed

FME custom transformer MAP_RESOURCE_ATTRIBUTION_REMOVER
Description 
This transformer tests if the ressources{}.url from the metadata records are present in the lookup table, if yes then it sets the xlink_role and protocol attributes
Input Ports 
URL: URL from the lookup table.
INPUT: Input metadata records to process.
Output Ports 
OUTPUT: The process output metdata records.
Parameters 
NONE

URL (input)
    -> AttributeExposer_2
AttributeExposer_2
    ATTR_LIST = url
    -> AttributeCreator
Note: Sorting order
AttributeCreator
    ATTR_TABLE = SET_TO _type = A
    -> Sorter
Input (input)
    -> AttributeExposer
AttributeExposer
    ATTR_LIST = resources{}.url
    -> ListElementCounter
Note: Count number of ressources{} occurrences
ListElementCounter
    CNT_ATTR = _element_count
    LIST_NAME = resources{}
    -> AttributeCreator_2
Note: Sorting order
AttributeCreator_2
    ATTR_TABLE = SET_TO _type = B
    -> Sorter
Note: Sort lookup table entry firstly. Metadata records secondly.
Sorter
    SORT_PARM = _type ALPHA ASCENDING
    SORTED -> PythonCaller
Note: Check if URL from the ressources{}.url is present in the looup table and set some attributes
PythonCaller
    PYTHONSOURCE:
      import fme
      import fmeobjects
      # Template Function interface:
      # When using this function, make sure its name is set as the value of
      # the 'Class or Function to Process Features' transformer parameter

      class FeatureProcessor(object):
          def __init__(self):
              self.url=[]

          def input(self,feature):
              # If the url of the ressources is present in the lookup table set some attributes

              if feature.getAttribute('_type')=='A':
                  #Adding URL from the llokup tablein the list
                  self.url.append(feature.getAttribute('url'))

              else:

                  if int(feature.getAttribute('_element_count'))>0:
                      for i in range(int(feature.getAttribute('_element_count'))):
                          url=feature.getAttribute('resources{%d}.url'%(i))
                          if url in self.url:
                              feature.setAttribute('resources{%d}.xlink_role'%(i),'')
                              feature.setAttribute('resources{%d}.protocol'%(i),'HTTPS')

                  # Release the feature
                  self.pyoutput(feature)

          def close(self):
              pass
    PYTHONSYMBOL = FeatureProcessor
    -> ATTRIBUTE_UNEXPOSER
ATTRIBUTE_UNEXPOSER
    -> Output (output)
Output (output)

FME custom transformer GEOSPATIAL_DATA_VALIDATOR
Description 
This custom transformer fan out the metadata records between three types of metadata (GeoSpatial, Non GeoSpatial and Unknown).  In order to determine the type of metadta record, the transformer is using two strategies: firstly by checking if the format has been published in the FGP (if positive it is a GeoSpatial record); secondly by checking the content of a list of keywords againts the content of an attribute in the metadata record (if there is a match it is a GeoSpatial record) 
Input Ports 
LOOKUP_TABLE_INPUT: Input information from the lookup table
DATA_INPUT: The input metadata records to process.
Output Ports 
GEOSPATIAL: Output port for all gepspatial metadata record
NON-GEOSPATIAL: Output port for all non geospatial metadata record
UNKNOWN_FORMAT: Output port for metadata record that cannot be mapped to geospatial or non geospatial
Parameters 
KEYWORD_SEARCH: List of keywords used to determine if a metadata record is geospatial.  If more than one keyword is needed, separate each keyword with a vertical bar "|"
LIST_SEARCH_ATTRIBITE: Name of the attribute in plain text (ex.: tag{}.display_name) used to search for a string match from the KEYWORD_SEARCH parameter

Parameters:
- KEYWORD_SEARCH =
- LIST_SEARCH_ATTRIBUTE =

LOOKUP_TABLE_INPUT (input)
    -> AttributeExposer_2
INPUT (input)
    -> AttributeExposer
UNKNOWN_FORMAT (output)
GEOSPATIAL (output)
NON-GEOSPATIAL (output)

Bookmark: Excel file validation
Note: Exposes attributes from lookup table
AttributeExposer_2
    ATTR_LIST = fgp_publish,format,spatial_type
    -> Tester_2
Note: Tests for value in required fields
Tester_2
    BOOL_OP = OR
    COMPOSITE_TEST = 1 OR 2
    TEST_CLAUSE:
      TEST fgp_publish ATTRIBUTE_HAS_A_VALUE ""
      TEST format ATTRIBUTE_HAS_A_VALUE ""
    TEST_MODE = TEST
    PASSED -> DuplicateFilter
    FAILED -> Terminator
Terminator
    MESSAGE = Missing values in fgp_publish or format attributes, Geospatial lookup table, GEOSPATIAL_DATA_VALIDATOR transformer.  Translation terminated.
Note: Tests for duplicates of 'format' attribute
DuplicateFilter
    INPUT_ORDERED_CHOICE = No
    KEYATTR = format
    UNIQUE -> Tester
    DUPLICATE -> Terminator_2
Terminator_2
    MESSAGE = Duplicate feature @Value(format) found in format attribute in Geospatial lookup table, GEOSPATIAL_DATA_VALIDATOR transformer.  Translation terminated.
Note: Validates 'spatial_type' attribute format.
Tester
    BOOL_OP = OR
    COMPOSITE_TEST = 1 OR 2 OR 3 OR 4
    TEST_CLAUSE:
      TEST @Value(spatial_type) = a-grid
      TEST @Value(spatial_type) = b-vector
      TEST @Value(spatial_type) = c-textTable
      TEST spatial_type NOT_ATTRIBUTE_HAS_A_VALUE ""
    TEST_MODE = TEST
    PASSED -> StringCaseChanger_2
    FAILED -> Terminator_3
Terminator_3
    MESSAGE = spatial_type attribute value @Value(spatial_type) from Geospatial lookup table is invalid in GEOSPATIAL_DATA_VALIDATOR transformer.  Value must be 'a-grid', 'b-vector','c-textTable' or value must be empty.  Translation terminated.
Note: Putting format and fgp_publish in lower case
StringCaseChanger_2
    ATTRCHOICE = Selected Attributes
    ATTRLIST = fgp_publish format
    CHANGE_TYPE = lowercase
    -> FeatureMerger [SUPPLIER]

Bookmark: Geospatial Data Validator
Note: Exposes attributes from incoming data
AttributeExposer
    ATTR_LIST = resources{}.format,tags{}.display_name,id,resources{}.url,resources{}.name,notes,title,resources{}.fgp_publish
    -> UUIDGenerator
Note: Creates unique ID for rejoining data
UUIDGenerator
    UUID_ATTR = _uuid
    -> AttributeRenamer
    -> ListElementCounter
Note: Rename 'id' to 'original_id' as not to conflict with resources{}.id when resources{} list is exploded
AttributeRenamer
    ATTR_TABLE = RENAME_SET_DEFAULT id > orig_id
    -> AttributeKeeper
Note: Retains _uuid, original_id and resources{} list only
AttributeKeeper
    KEEP_ATTRS = notes,title,orig_id,_uuid
    KEEP_LIST = resources{}
    -> ListExploder
Note: Explodes resources{} list
ListExploder
    ATTR_ACCUM_MODE = Merge List Attributes
    ATTR_CONFLICT_RES = Use List Attribute Values
    INDEX_ATTR = _element_index
    LIST_ATTR = resources{}
    ELEMENTS -> Tester_3
    <REJECTED> -> Cloner
Tester_3
    BOOL_OP = OR
    COMPOSITE_TEST = 1
    TEST_CLAUSE = TEST @LowerCase(@Value(fgp_publish)) = oui
    TEST_MODE = TEST
    PASSED -> StringCaseChanger
    FAILED -> AttributeRemover_3
AttributeRemover_3
    REMOVE_ATTRS = fgp_publish
    -> StringCaseChanger
Note: Putting format in lowercasse
StringCaseChanger
    ATTRCHOICE = Selected Attributes
    ATTRLIST = format
    CHANGE_TYPE = lowercase
    -> FeatureMerger [REQUESTOR]
Note: Joins lookup table and feature data on value 'format'
FeatureMerger
    ATTR_ACCUM_MODE = Merge Supplier
    ATTR_CONFLICT_RES = Use Requestor
    IGNORE_NULLS = No
    JOIN_KEYS = @Value(format) @Value(format) AUTO
    MERGE_TYPE = Attributes Only
    PROCESS_DUPS = NO
    REJECT_NULL_MISSING_KEYS = No
    SUPPLIERS_FIRST = No
    MERGED -> FeatureMerger_2 [SUPPLIER]
    UNMERGED_REQUESTOR -> AttributeRenamer_2
    <REJECTED> -> Terminator_4
Terminator_4
    MESSAGE = Process failed at Feature Merger, GEOSPATIAL_DATA_VALIDATOR transformer.  Translation terminated.
Note: Rename 'orignal_id' back to 'id'
AttributeRenamer_2
    ATTR_TABLE = RENAME_SET_DEFAULT orig_id > id
    -> Logger
Logger
    LOG_FEATURE = LOG_ONLY
    MAXCOORDS = 20
    MAXFEATS = 20
    MESSAGE = Attribute value @Value(format) missing from Geospatial lookup table in GEOSPATIAL_DATA_VALIDATOR transformer.  See PROCESS_REPORT_MANUAL_TASKS.xls file in XLS directory for details.
    SEVERITY = WARN
    LOGGED -> AttributeKeeper_2
Note: Retains 'id' and 'format' for unmapped output file
AttributeKeeper_2
    KEEP_ATTRS = id,format
    -> UNKNOWN_FORMAT (output)
Cloner
    COPIES = 1
    COPYATT = _copynum
Note: Compter le nombre de ressource avec la vaidation
ListElementCounter
    CNT_ATTR = _nb_res_avant
    LIST_NAME = resources{}
    -> AttributeRemover
Note: Removes resources{} list
AttributeRemover
    LIST_ATTRS = resources{}
    -> FeatureMerger_2 [REQUESTOR]
Note: Rejoins data on _uuid attribute and rebuilds resources{} list
FeatureMerger_2
    ATTR_ACCUM_MODE = Merge Supplier
    ATTR_CONFLICT_RES = Use Requestor
    IGNORE_NULLS = No
    JOIN_KEYS = @Value(_uuid) @Value(_uuid) AUTO
    LIST_NAME = resources
    MERGE_TYPE = Attributes Only
    PROCESS_DUPS = NO
    REJECT_NULL_MISSING_KEYS = No
    SUPPLIERS_FIRST = No
    MERGED -> ListElementCounter_2
    <REJECTED> -> Terminator_5
ListElementCounter_2
    CNT_ATTR = _nb_res_apres
    LIST_NAME = resources{}
    -> Tester_4
Note: Uniquement les entités ayant le même nombre de ressource avant/apres / Si le nombre change, cela indique que des formats sont inconnus
Tester_4
    BOOL_OP = OR
    COMPOSITE_TEST = 1
    TEST_CLAUSE = TEST @Value(_nb_res_avant) = @Value(_nb_res_apres)
    TEST_MODE = TEST
    PASSED -> ListSearcher_2
Note: Searches resources{}.fgp_publish list for value 'Oui' for publishing
ListSearcher_2
    ATTR_VALUE = oui
    INDEX_ATTR = _list_index
    LIST_ATTR = resources{}.fgp_publish
    MATCHTYPE = REGULAR_EXPRESSION_ENCODED
    FOUND -> AttributeRemover_4
    NOT_FOUND -> ListSearcher
Note: Secondary list search. Searches on tags{}.display_name for BC and QC data and resources{}.contains_geographic_markers for ON data. LIST_SEARCH_ATTRIBUTE is the list attribute to be searched, KEYWORD_SEARCH represents the value(s).
ListSearcher
    ATTR_VALUE = $(KEYWORD_SEARCH)
    INDEX_ATTR = _list_index
    LIST_ATTR = $(LIST_SEARCH_ATTRIBUTE)
    MATCHTYPE = REGULAR_EXPRESSION_ENCODED
    FOUND -> AttributeRemover_4
    NOT_FOUND -> AttributeRemover_2
Note: Attribute cleanup
AttributeRemover_4
    LIST_ATTRS = resources{}._element_index resources{}._uuid resources{}.fgp_publish
    REMOVE_ATTRS = _element_index,format,_list_index,fgp_publish,_uuid
    -> ATTRIBUTE_UNEXPOSER
ATTRIBUTE_UNEXPOSER
    -> GEOSPATIAL (output)
Note: Attribute cleanup
AttributeRemover_2
    LIST_ATTRS = resources{}._element_index resources{}._uuid resources{}.fgp_publish
    REMOVE_ATTRS = _uuid,_element_index,format,fgp_publish
    -> ATTRIBUTE_UNEXPOSER_2
ATTRIBUTE_UNEXPOSER_2
    -> NON-GEOSPATIAL (output)
Terminator_5
    MESSAGE = Process failed at Feature Merger_2, GEOSPATIAL_DATA_VALIDATOR transformer.  Translation terminated.

FME custom transformer JSON_PUBLISHER_NG
Description 
This custom transformer is translating the input CKAN metadata model into the JSON TBS model.  The rules on how to map the input CKAN features attributes into the TBS attributes are stored in the JSON configuration file. The JSON templates used to create the JSON file are supplied with the input parameters of the custom transformers.  The mapping into JSON file is done with FME JSON Templater transformer.
Input Ports 
Input: The input metadata records to translate into the JSON TBS model.
Output Ports 
OUTPUT_LOCAL: The output metdata records translated into the JSON TBS model.
Parameters 
JSON_ROOT_TEMPLATE: File system address containing the root section of the TBS model in JSON format.
JSON_RESOURCE_TEMPLATE: File system address containing the resources section of the TBS model in JSON format.

Parameters:
- JSON_ROOT_TEMPLATE =
- JSON_RESOURCE_TEMPLATE =
- Keywords_EN =   # Keywords list in English
- Keywords_FR =   # Keywords list in French
- Topic_LIST =   # Enter Topic list
- Subject_LIST =   # Enter Subject list
- FEATURE_TYPE =
- IN_CSV_LOOKUP_TABLES_DIR =
- P-T_ABBR =

Note: Read the CSV lookup table
LOOKUP_TABLES_READER_NG
    CSV_ENCODING = utf-8
    CSV_PATH = $(IN_CSV_LOOKUP_TABLES_DIR)
    FEATURE_TYPE = $(FEATURE_TYPE)
    PT = $(P-T_ABBR)
    -> AttributeExposer
AttributeExposer
    ATTR_LIST = TBS_ATTRIBUTES,FEATURE_ATTRIBUTES,SECTION
    -> AttributeSplitter_2
Terminator_5
    MESSAGE = Translation Terminated
AttributeCreator_2
    ATTR_TABLE = SET_TO _order = 1
    -> Sorter_2
INPUT (input)
    -> AttributeCreator
AttributeCreator
    ATTR_TABLE = SET_TO CKAN_Transaction = Yes
    -> AttributeExposer_3
    -> AttributeExposer_4
AttributeExposer_3
    ATTR_LIST = TBS_subject,TBS_topic,data_collection_end_date,data_collection_start_date,date_published,description_en,description_fr,email,id,jurisdiction,keywords_en,keywords_fr,locale,metadata_modified,nom_organisation_en,nom_organisation_fr,org_name,p-t_entity_en,p-t_entity_fr,position_name_en,position_name_fr,prov_portal_last_modified,source_metadata_date_created,tbs_att_name_date_modified_prov,tbs_collection,tbs_hierarchy_level,tbs_imso_approval,tbs_license_id,tbs_locale,tbs_owner_org_id,tbs_ready_to_publish,tbs_responsible_role,tbs_restriction,tbs_state,tbs_type,title_en,title_fr,update_frequency_tbs,$(Keywords_FR),$(Keywords_EN),resources{},TBS_subject,TBS_topic,data_collection_end_date,data_collection_start_date,date_published,description_en,description_fr,email,format_tbs,id,jurisdiction,keywords_en,keywords_fr,locale,metadata_modified,name_en,name,name_fr,nom_organisation_en,nom_organisation_fr,org_name,p-t_entity_en,p-t_entity_fr,position_name_en,position_name_fr,prov_portal_last_modified,res_type_tbs,source_metadata_date_created,tbs_att_name_date_modified_prov,tbs_collection,tbs_hierarchy_level,tbs_imso_approval,tbs_license_id,tbs_locale,tbs_owner_org_id,tbs_ready_to_publish,tbs_resource_language,tbs_responsible_role,tbs_restriction,tbs_state,tbs_type,title_en,title_fr,update_frequency_tbs,url,$(Subject_LIST),$(Topic_LIST)
AttributeExposer_4
    ATTR_LIST = resources{},id
    -> FeatureMerger [REQUESTOR]
Note: Sorts config file and incoming data attributes so that config file attributes are ranked first.
Sorter_2
    SORT_PARM = _order NUMERIC ASCENDING
    SORTED -> PythonCaller_2
Note: Python script utilizes attribute names and list attribute names created by the config file to convert metadata attribute keys to the HNAP_ATTRIBUTE Keys created from the config file. The HNAP_ATTRIBUTE keys are consumed by the XML Templates used to build the metadata XML file
PythonCaller_2
    PYTHONSOURCE:
      import fme
      import fmeobjects

      # Template Class Interface:
      # When using this class, make sure its name is set as the value of
      # the 'Class or Function to Process Features' transformer parameter
      class FeatureProcessor(object):
          def __init__(self):
              #Creating dictionnairy
              #{key:[{a:b}{c:d},{a:e}{b:f}],key:[{a:b}{c:d},{a:e}{b:f}]}

              self.config={}
          def input(self,feature):
              #Config or metadata
              if int(feature.getAttribute('_order'))==1:
                 #Process config records
                 print (feature.getAttribute('_element_count'))
                 n2=[]
                 for i in range(feature.getAttribute('_element_count')):
                     n3={}
                     n3['TBS_ATTRIBUTES']=feature.getAttribute('_list{%s}.TBS_ATTRIBUTES'%(str(i)))
                     n3['FEATURE_ATTRIBUTES']=feature.getAttribute('_list{%s}.FEATURE_ATTRIBUTES'%(str(i)))
                     n3['LIST_NAME']=feature.getAttribute('_RANDOM_list_name')
                     n3['RANDOM_LIST_ATTRIBUTE']=feature.getAttribute('_RANDOM_FEATURE_ATTRIBUTES')

                     n2.append(n3)

                 self.config[feature.getAttribute('SECTION')]=n2

              else:

                  #Process metadata records
                  for keys in self.config:

                      if self.config[keys][0]['LIST_NAME']:

                          #Need to look in list to create multiple feature

                          # Only if metadatasection exists
                          if feature.getAttribute(self.config[keys][0]['RANDOM_LIST_ATTRIBUTE']):
                              for index in range(len(feature.getAttribute(self.config[keys][0]['RANDOM_LIST_ATTRIBUTE']))):
                                  new_feature=fmeobjects.FMEFeature()
                                  new_feature.setAttribute('SECTION',keys)

                                  for i in self.config[keys]:
                                      new_att=i['TBS_ATTRIBUTES']

                                      if '{}' in i['FEATURE_ATTRIBUTES']:
                                          new_values=feature.getAttribute('%s{%s}.%s'%(i['FEATURE_ATTRIBUTES'].split('{}.')[0],str(index),i['FEATURE_ATTRIBUTES'].split('{}.')[1]))
                                      else:
                                          new_values=feature.getAttribute(i['FEATURE_ATTRIBUTES'])
                                      new_feature.setAttribute(new_att,new_values)

                                  self.pyoutput(new_feature)

                      else:
                          #No list related to metasection, just need to parse regular attributes
                          new_feature=fmeobjects.FMEFeature()
                          new_feature.setAttribute('SECTION',keys)
                          for i in self.config[keys]:
                              new_att=i['TBS_ATTRIBUTES']
                              new_values=feature.getAttribute(i['FEATURE_ATTRIBUTES'])
                              new_feature.setAttribute(new_att,new_values)
                          self.pyoutput(new_feature)

          def close(self):
              pass
    PYTHONSYMBOL = FeatureProcessor
    -> AttributeFilter
AttributeFilter
    ATTR_NAME = SECTION
    ATTR_VALUES = <Empty>,<Missing>,<Null>,<Unfiltered>,ROOT,RESOURCES
    <EMPTY> -> Terminator_4
    <MISSING> -> Terminator_4
    <NULL> -> Terminator_4
    <UNFILTERED> -> Terminator_4
    ROOT -> JSONTemplater [ROOT]
    RESOURCES -> JSONTemplater [RESOURCES]
Terminator_4
    MESSAGE = ERROR: Unknown SECTION in JSON config file
Note: Creating JSON based on TBS minimum model
JSONTemplater
    CONSECUTIVE_GROUPS = No
    GROUP_BY = id
    RESOURCES_QUERY_FILE = $(JSON_RESOURCE_TEMPLATE)
    RESULT_ATTRIBUTE = json_file
    ROOT_QUERY_FILE = $(JSON_ROOT_TEMPLATE)
    VISIBLE_QUERY_VALIDATE = Yes
    -> AttributeExposer_5
OUTPUT_LOCAL (output)
Terminator_6
    MESSAGE = Translation Terminated

Bookmark: Adding PyCSW_Transaction, date_runtime, TBS_topic, TBS_subject, keywords_fr and keywords_fr attribute to ROOT +
Creator
    GEOMTYPE = Geometry Object
    NUM = 1
    CREATED -> AttributeCreator_8
    CREATED -> AttributeCreator_11
    CREATED -> AttributeCreator_5
    CREATED -> AttributeCreator_10
    CREATED -> AttributeCreator_9
    CREATED -> AttributeCreator_12
AttributeCreator_8
    ATTR_TABLE:
      SET_TO FEATURE_ATTRIBUTES = CKAN_Transaction
      SET_TO TBS_ATTRIBUTES = CKAN_Transaction
      SET_TO SECTION = ROOT
    -> AttributeExposer
AttributeCreator_11
    ATTR_TABLE:
      SET_TO FEATURE_ATTRIBUTES = date_runtime
      SET_TO TBS_ATTRIBUTES = date_runtime
      SET_TO SECTION = ROOT
    -> AttributeExposer
AttributeCreator_5
    ATTR_TABLE:
      SET_TO FEATURE_ATTRIBUTES = TBS_subject
      SET_TO TBS_ATTRIBUTES = TBS_subject
      SET_TO SECTION = ROOT
    -> AttributeExposer
AttributeCreator_10
    ATTR_TABLE:
      SET_TO FEATURE_ATTRIBUTES = TBS_topic
      SET_TO TBS_ATTRIBUTES = TBS_topic
      SET_TO SECTION = ROOT
    -> AttributeExposer
AttributeCreator_9
    ATTR_TABLE:
      SET_TO FEATURE_ATTRIBUTES = keywords_fr
      SET_TO TBS_ATTRIBUTES = keywords_fr
      SET_TO SECTION = ROOT
    -> AttributeExposer
AttributeCreator_12
    ATTR_TABLE:
      SET_TO FEATURE_ATTRIBUTES = keywords_en
      SET_TO TBS_ATTRIBUTES = keywords_en
      SET_TO SECTION = ROOT
    -> AttributeExposer

Bookmark: Searching for attribuite linked to more metadatasection
Note: From the lookup table, the METADATA_SECTION attribute for HNAP_ATTRIBUTES found in mulitple metadata sections is split into one attribute per METADATA_SECTION creating METADATA_SECTION{} list
AttributeSplitter_2
    ATTR_NAME = SECTION
    DELIMITER = ;
    DROP_EMPTY_PARTS = No
    LIST_NAME = SECTION
    TRIM_OPTION = Both
    -> ListExploder_9
Note: SECTION{} list is exploded to its individual parts
ListExploder_9
    ATTR_ACCUM_MODE = Merge List Attributes
    ATTR_CONFLICT_RES = Use List Attribute Values
    INDEX_ATTR = _element_index
    LIST_ATTR = SECTION{}
    ELEMENTS -> StringSearcher
    <REJECTED> -> Terminator_2
Terminator_2
    MESSAGE = Translation Terminated

Bookmark: Searching for list containing attributes. Need to generate multiple records from them
Note: Searches lookup table for FEATURE_ATTRIBUTES that are list attributes.
StringSearcher
    CASE = no
    MATCHED_RESULT_ATTR = _first_match
    REGEXP = {}
    STRING_TO_SEARCH = @Value(FEATURE_ATTRIBUTES)
    MATCHED -> AttributeSplitter_3
    NOT_MATCHED -> AttributeKeeper
Note: Splits list attributes using {} delimiter and creates _list{} list attribute from results
AttributeSplitter_3
    ATTR_NAME = FEATURE_ATTRIBUTES
    DELIMITER = {}
    DROP_EMPTY_PARTS = No
    LIST_NAME = _list
    TRIM_OPTION = Both
    -> AttributeCreator_7
Note: Extracts _list{0} attribute creating list_name attribute which is original FEATURE_ATTRIBUTE list name.
AttributeCreator_7
    ATTR_TABLE = SET_TO list_name = @Value(_list{0})
    -> AttributeKeeper
Note: Removes out of scope attributes
AttributeKeeper
    KEEP_ATTRS = TBS_ATTRIBUTES,FEATURE_ATTRIBUTES,SECTION,list_name
    -> ListBuilder_2

Bookmark: Grouo by metadatasection
Note: Builds _list{} list attributes from FEATURE_ATTRIBUTES, HNAP_ATTRIBUTES and list_name, grouped by METADATA_SECTION attributes
ListBuilder_2
    GROUPS_ORDERED = No
    GROUP_BY = SECTION
    LIST_ATTRS_TO_INCLUDE = FEATURE_ATTRIBUTES list_name TBS_ATTRIBUTES
    LIST_NAME = _list
    -> AttributeCreator_6
Note: Creates _order attribute with value of 1
AttributeCreator_6
    ATTR_TABLE = SET_TO _order = 1
    -> ListElementCounter_2
Note: Retreives _list{} element count for each METADATA_SECTION
ListElementCounter_2
    CNT_ATTR = _element_count
    LIST_NAME = _list{}
    -> ListSearcher

Bookmark: Extracting to identify list and random feature attributes
Note: Searches for _list{}.listname attribute in each METADATA_SECTION
ListSearcher
    INDEX_ATTR = _list_index
    LIST_ATTR = _list{}.list_name
    SEARCH_TYPE = First not matching
    FOUND -> ListIndexer
    NOT_FOUND -> AttributeCreator_2
Note: Extracts _list_index from all _list{}.listname attributes
ListIndexer
    INDEX = @Value(_list_index)
    LIST_ATTR = _list{}
    PREFIX = _RANDOM_
    -> AttributeCreator_2
    <REJECTED> -> Terminator_5

Bookmark: Adding date_runtime on incomming feature
Creator_2
    GEOMTYPE = Geometry Object
    NUM = 1
    CREATED -> DateTimeStamper
DateTimeStamper
    DATETIME_ATTR = date_runtime
    INCLUDE_OFFSET = NO
    STAMP_TYPE = datetime
    TIMEZONE = utc
    -> DateTimeConverter
DateTimeConverter
    DATETIME_ATTR = date_runtime
    OUT_FORMAT = ISO
    PASSTHROUGH = NO
    REPAIR_INPUT = YES
    -> AttributeKeeper_2
AttributeKeeper_2
    KEEP_ATTRS = date_runtime
    -> FeatureMerger [SUPPLIER]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> ListConcatenator_2
    UNMERGED_REQUESTOR -> Terminator_6
    <REJECTED> -> Terminator_6

Bookmark: Managing keywords, Topics and Subjects
ListConcatenator_2
    DROP_EMPTY_PARTS = No
    LIST_ATTR = $(Keywords_FR)
    SEP = ","
    VAL_ATTR = keywords_fr
    -> ListConcatenator
ListConcatenator
    DROP_EMPTY_PARTS = No
    LIST_ATTR = $(Keywords_EN)
    SEP = ","
    VAL_ATTR = keywords_en
    -> ListConcatenator_3
ListConcatenator_3
    DROP_EMPTY_PARTS = No
    LIST_ATTR = $(Subject_LIST)
    SEP = ","
    VAL_ATTR = TBS_subject
    -> ListConcatenator_4
ListConcatenator_4
    DROP_EMPTY_PARTS = No
    LIST_ATTR = $(Topic_LIST)
    SEP = ","
    VAL_ATTR = TBS_topic
    -> AttributeCreator_3
AttributeCreator_3
    ATTR_TABLE = SET_TO _order = 2
    -> ListElementCounter

Bookmark: Managing resource language to write them properly
ListElementCounter
    CNT_ATTR = _nb_res
    LIST_NAME = resources{}
    -> PythonCaller
PythonCaller
    NEW_ATTRIBUTES = _res_lang_list
    PYTHONSOURCE:
      import fme
      import fmeobjects
      # Template Function interface:
      # When using this function, make sure its name is set as the value of
      # the 'Class or Function to Process Features' transformer parameter
      def processFeature(feature):
          # Create a new attribute "_res_lang_list" containing a string representing the resource language and number of resources for this metadata
          # ex.: "['fr']|['fr']" for 2 resources where French is the FME resource language
          _res_lang_list=''
          for i in range(int(feature.getAttribute('_nb_res'))):
              feature.setAttribute('resources{%d}.res_index'%(i),'FME_RESOURCE_LANGUAGE_%d'%(i))
              _res_lang_list='%s|%s'%(_res_lang_list,feature.getAttribute('resources{%d}.language_list'%(i)))
          feature.setAttribute('_res_lang_list',_res_lang_list.lstrip('|'))
    PYTHONSYMBOL = processFeature
    -> Sorter_2

Bookmark: Text editing
AttributeExposer_5
    ATTR_LIST = metadata_contact_fr,metadata_contact_en,email
    -> PythonCaller_4
PythonCaller_4
    PYTHONSOURCE:
      import fme
      import fmeobjects
      # Template Function interface:
      # When using this function, make sure its name is set as the value of
      # the 'Class or Function to Process Features' transformer parameter
      def processFeature(feature):
          json_file=feature.getAttribute('json_file')


          email=''
          contact_form_en=''
          contact_form_fr=''
          metadata_contact_fr=feature.getAttribute('metadata_contact_fr')
          metadata_contact_en=feature.getAttribute('metadata_contact_en')

          if feature.getAttribute('email'):
              email=r',\"electronic_mail_address\": \"%s\"'%(feature.getAttribute('email'))

          if feature.getAttribute('contact_form_en'):
              contact_form_en=r',\"contact_form\": \"%s\"'%(feature.getAttribute('contact_form_en'))
          if  feature.getAttribute('contact_form_fr'):
              contact_form_fr=r',\"contact_form\": \"%s\"'%(feature.getAttribute('contact_form_fr'))

          remplacement=r'"{\"fr\": {\"organization_name\": \"%s\"%s%s},\"en\": {\"organization_name\": \"%s\"%s%s}}"'%(metadata_contact_fr,email,contact_form_fr,metadata_contact_en,email,contact_form_en)

          json_new=json_file.replace(r'"FME_CONTACT_INFORMATION_VALUES"',remplacement)
          feature.setAttribute('json_file',json_new)
    PYTHONSYMBOL = processFeature
    -> StringReplacer_3
Note: Remplacement de la chaine de caractère pour keyword fr
StringReplacer_3
    CASE = NO
    FIND_TEXT = "FME_KEYWORDS_FR"
    NO_MATCH = _FME_NO_OP_
    REGEXP = NO
    REPLACE_TEXT = ["@Value(keywords_fr)"]
    SRC_ATTRS = json_file
    -> StringReplacer_4
Note: Remplacement de la chaine de caractère pour keyword en
StringReplacer_4
    CASE = NO
    FIND_TEXT = "FME_KEYWORDS_EN"
    NO_MATCH = _FME_NO_OP_
    REGEXP = NO
    REPLACE_TEXT = ["@Value(keywords_en)"]
    SRC_ATTRS = json_file
    -> StringReplacer_6
Note: Remplacement de la chaine de caractère pour tbs_subject
StringReplacer_6
    CASE = NO
    FIND_TEXT = "FME_SUBJECT_VALUES"
    NO_MATCH = _FME_NO_OP_
    REGEXP = NO
    REPLACE_TEXT = ["@Value(TBS_subject)"]
    SRC_ATTRS = json_file
    -> StringReplacer_7
Note: Remplacement de la chaine de caractère pour tbs_topic
StringReplacer_7
    CASE = NO
    FIND_TEXT = "FME_TOPIC_CATEGORY"
    NO_MATCH = _FME_NO_OP_
    REGEXP = NO
    REPLACE_TEXT = ["@Value(TBS_topic)"]
    SRC_ATTRS = json_file
    -> PythonCaller_3
Note: Gestion de la langue des resources
PythonCaller_3
    PYTHONSOURCE:
      import fme
      import fmeobjects
      # Template Function interface:
      # When using this function, make sure its name is set as the value of
      # the 'Class or Function to Process Features' transformer parameter
      def processFeature(feature):
          #Reading json_file attribute
          temp_json=feature.getAttribute('json_file')

          # Replace the language fr or en in the resource section of the JSON with FME_RESOURCE_LANGUAGE_X
          list_lang=feature.getAttribute('_res_lang_list').split('|')
          for i in range(len(list_lang)):
              temp_json=temp_json.replace('"FME_RESOURCE_LANGUAGE_%d"'%(i),list_lang[i])

          # Write json_file_attribute
          feature.setAttribute('json_file',temp_json)
    PYTHONSYMBOL = processFeature
    -> StringReplacer
Note: Nettoyage des listes vides
StringReplacer
    CASE = NO
    FIND_TEXT = [""]
    NO_MATCH = _FME_NO_OP_
    REGEXP = NO
    REPLACE_TEXT = [ ]
    SRC_ATTRS = json_file
    -> AttributeKeeper_3
AttributeKeeper_3
    KEEP_ATTRS = id,json_file
    -> OUTPUT_LOCAL (output)

FME custom transformer GEO_NONE_GEO_SELECTOR
Description 
This custom transformer fans out the metadata records between two types of metadata (GeoSpatial and None GeoSpatial). When a metadata record cannot be validates as GeoSpatial it is declared None Geospatial. In order to determine the type of metadata record, the transformer analyse attributes according to the YAML directives. See the section Content of the YAML directives below for a complete description of the YAML directives.
This custom transformer also adds the attribute _typedatasets which contains the value geo for the geospatial features and nonegeo for the none geospatial features.
Input Ports 
DATA_INPUT: The input metadata records to process.
Output Ports 
GEOSPATIAL: Output port for all gepspatial metadata records;
NON-GEOSPATIAL: Output port for all none geospatial metadata records;
ERROR_LOG: Output port for metadata records that need to be logged according to the YAML directives.
Note: All the input records will go through either the GeoSpatial the None GeoSpatial port. Some input records may be duplicated and sent through the LOG_ERROR port if requested by the YAML directives.
Parameters 
CSV_FILE_NAME: Name lookup table file name in CSV format. 
CSV_PATH: File path of the CSV file. 
CSV_PROVINCE: Code of the province (two letters) . 
YAML_DIRECTIVES: YAML directives for determining the Geospatial and None Geospatial records. See the section Content of the YAML directives below for a description of the YAML directives.
Content of the YAML directives 
The YAML directives are used by the custom transformer to decide the type of the metadata records: GeoSpatial or None GeoSpatial. Here's an exemple of a YAML directives:
resources{}.format:  
domain: lookup_table_format  
spatial_type: overwrite  
not_found: log  
search_type: equals  
#  
description:  
domain: [spatial, geographic]  
spatial_type: no_overwrite  
not_found: no_log  
search_type: contains 
Description of the YAML directives
The first part of the YAML is the name of the FME attribute to use to validate the record, it can be a list attribute (ex.: resources{}..format) or a simple attribute (ex.: description). If it's a list attribute,the name must contain the 2 characters:"{}". The content of that attribute will be used to determine if the record is GeoSpatial or None GeoSpatial.
Following the FME attribute to validate, there are 4 keywords: domain, spatial_type, not_found and search_type.
The first keyword domain defines the domain of values that are used to determine if a metadata record is GeoSpatial or None GeoSpatial. Two values are possible: lookup_table_format or a list of word defining the domain between brackets (ex.: [point, line, poygone]). When using the keyword lookup_table_format, the custom transformer will use the content of the column name format of the CSV fileto define the domain of values. The record type will be GeoSpatial if the column fgp_publish is set to "oui". When using a domain list, the metadata record will be GeoSpatial if the value of the FME attribute is contained in the domain list.
The second keyword spatial_type defines how to set the spatial type when there is a domain match of the FME attribute. Three values are possible: no_overwite, overwrite and if_null_overwrite. no_overwite means that even if there is a match do not try to overwrite the spatial type. overwite means that if there is a match, take the spatial type value associated in the CSV file (column name: spatial_type) and assign it (or create it if empty) to the corresponding FME attribute. if_null_overwite as the same meaning as overwrite but only when the content of the spatial type is empty or missing. The values overwrite and if_null_overwrite can only be used when the domain keyword value is lookup_table_format.
The third keyword not_found defines how the custom transformer behaves when an FME attribute is not found in the domain of values. Two values are possible: log and no_log. log means create a duplicate (clone) of the record and send it through the LOG_ERROR output port. no_log means do not log any error when the FME attribute is not found in the domain of values.
The fourth keyword search type defines how to search the content of the FME attribute. Two values are possible: equals or contains. equals means that the value of the FME attribute must be exactly the same. contains means that one of the word the FME attribute must be in the domain values (usefull when we search for one word in a sentence).
You can define more than one FME attribute to search. Do not duplicate the FME attribute name because the last one will overwrite the others.

Parameters:
- CSV_FILE_NAME = GeoSpatialValidation
- CSV_PATH = .
- CSV_PROVINCE =
- YAML_DIRECTIVES =   # " " YAML_DIRECTIVES

INPUT (input)
    -> AttributeCreator_2
Note: _order = 3
AttributeCreator_2
    ATTR_TABLE = SET_TO _order = 3
    -> Sorter_2
Note: YMAL reader
Creator
    GEOMTYPE = Geometry Object
    NUM = 1
    CREATED -> AttributeCreator_3
Note: _order = 2 / YAML content
AttributeCreator_3
    ATTR_TABLE:
      SET_TO _order = 2
      SET_TO _yaml_str = $(YAML_DIRECTIVES)
    -> Sorter_2
Note: Sort CSV feature first
Sorter_2
    SORT_PARM = _order NUMERIC ASCENDING
    SORTED -> PythonCaller
Note: Call GeoNoneGeoSelector python code
PythonCaller
    PYTHONSOURCE = from Python.GEO_NONE_GEO_SELECTOR import GeoNoneGeoSelector
    PYTHONSYMBOL = GeoNoneGeoSelector
    -> AttributeExposer
AttributeExposer
    ATTR_LIST = _geo_none_geo_status
    -> PythonCaller_2
Note: Lower case attribute: resources{}.format
PythonCaller_2
    PYTHONSOURCE = from Python.GEO_NONE_GEO_SELECTOR import lower_resources_format
    PYTHONSYMBOL = lower_resources_format
    -> PythonCaller_3
Note: Copy attribute id, notes and title in the attribute list resources{}
PythonCaller_3
    PYTHONSOURCE = from Python.GEO_NONE_GEO_SELECTOR import copy_attributes_in_resources
    PYTHONSYMBOL = copy_attributes_in_resources
    -> AttributeRemover
Note: Remove attribute created by the custom transformer
AttributeRemover
    REMOVE_ATTRS = _order,_creation_instance,_yaml_str
    -> TestFilter
Note: Sort Geo and None geo features
TestFilter
    DEFAULT_VALUE = <UNFILTERED>
    TEST_LIST = "BOOL_OP,OR,COMPOSITE_TEST,""""""1"""""",TEST_CLAUSE,TEST @Value(_geo_none_geo_status) = geo",GEO,"BOOL_OP,OR,COMPOSITE_TEST,""""""1"""""",TEST_CLAUSE,TEST @Value(_geo_none_geo_status) = none_geo",NONE_GEO,"BOOL_OP,OR,COMPOSITE_TEST,""""""1"""""",TEST_CLAUSE,TEST @Value(_geo_none_geo_status) = log_error",LOG_ERROR
    GEO -> AttributeRemover_2
    NONE_GEO -> AttributeRemover_3
    LOG_ERROR -> AttributeExposer_2
    <UNFILTERED> -> Terminator
Note: Remove unnecessary attributes
AttributeRemover_2
    REMOVE_ATTRS = _geo_none_geo_status
    -> AttributeCreator_11
Note: Add geo attribute
AttributeCreator_11
    ATTR_TABLE = SET_TO _typedatasets = geo
    -> GEOSPATIAL (output)
GEOSPATIAL (output)
Note: Remove unnecessary attributes
AttributeRemover_3
    REMOVE_ATTRS = _geo_none_geo_status
    -> AttributeCreator_12
Note: Add nonegeo attribute
AttributeCreator_12
    ATTR_TABLE = SET_TO _typedatasets = nongeo
    -> NONE_GEOSPATIAL (output)
NONE_GEOSPATIAL (output)
AttributeExposer_2
    ATTR_LIST = id,_not_found_err_msg,format
    -> Logger
    -> LOG_ERROR (output)
LOG_ERROR (output)
Logger
    LOG_FEATURE = LOG_ONLY
    MAXCOORDS = 20
    MAXFEATS = 20
    MESSAGE = ERROR in GEOSPATIAL_DATA_VALIDATOR transforme: @value(_not_found_err_msg)  See PROCESS_REPORT_MANUAL_TASKS.xls file in XLS directory for details.
    SEVERITY = WARN
Terminator
    MESSAGE = Unknown attribute _geo_none_geo_status @Value(_geo_none_geo_status)Translation Terminated

Bookmark: Reading CSV file
Note: Reading GeospatialValidation CSV file
LOOKUP_TABLES_READER_NG
    CSV_ENCODING = utf-8
    CSV_PATH = $(CSV_PATH)
    FEATURE_TYPE = $(CSV_FILE_NAME)
    PT = $(CSV_PROVINCE)
    -> AttributeCreator
Note: _order = 1
AttributeCreator
    ATTR_TABLE = SET_TO _order = 1
    -> Sorter_2
