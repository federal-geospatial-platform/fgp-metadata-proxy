FME workspace WatchDog_Publication.fmw
Title: WatchDog_Publication
Description: Description:
Programme développé dans le cadre du projet de fédération de données. Ce programme a pour but de valider la sycnhronisation de contenu entre les différentes composantes du processus. Les validations se font autant pour le contenu géo que non Géo. Le processus valide à la fois la présence des données dans les différentes composantes ainsi que la date de mise jour permettant ainsi de détecter les problèmes d"ajout/suppression de métadonnées ainsi que les mises à jour.
Validation du contenu non geo:
Les données non geo se retrouvent à deux endrroits pour la fédération de données. Le répertoire JSON_LOCAL (appelé disque) de chaque P/T sur la machine FME Server où sont traitées les données ainsi que le portail Open Data (appelé CKAN où sont publiées les données Le programme comparre ces 2 dépôts et peut identifier 3 types d'erreurs:
Problème de mise à jour de contenu de CKAN.
Les métadonnées sont présentes à la fois sur le disque et dans CKAN mais la date de mise à jour dans CKAN est plus vieille que celle des fichiers sur le disque. Il y a donc un problème de mise àj jour des données. Lorsqu'une erreur de ce type est identifiée, elle est écrite dans NG-ProblemeDate. 
Problème d'ajout de métadonné. 
Pour identifier cette erreur, on compare la date federated_date_modified (DISQUE) avec modified_date (CKAN) avec    La métadonnée a été écrite sur le DISQUE mains n'a pas été publié dans CKAN.  Lorsqu'une erreur de ce type est identifiée, elle est écrite dans NG-DisquePasCKAN
Problème de suppresion de métadonnée. 
La métadonnée a été supprimé du DISQUE mais l'action n'a pas percollé au niveau de CKAN.  Lorsqu'une erreur de ce type est identifiée, elle est écrite dans NG-CkanPasDisque
Validation du contenu géo
La validation pour la partie Géo est plus complexe que le non géo car les métadonnées se retrouvent à 3 endroits soit le #1 pycsw (appelé Pycsw), #2  le catalogue externe de la PGF (appelé CatExt) et#3  OpenData  (appelé CKAN). Tout comme pour le non géo, on retrouve des problèmes de mises à jours de métadonnées et des problèmes d'ajout/supresion
Problème de mise à jour de métadonnées dans OpenData: 
La métadonnée présente  dans Open Data n'est pas à jour par rapport au contenu du catalogue externe de la PGF. La date de modification de la donnée dans OpenData est plus veille que la date de transaction dans le catalogue externe . Lorsqu'une erreur de ce type est identifiée, elle est écrite dans G-ProbDateCatExtCKAN 
Problème d"ajout de métadonnées dans OpenData:
La métadonnée est présente dans le catalgoue externe de la PGF mais absent d'OpenData. Lorsqu'une erreur de ce type est identifiée, elle est écrite dans G-CatExtPasCkan
Problème de suppresion de métadonnées dans OpenData:
La métaonnée n'existe pas dans le catalgoue externe mais est toujours présente dans Open Data. Lorsqu'une erreur de ce type est identifiée, elle est écrite dans  G-CkanPasCatExt 
Problème de mise à jour du catalogue externe:
La métadonnée présente  dans catalogue externe  n'est pas à jour par rapport au contenu du pycsw  La date de transaction dans le catalgoue est plus veille que le time stamp de création de la métadonnée dans le PyCSW. Lorsqu'une erreur de ce type est identifiée, elle est écrite dans G-ProbDate-CatExtPycsw 
Problème d"ajout de métadonnées dans le catalogue externe:
La métadonnée est présente dans le pycsw mais absente du catalogue externe. Lorsqu'une erreur de ce type est identifiée, elle est écrite dans G-PycswPasCatExt
Problème de suppresion de métadonnées dans le catalogue externe:
La métaonnée n'existe pas dans le pycsw  mais est toujours présente dansle catalogue externe. Lorsqu'une erreur de ce type est identifiée, elle est écrite dans  G-CatExtPasPycsw

Parameters:
- IN_OUT_WORKING_DIR = $(FME_SHAREDRESOURCE_DATA)\PT_Harvester
- PYCSW_URL =
- OUT_XLS_DIR = $(IN_OUT_WORKING_DIR)\WatchDog
- LOG_FILE = $(IN_OUT_WORKING_DIR)\WatchDog\WatchDog_@DateTimeFormat(@DateTimeNow(),%Y%m%d).log
- FME_SHAREDRESOURCE_DATA = C:\Data   # FME Flow Data Directory

Writers:
- XLSXW_1: XLSXW to $(OUT_XLS_DIR)

Bookmark: Bloc Geo
Creator_2
    GEOMTYPE = Geometry Object
    NUM = 1
    CREATED -> AttributeCreator_6
Note: Création du payload pour connaitre le nombre total de record / On ne filtre pas les records directement dans la requete. Instable au niveau du comportement,. / On lit tout et on filte après
AttributeCreator_6
    ATTR_TABLE:
      SET_TO payload_search (varchar(200)) = <csw:GetRecords xmlns:csw="http://www.opengis.net/cat/csw/2.0.2" service="CSW" version="2.0.2" resultType="hits" startPosition='1' maxRecords='1' typeNames="csw:Record">
            <csw:Query >
            </csw:Query>
        </csw:GetRecords>
    -> HTTPCaller
Note: Lecture pour connaitre le nombre de record à lire. Call POST
HTTPCaller
    CLIENT_CERTIFICATE_TYPE = NONE
    CONNECTION_TIMEOUT_LENGTH = 60
    CONTENT_TYPE_LOOKUP = application/xml
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://maps.canada.ca/geonetwork/srv/eng/csw
    TRANSFER_TIMEOUT_LENGTH = 90
    UPLOAD_BODY = @Value(payload_search)
    UPLOAD_TYPE = STRING_UPLOAD
    USE_COOKIES = No
    VERIFY_SSL_CERTIFICATES = No
    UPLOAD_CONTENT_TYPE = XML (application/xml)
    -> XMLFlattener
Note: Extraction de l'info
XMLFlattener
    ATTRIBUTE_XML = _response_body
    DISABLE_EXTERNAL_ENTITY_PROCESSING = Yes
    EMBEDDED_EXPRESSIONS = SearchResults
    ENTITY_RESOLVER = Yes
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    IGNORE_DATASET_EXTERNAL_DTD = No
    XML_SOURCE_TYPE = xml_attr
    -> AttributeExposer
Note: Lecture par lot de 100 / Call POST
HTTPCaller_2
    CLIENT_CERTIFICATE_TYPE = NONE
    CONNECTION_TIMEOUT_LENGTH = 60
    CONTENT_TYPE_LOOKUP = application/xml
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://maps.canada.ca/geonetwork/srv/eng/csw
    TRANSFER_TIMEOUT_LENGTH = 90
    UPLOAD_BODY = @Value(payload)
    UPLOAD_TYPE = STRING_UPLOAD
    USE_COOKIES = No
    VERIFY_SSL_CERTIFICATES = No
    UPLOAD_CONTENT_TYPE = XML (application/xml)
    -> XMLFragmenter
AttributeExposer_5
    ATTR_TABLE = _response_body,,xml_fragment,
    -> AttributeRemover
AttributeRemover
    REMOVE_ATTRS = _response_body,xml_fragment
    -> AttributeExposer_7
AttributeExposer_7
    ATTR_TABLE = identifier,,info.changeDate,
    -> ListSearcher
AttributeKeeper_6
    CREATE_BULK_MODE_FEATURES = NO
    KEEP_ATTRS = identifier,metadata_modified,PT
    -> FeatureMerger_3 [REQUESTOR]
FeatureMerger_3
    ATTR_ACCUM_MODE = Merge Supplier
    ATTR_CONFLICT_RES_LOOKUP = REQUESTOR_IF_CONFLICT
    IGNORE_NULLS = No
    JOIN_KEYS = @Value(identifier) @Value(identifier) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> DateTimeConverter_5
    UNMERGED_REQUESTOR -> G-CkanPasCatExt (writer XLSXW_1)
    UNUSED_SUPPLIER -> AttributeCreator_14
    <REJECTED> -> Logger_2
DateTimeConverter_5
    DATETIME_ATTR = metadata_modified
    OUT_FORMAT = %Y%m%d
    PASSTHROUGH = NO
    REPAIR_INPUT = YES
    -> DateTimeConverter_6
DateTimeConverter_6
    DATETIME_ATTR = info.changeDate
    OUT_FORMAT = %Y%m%d
    PASSTHROUGH = NO
    REPAIR_INPUT = YES
    -> DateTimeCalculator_2
DateTimeCalculator_2
    MODE = DATETIMECALC_3_CALCULATE_INTERVAL
    OPERATION_PARAMETERS = START_DATETIME]@Value(metadata_modified)]END_DATETIME]@Value(info.changeDate)]RESULT_TYPE]DAYS]RESULT_INTERVAL]_result_interval]FME_CONTROLLER_QUERY_FILE]transformers/dependencies/datetimecalculator/DATETIMECALC_3_CALCULATE_INTERVAL.fme]FME_CONTROLLER_CHOICE]DATETIMECALC_3_CALCULATE_INTERVAL
    -> Tester_6
Tester_6
    BOOL_OP = OR
    TEST_CLAUSE = TEST @Value(_result_interval) > 0
    TEST_MODE = TEST
    PASSED -> AttributeCreator_8
AttributeCreator_8
    ATTR_TABLE:
      SET_TO date_catalogue_externe (varchar(200)) = @Value(info.changeDate)
      SET_TO date_openmaps (varchar(200)) = @Value(metadata_modified)
    -> G-ProbDateCatExtCKAN (writer XLSXW_1)
G-ProbDateCatExtCKAN (writer XLSXW_1)
    attributes: date_catalogue_externe string(200), date_openmaps string(200), identifier string(200), PT string(200)
G-CkanPasCatExt (writer XLSXW_1)
    attributes: identifier string(200), metadata_modified string(200), PT string(200)
AttributeCreator_14
    ATTR_TABLE = SET_TO date_catalogue_externe (varchar(200)) = @Value(info.changeDate)
    -> G-CatExtPasCkan (writer XLSXW_1)
G-CatExtPasCkan (writer XLSXW_1)
    attributes: date_catalogue_externe string(200), PT string(200), identifier string(200)
Logger_2
    LOG_FEATURE = LOG_ONLY
    MAXCOORDS = 20
    MAXFEATS = 20
    MESSAGE = Feature is:
    SEVERITY = INFO
Creator_4
    GEOMTYPE = Geometry Object
    NUM = 1
    CREATED -> Catalogue_Reader_2
Note: Lecture du contenu du pycsw
Catalogue_Reader_2: Catalogue Reader
    CKAN_FILTER = fq=collection:federated&fl=metadata_modified,id
    CUSTOM_CSW_LIST_NAME = MD_Metadata{}
    CUSTOM_CSW_SCHEMA = http://www.isotc211.org/2005/gmd
    CUSTOM_CSW_VERSION = 2.0.2
    CUSTOM_URL = $(PYCSW_URL)
    CUSTOM_URL_CSW_TYPENAMES = gmd:MD_Metadata
    SOURCE_URL = https://pycsw.ddr-stage.services.geo.ca/pycsw?
    Résultats -> AttributeExposer_8
AttributeExposer_8
    ATTR_TABLE = MD_Metadata.dateStamp.Date,,MD_Metadata.fileIdentifier.CharacterString,,MD_Metadata.identificationInfo.MD_DataIdentification.graphicOverview.MD_BrowseGraphic.fileName.CharacterString,
    -> AttributeCreator_9
AttributeCreator_9
    ATTR_TABLE:
      SET_TO identifier (varchar(200)) = @Value(MD_Metadata.fileIdentifier.CharacterString)
      SET_TO modified_date (varchar(200)) = @Value(MD_Metadata.dateStamp.Date)
    -> AttributeSplitter_2
AttributeSplitter_2
    ATTR_NAME = MD_Metadata.identificationInfo.MD_DataIdentification.graphicOverview.MD_BrowseGraphic.fileName.CharacterString
    DELIMITER = /
    DROP_EMPTY_PARTS = NO
    LIST_NAME = _list
    TRIM_TYPE = BOTH
    -> ListIndexer
ListIndexer
    INDEX = -2
    LIST_ATTR = _list{}
    -> AttributeCreator_10
AttributeCreator_10
    ATTR_TABLE = SET_TO PT (varchar(200)) = @Value(_list)
    -> AttributeKeeper_5
AttributeKeeper_5
    CREATE_BULK_MODE_FEATURES = NO
    KEEP_ATTRS = modified_date,PT,identifier
    -> FeatureMerger_4 [SUPPLIER]
    -> AttributeCreator_19
FeatureMerger_4
    ATTR_ACCUM_MODE = Merge Supplier
    ATTR_CONFLICT_RES_LOOKUP = REQUESTOR_IF_CONFLICT
    IGNORE_NULLS = No
    JOIN_KEYS = @Value(identifier) @Value(identifier) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> DateTimeConverter_7
    UNMERGED_REQUESTOR -> AttributeCreator_17
    UNUSED_SUPPLIER -> AttributeCreator_18
DateTimeConverter_7
    DATETIME_ATTR = modified_date
    OUT_FORMAT = %Y%m%d
    PASSTHROUGH = NO
    REPAIR_INPUT = YES
    -> DateTimeConverter_8
DateTimeConverter_8
    DATETIME_ATTR = info.changeDate
    OUT_FORMAT = %Y%m%d
    PASSTHROUGH = NO
    REPAIR_INPUT = YES
    -> DateTimeCalculator_3
DateTimeCalculator_3
    MODE = DATETIMECALC_3_CALCULATE_INTERVAL
    OPERATION_PARAMETERS = START_DATETIME]@Value(info.changeDate)]END_DATETIME]@Value(modified_date)]RESULT_TYPE]DAYS]RESULT_INTERVAL]_result_interval]FME_CONTROLLER_QUERY_FILE]transformers/dependencies/datetimecalculator/DATETIMECALC_3_CALCULATE_INTERVAL.fme]FME_CONTROLLER_CHOICE]DATETIMECALC_3_CALCULATE_INTERVAL
    -> Tester_7
Tester_7
    BOOL_OP = OR
    TEST_CLAUSE = TEST @Value(_result_interval) > 0
    TEST_MODE = TEST
    PASSED -> AttributeCreator_11
AttributeCreator_11
    ATTR_TABLE:
      SET_TO date_catalogue_externe (varchar(200)) = @Value(info.changeDate)
      SET_TO date_pycsw (varchar(200)) = @Value(modified_date)
    -> G-ProbDate-CatExtPycsw (writer XLSXW_1)
G-ProbDate-CatExtPycsw (writer XLSXW_1)
    attributes: date_catalogue_externe string(200), date_pycsw string(200), identifier string(200), PT string(200)
AttributeCreator_17
    ATTR_TABLE = SET_TO date_catalogue_externe (varchar(200)) = @Value(info.changeDate)
    -> G-CatExtPasPycsw (writer XLSXW_1)
G-CatExtPasPycsw (writer XLSXW_1)
    attributes: PT string(200), identifier string(200), date_catalogue_externe string(200)
AttributeCreator_18
    ATTR_TABLE = SET_TO date_pycsw (varchar(200)) = @Value(modified_date)
    -> G-PycswPasCatExt (writer XLSXW_1)
G-PycswPasCatExt (writer XLSXW_1)
    attributes: PT string(200), identifier string(200), date_pycsw string(200)
AttributeCreator_19
    ATTR_TABLE = SET_TO new_ct (varchar(200)) = 20240101
    -> DateTimeCalculator_4
DateTimeCalculator_4
    MODE = DATETIMECALC_3_CALCULATE_INTERVAL
    OPERATION_PARAMETERS = START_DATETIME]@Value(new_ct)]END_DATETIME]@Value(modified_date)]RESULT_TYPE]DAYS]RESULT_INTERVAL]_result_interval]FME_CONTROLLER_QUERY_FILE]transformers/dependencies/datetimecalculator/DATETIMECALC_3_CALCULATE_INTERVAL.fme]FME_CONTROLLER_CHOICE]DATETIMECALC_3_CALCULATE_INTERVAL
    -> Tester_2
Tester_2
    BOOL_OP = OR
    TEST_CLAUSE = TEST @Value(_result_interval) < 0
    TEST_MODE = TEST
    PASSED -> VideSiNewDeltaFinder (writer XLSXW_1)
VideSiNewDeltaFinder (writer XLSXW_1)
    attributes: PT string(200), identifier string(200), modified_date string(200)

Bookmark: Création de paquet de 10
AttributeExposer
    ATTR_TABLE = SearchResults.numberOfRecordsMatched,
    -> Cloner
Cloner
    COPIES = @ceil(@Value(SearchResults.numberOfRecordsMatched)/100)
    COPYATT = _copynum
    COPY -> AttributeCreator

Bookmark: Cération du payload pour lire en paquet de 100
AttributeCreator
    ATTR_TABLE = SET_TO start_index (varchar(200)) = @Evaluate(1+@Value(_copynum)*100)
    -> AttributeCreator_5
AttributeCreator_5
    ATTR_TABLE:
      SET_TO payload (varchar(200)) = <csw:GetRecords xmlns:csw="http://www.opengis.net/cat/csw/2.0.2" service="CSW" version="2.0.2" resultType="results_with_summary" startPosition='@Value(start_index)' maxRecords='100' typeNames="csw:Record">
            <csw:Query >
            </csw:Query>
        </csw:GetRecords>
    -> HTTPCaller_2

Bookmark: Extraction du contenu du XML
XMLFragmenter
    ATTRIBUTE_XML = _response_body
    DISABLE_EXTERNAL_ENTITY_PROCESSING = Yes
    EMBEDDED_EXPRESSIONS = csw:Record
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    IGNORE_DATASET_EXTERNAL_DTD = No
    MERGE_ATTRS = Yes
    REJECT_FEATURES_WITH_NO_FRAGMENTS = YES
    XML_SOURCE_TYPE = xml_attr
    FRAGMENTS -> AttributeExposer_2
AttributeExposer_2
    ATTR_TABLE = identifier,,info.changeDate,,Province,,URI{},
    -> ListElementCounter_2

Bookmark: Filtrage pour contenu PT uniuqment
ListElementCounter_2
    CNT_ATTR = _element_count
    LIST_NAME = URI{}
    -> PythonCaller
Note: On garde les entités pointant vers https://raw.githubusercontent.com/federal-geospatial-platform/fgp-metadata-proxy/master/images
PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):


              for i in range(int(feature.getAttribute('_element_count'))):
                  value=str(feature.getAttribute('URI{%i}'%(i)))

                  if r'https://raw.githubusercontent.com/federal-geospatial-platform/fgp-metadata-proxy/master/images' in value:
                      self.pyoutput(feature)
          def close(self):
              pass
    PYTHONSYMBOL = FeatureProcessor
    -> AttributeExposer_5

Bookmark: Extraction de la province
ListSearcher
    ATTR_VALUE = https://raw.githubusercontent.com/federal-geospatial-platform/fgp-metadata-proxy/master/images/resampled
    CASE = CASE_SENSITIVE
    INDEX_ATTR = _list_index
    LIST_ATTR = URI{}
    MATCHTYPE = REGULAR_EXPRESSION_ENCODED
    PREFIX = thumbnail
    FOUND -> AttributeSplitter_3
AttributeSplitter_3
    ATTR_NAME = thumbnailURI
    DELIMITER = /
    DROP_EMPTY_PARTS = NO
    LIST_NAME = _list
    TRIM_TYPE = BOTH
    -> ListIndexer_2
ListIndexer_2
    INDEX = -2
    LIST_ATTR = _list{}
    -> AttributeCreator_12
AttributeCreator_12
    ATTR_TABLE = SET_TO PT (varchar(200)) = @Value(_list)
    -> FeatureMerger_3 [SUPPLIER]
    -> FeatureMerger_4 [REQUESTOR]

Bookmark: New Bookmark
Creator_5
    GEOMTYPE = Geometry Object
    NUM = 1
    CREATED -> Catalogue_Reader_3
Note: Lecture du contenu dans open Data
Catalogue_Reader_3: Catalogue Reader
    CKAN_FILTER = fq=collection:fgp
    CUSTOM_CSW_LIST_NAME = MD_Metadata{}
    CUSTOM_CSW_SCHEMA = http://www.isotc211.org/2005/gmd
    CUSTOM_CSW_VERSION = 2.0.2
    CUSTOM_URL_CSW_TYPENAMES = gmd:MD_Metadata
    SOURCE_URL = https://open.canada.ca/data/api/action
    Résultats -> AttributeExposer_6

Bookmark: Uniquement le stock PT
AttributeExposer_6
    ATTR_TABLE = license_id,,id,,metadata_modified,
    -> AttributeCreator_13
AttributeCreator_13
    ATTR_TABLE = SET_TO identifier (varchar(200)) = @Value(id)
    -> Tester_5
Tester_5
    BOOL_OP = OR
    TEST_CLAUSE = TEST @Value(license_id) != ca-ogl-lgo
    TEST_MODE = TEST
    PASSED -> AttributeSplitter_4

Bookmark: Extraction de PT à partir de la licence
AttributeSplitter_4
    ATTR_NAME = license_id
    DELIMITER = -
    DROP_EMPTY_PARTS = NO
    LIST_NAME = _list
    TRIM_TYPE = BOTH
    -> AttributeCreator_16
AttributeCreator_16
    ATTR_TABLE = SET_TO PT (varchar(200)) = @Value(_list{0})
    -> StringReplacer
StringReplacer
    CASE = NO
    FIND_TEXT = nwt
    NO_MATCH = _FME_NO_OP_
    REGEXP = NO
    REPLACE_TEXT = nt
    SRC_ATTRS = PT
    -> AttributeKeeper_6

Bookmark: Lecture des JSON sur le disque pour toutes le provinces
Creator_3
    GEOMTYPE = Geometry Object
    NUM = 1
    CREATED -> AttributeCreator_4
AttributeCreator_4
    ATTR_TABLE = SET_TO Province (varchar(200)) = BC,AB,SK,MB,ON,QC,NB,NS,PEI,NL,YT,NT
    -> AttributeSplitter
AttributeSplitter
    ATTR_NAME = Province
    DELIMITER = ,
    DROP_EMPTY_PARTS = NO
    LIST_NAME = _list
    TRIM_TYPE = BOTH
    -> ListExploder
ListExploder
    ATTR_CONFLICT_RES_LOOKUP = INCOMING_IF_CONFLICT
    INDEX_ATTR = _element_index
    LIST_ATTR = _list{}
    ATTR_ACCUM_MODE = Merge List Attributes
    ATTR_CONFLICT_RES = Use List Attribute Values
    ELEMENTS -> AttributeCreator_7
AttributeCreator_7
    ATTR_TABLE = SET_TO PT (varchar(200)) = @Value(_list)
    -> AttributeKeeper_4
AttributeKeeper_4
    CREATE_BULK_MODE_FEATURES = NO
    KEEP_ATTRS = PT
    -> FeatureReader [INITIATOR]
Note: Lecture des données JSON sur le disque
FeatureReader
    ATTR_ACCUM_MODE = Merge Initiator and Result
    ATTR_CONFLICT_RES = Use Result
    ATTR_IGNORE_NULLS = No
    COMBINE_GEOM = Use Result
    DATASET = $(IN_OUT_WORKING_DIR)\@Value(PT)\JSON_LOCAL\*.json
    FEATURETYPES = JSONFeature
    FORMAT = JSON
    INITIATOR_FIRST_OUTPUT = default
    JSON_DECODE_TEXT_STRINGS = Yes
    JSON_FEATURE_TYPE_KEY = json_featuretype
    JSON_FLATTEN_MODE = ALL_LEVELS
    JSON_GEOMETRY_FORMAT = None
    JSON_SAVE_FRAGMENTS = NO
    JSON_SCAN_MODE = AUTO
    JSON_USE_BASENAME_AS_DEFAULT_FEATURE_TYPE = No
    JSON_USE_SEARCH_ENVELOPE = NO
    ORDER_RESULTS = No
    OUTPUT_ADD_SCHEMA_ATTRIBUTES = NO
    OUTPUT_FEATURES_DISPLAY = Schema and Data Features
    <OTHER> -> AttributeExposer_3
    <REJECTED> -> Logger
AttributeExposer_3
    ATTR_TABLE = federated_date_modified,,id,
    -> AttributeCreator_15
AttributeCreator_15
    ATTR_TABLE = SET_TO identifier (varchar(200)) = @Value(id)
    -> AttributeKeeper_2
AttributeKeeper_2
    CREATE_BULK_MODE_FEATURES = NO
    KEEP_ATTRS = federated_date_modified,PT,identifier
    -> FeatureMerger_2 [SUPPLIER]
Logger
    LOG_FEATURE = LOG_ONLY
    MAXCOORDS = 20
    MAXFEATS = 20
    MESSAGE = Aucune données non geo pour @Value(PT)
    SEVERITY = INFO

Bookmark: Lecture de la collection Federated
Creator
    GEOMTYPE = Geometry Object
    NUM = 1
    CREATED -> Catalogue_Reader
Note: Lecture du contenu dans open Data de la collection federated
Catalogue_Reader: Catalogue Reader
    CKAN_FILTER = fq=collection:federated
    CUSTOM_CSW_LIST_NAME = MD_Metadata{}
    CUSTOM_CSW_SCHEMA = http://www.isotc211.org/2005/gmd
    CUSTOM_CSW_VERSION = 2.0.2
    CUSTOM_URL_CSW_TYPENAMES = gmd:MD_Metadata
    SOURCE_URL = https://open.canada.ca/data/api/action
    Résultats -> AttributeExposer_4
AttributeExposer_4
    ATTR_TABLE = collection,,id,,metadata_modified,,license_id,
    -> AttributeCreator_2
AttributeCreator_2
    ATTR_TABLE = SET_TO identifier (varchar(200)) = @Value(id)
    -> AttributeSplitter_5

Bookmark: Extraction de PT à partir de la licence
AttributeSplitter_5
    ATTR_NAME = license_id
    DELIMITER = -
    DROP_EMPTY_PARTS = NO
    LIST_NAME = _list
    TRIM_TYPE = BOTH
    -> AttributeCreator_20
AttributeCreator_20
    ATTR_TABLE = SET_TO PT (varchar(200)) = @Value(_list{0})
    -> StringReplacer_2
StringReplacer_2
    CASE = NO
    FIND_TEXT = nwt
    NO_MATCH = _FME_NO_OP_
    REGEXP = NO
    REPLACE_TEXT = nt
    SRC_ATTRS = PT
    -> FeatureMerger_2 [REQUESTOR]

Bookmark: Bloc NonGeo
Note: Validation de la condorfance des ID
FeatureMerger_2
    ATTR_ACCUM_MODE = Merge Supplier
    ATTR_CONFLICT_RES_LOOKUP = REQUESTOR_IF_CONFLICT
    IGNORE_NULLS = No
    JOIN_KEYS = @Value(identifier) @Value(identifier) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> DateTimeConverter_2
    UNMERGED_REQUESTOR -> NG-CkanPasDisque (writer XLSXW_1)
    UNUSED_SUPPLIER -> AttributeCreator_21
Note: Les données à jour sur le disque n'ont pas été transférées dans CKAN
NG-ProblemeDate (writer XLSXW_1)
    attributes: date_json_local date(200), date_ckan date(200), identifier string(200), PT string(200)
Note: Données présentes dans CKAN mais absente du disque. Fort proablement une erreur de maintenance, la donnée a été supprimée du disque mais pas de CKAN
NG-CkanPasDisque (writer XLSXW_1)
    attributes: identifier string(200), PT string(200)
AttributeCreator_21
    ATTR_TABLE = SET_TO date_json_local (varchar(200)) = @Value(federated_date_modified)
    -> NG_DisquePasCKAN (writer XLSXW_1)
Note: Données présentes sur le Disque mais absente de CKAN. Fort à parier un problème de ocntenu rendant l'ajout de la métadonnée impossible
NG_DisquePasCKAN (writer XLSXW_1)
    attributes: date_json_local string(200), identifier string(200), PT string(200)

Bookmark: Validetion des dates. On doit s'assurer que la date de mise à jour est plus récente au niveau CKAN que du disque. Sinon, on a une erreur de mise à jour
DateTimeConverter_2
    DATETIME_ATTR = metadata_modified
    OUT_FORMAT = %Y%m%d
    PASSTHROUGH = NO
    REPAIR_INPUT = YES
    -> DateTimeConverter_4
DateTimeConverter_4
    DATETIME_ATTR = federated_date_modified
    IN_FORMAT = %Y-%m-%d
    OUT_FORMAT = %Y%m%d
    PASSTHROUGH = NO
    REPAIR_INPUT = YES
    -> DateTimeCalculator
DateTimeCalculator
    MODE = DATETIMECALC_3_CALCULATE_INTERVAL
    OPERATION_PARAMETERS = START_DATETIME]@Value(metadata_modified)]END_DATETIME]@Value(federated_date_modified)]RESULT_TYPE]DAYS]RESULT_INTERVAL]_result_interval]FME_CONTROLLER_QUERY_FILE]transformers/dependencies/datetimecalculator/DATETIMECALC_3_CALCULATE_INTERVAL.fme]FME_CONTROLLER_CHOICE]DATETIMECALC_3_CALCULATE_INTERVAL
    -> Tester
Tester
    BOOL_OP = OR
    TEST_CLAUSE = TEST @Value(_result_interval) > 0
    TEST_MODE = TEST
    PASSED -> AttributeCreator_3
AttributeCreator_3
    ATTR_TABLE:
      SET_TO date_json_local (varchar(200)) = @Value(federated_date_modified)
      SET_TO date_ckan (varchar(200)) = @Value(metadata_modified)
    -> NG-ProblemeDate (writer XLSXW_1)
