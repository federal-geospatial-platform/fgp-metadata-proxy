FME workspace OGSL_PROD.fmw
Title: OGSL_PROD
Description: Description

Parameters:
- ACTIVATE_TRANSLATION = No
- CATALOGUE_READER_SELECT = Yes
- IN_OUT_WORKING_DIR = C:\Data\PT_Harvester
- IN_CSV_LOOKUP_TABLES_DIR = $(IN_OUT_WORKING_DIR)\LOOKUP_TABLES   # DEFAULT_IN_CSV_LOOKUP_TABLES_DIR
- LOG_FILE = $(IN_OUT_WORKING_DIR)\$(P-T_ABBR)\LOG\AB_FGP_XML_BUILDER.log
- OUT_XLS_NOTIFICATION_DIR = $(IN_OUT_WORKING_DIR)\$(P-T_ABBR)\XLS
- OUT_geodcat_DIR = $(IN_OUT_WORKING_DIR)\$(P-T_ABBR)\geodcat
- OUT_old_geodcat_DIR = $(IN_OUT_WORKING_DIR)\$(P-T_ABBR)\old_geodcat
- ENV = STAGING
- FME_SHAREDRESOURCE_DATA = C:\Data   # FME Flow Data Directory

Writers:
- TEXTLINE_1: TEXTLINE to $(IN_OUT_WORKING_DIR)\$(P-T_ABBR)\XML_FAILED
- TEXTLINE_2: TEXTLINE to $(IN_OUT_WORKING_DIR)\$(P-T_ABBR)\XML_LOCAL
- TEXTLINE_3: TEXTLINE to $(IN_OUT_WORKING_DIR)\$(P-T_ABBR)\XML_PASSED
- XLSXW_1: XLSXW to $(OUT_XLS_NOTIFICATION_DIR)
- TEXTLINE_4: TEXTLINE to $(IN_OUT_WORKING_DIR)\$(P-T_ABBR)\JSON_LOCAL

Creator_2
    GEOMTYPE = Geometry Object
    NUM = 1
    CREATED -> Tester_2
Note: Supprimer le Startup Python Script in Workspace Parameters / Scripting quand la migration sera terminée en local
Tester_2
    BOOL_OP = OR
    TEST_CLAUSE = TEST $(CATALOGUE_READER_SELECT) = Yes
    TEST_MODE = TEST
    PASSED -> Catalogue_Reader_3
    PASSED -> Catalogue_Reader
    FAILED -> FeatureReader_2 [INITIATOR]
    FAILED -> FeatureReader_3 [INITIATOR]
AttributeExposer_9
    ATTR_TABLE = id,,citation.en,,citation.fr,,notes_translated.en,,notes_translated.fr,
    -> AttributeKeeper_2
    -> FeatureMerger_6 [REQUESTOR]
FeatureMerger_6
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(id) @Value(id_original) AUTO
    MERGE_TYPE_VAL = ATTRIBUTES
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes Only
    MERGED -> FeatureMerger_5 [REQUESTOR]
FeatureMerger_5
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(id) @Value(id_original) AUTO
    MERGE_TYPE_VAL = ATTRIBUTES
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes Only
    MERGED -> AttributeRemover_3
    MERGED -> AttributeKeeper_6
Note: Description normalize newlines
PythonCaller
    PYTHONSOURCE:
      import fme
      import fmeobjects


      def processFeature(feature):
          # Read the original text attribute
          text = feature.getAttribute('Description (EN)')
          text2 = feature.getAttribute('Description (FR)')

          if text:
              # Replace real newline characters with <br>
              text = text.replace("\r\n", "<br>")  # Windows-style newlines
              text = text.replace("\n", "<br>")    # Unix-style newlines
              text = text.replace("\r", "<br>")    # Rare, but safe to include

          if text2:
              # Replace real newline characters with <br>
              text2 = text2.replace("\r\n", "<br>")  # Windows-style newlines
              text2 = text2.replace("\n", "<br>")    # Unix-style newlines
              text2 = text2.replace("\r", "<br>")    # Rare, but safe to include

              # Write the cleaned text back to a new attribute
              feature.setAttribute("Description (EN)", text)
              feature.setAttribute("Description (FR)", text2)

          pass
    PYTHONSYMBOL = processFeature
    -> PythonCaller_4
Note: Organisation names, individual names
PythonCaller_4
    NEW_ATTRIBUTES = all_individual_names buffer all_organisation_names buffer
    PYTHONSOURCE:
      import fme
      import fmeobjects


      def processFeature(feature):
          # Read the list attributes from FME
          individuals = feature.getAttribute('cited-responsible-party{}.individual-name')
          organisations = feature.getAttribute('cited-responsible-party{}.organisation-name')

          # FME returns None if the list doesn't exist, so convert to empty lists
          if individuals is None:
              individuals = []
          if organisations is None:
              organisations = []

          # Remove empty or null entries
          individuals = [i for i in individuals if i not in (None, '')]
          organisations = [o for o in organisations if o not in (None, '')]

          # Concatenate with "; "
          individuals_joined = "; ".join(individuals)
          organisations_joined = "; ".join(organisations)

          # Set new attributes on the feature
          feature.setAttribute('all_individual_names', individuals_joined)
          feature.setAttribute('all_organisation_names', organisations_joined)

          # Return the feature
          return feature
    PYTHONSYMBOL = processFeature
    -> PythonCaller_5
AWS_translate_errors (writer XLSXW_1)
    attributes: _aws_activation string(200), _mode string(200), _attr2translate string(200), _attrlist2translate string(200), Identifier.Artifact string(200), disclaimer string(20), _translation_status string(20)
Note: RecordKeeper.LastUserToModify
AttributeCreator_16
    ATTR_TABLE = SET_TO RecordKeeper.LastUserToModify (varchar(200)) = OSDP.@Value(Contributor System).@Value(Content Category)
    -> AttributeExposer_13
Creator_3
    GEOMTYPE = Geometry Object
    NUM = 1
    CREATED -> AttributeCreator_22
    CREATED -> Junction
Note: FeatureReader : Initiator
Junction
    -> Junction_2
FeatureMerger_9
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = 1 1 AUTO
    MERGE_TYPE_VAL = ATTRIBUTES
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes Only
    MERGED -> ATTRIBUTE_UNEXPOSER

Bookmark: Reading FGP prod catalogue
Catalogue_Reader_3: Catalogue Reader
    CUSTOM_CSW_LIST_NAME = MD_Metadata{}
    CUSTOM_CSW_SCHEMA = http://www.isotc211.org/2005/gmd
    CUSTOM_CSW_VERSION = 2.0.2
    CUSTOM_URL_CSW_TYPENAMES = gmd:MD_Metadata
    SOURCE_URL = https://open.canada.ca/data/api/action
    Résultats -> AttributeExposer
Note: Reading FFS FGP prod file
FeatureReader_3 [off]
    ATTR_ACCUM_MODE = Only Use Result
    CLIP_TO_ENVELOPE = NO
    COMBINE_GEOM = Use Result
    DATASET = C:\Users\gepotvin\Downloads\OGSL_2026-7-15-T131136\out_catalogue.ffs
    FFS_USE_SEARCH_ENVELOPE = NO
    FORMAT = FFS
    INITIATOR_FIRST_OUTPUT = default
    INTERACT = NONE
    ORDER_RESULTS = No
    OUTPUT_ADD_SCHEMA_ATTRIBUTES = NO
    OUTPUT_FEATURES_DISPLAY = Schema and Data Features
    <OTHER> -> AttributeExposer
AttributeExposer
    ATTR_TABLE = title_translated.en,,title_translated.fr,,id,
    -> DuplicateFilter
DuplicateFilter
    INPUT_ORDERED_CHOICE_LOOKUP = NO
    KEYATTR = title_translated.en title_translated.fr id
    INPUT_ORDERED_CHOICE = No
    UNIQUE -> FeatureMerger [SUPPLIER]

Bookmark: Reading OGSL ckan datasets
Catalogue_Reader: Catalogue Reader
    CUSTOM_CSW_LIST_NAME = DefaultNoList{}
    CUSTOM_URL = https://catalogue.ogsl.ca/fr/api/3/action
    SOURCE_URL = Manuel
    Résultats -> AttributeExposer_2
Note: Reading FFS OGSL file
FeatureReader_2 [off]
    ATTR_ACCUM_MODE = Only Use Result
    CLIP_TO_ENVELOPE = NO
    COMBINE_GEOM = Use Result
    DATASET = C:\Users\gepotvin\Downloads\OGSL_2026-7-15-T131136\out_ogsl.ffs
    FFS_USE_SEARCH_ENVELOPE = NO
    FORMAT = FFS
    INITIATOR_FIRST_OUTPUT = default
    INTERACT = NONE
    ORDER_RESULTS = No
    OUTPUT_ADD_SCHEMA_ATTRIBUTES = NO
    OUTPUT_FEATURES_DISPLAY = Schema and Data Features
    <OTHER> -> AttributeExposer_2
AttributeExposer_2
    ATTR_TABLE = title,,title_translated.en,,title_translated.fr,,extras{}.key,,extras{}.value,,extras{3}.key,,extras{3}.value,,extras{2}.key,,extras{2}.value,
    -> PythonCaller_3

Bookmark: get id from guid extra{} key value
PythonCaller_3
    NEW_ATTRIBUTES = id buffer
    PYTHONSOURCE:
      import fme
      import fmeobjects
      from Python.FME_utils import FME_utils

      #import sys
      #sys.path.append(r"C:\Data\PT_Harvester\Transformers")
      #import Python.FME_utils as FME_utils



      # Template Function interface:
      # When using this function, make sure its name is set as the value of
      # the 'Class or Function to Process Features' transformer parameter
      def processFeature(feature):
          #max_index=FME_utils.FME_utils.max_index_attribute_list(feature, 'extras{}')
          max_index=FME_utils.max_index_attribute_list(feature, 'extras{}')
          for j in range(max_index+1):
              key = feature.getAttribute('extras{%i}.key'%(j))
              value = feature.getAttribute('extras{%i}.value'%(j))

              if key == 'guid':
                feature.setAttribute('id',value)



      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> StringReplacer_4
StringReplacer_4
    CASE = NO
    FIND_TEXT = ca.cioos_
    NO_MATCH = _FME_NO_OP_
    REGEXP = NO
    SRC_ATTRS = id
    -> FeatureMerger [REQUESTOR]

Bookmark: exclude data already in the catalogue
FeatureMerger
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(title_translated.fr) @Value(title_translated.fr) AUTO
    MERGE_TYPE_VAL = ATTRIBUTES
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes Only
    UNMERGED_REQUESTOR -> FeatureMerger_2 [REQUESTOR]
    UNUSED_SUPPLIER -> FeatureMerger_2 [SUPPLIER]
FeatureMerger_2
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(title_translated.en) @Value(title_translated.en) AUTO
    MERGE_TYPE_VAL = ATTRIBUTES
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes Only
    UNMERGED_REQUESTOR -> AttributeExposer_3

Bookmark: License filtering
AttributeExposer_3
    ATTR_TABLE = license_id,,license_title,
    -> AttributeCreator_21
AttributeCreator_21
    ATTR_TABLE = SET_TO license_id (varchar(200)) = FME_CONDITIONAL:DEFAULT_VALUE'_FME_NO_OP_'BOOL_OP;OR;COMPOSITE_TEST;1;TEST @Value(license_id) = CC-BY-4.0'CC-BY-40'FME_NUM_CONDITIONS2___
    -> LICENSE_FILTER_NG
LICENSE_FILTER_NG
    FEATURE_TYPE = License_OGSL
    IN_CSV_LOOKUP_TABLES_DIR = $(IN_CSV_LOOKUP_TABLES_DIR)
    LICENSE_ATT = @Value(license_id)
    P-T_ABBR = $(P-T_ABBR)
    LICENSE_FILTER_PASSED -> AttributeExposer_9
    UNKNOWN_LICENSE -> UNKNOWN_LICENCE (writer XLSXW_1)
UNKNOWN_LICENCE (writer XLSXW_1)
    attributes: license_id auto(20), id string(37)

Bookmark: manage Citations
AttributeKeeper_2
    CREATE_BULK_MODE_FEATURES = NO
    KEEP_ATTRS = citation.en,citation.fr,id
    -> AttributeCreator_13
AttributeCreator_13
    ATTR_TABLE = SET_TO id_original (varchar(200)) = @Value(id)
    -> StringReplacer
StringReplacer
    CASE = NO
    FIND_TEXT = \"
    NO_MATCH = _FME_NO_OP_
    REGEXP = NO
    REPLACE_TEXT = "
    SRC_ATTRS = citation.en,citation.fr
    -> StringReplacer_2
StringReplacer_2
    CASE = NO
    FIND_TEXT = ^\[|\]$
    NO_MATCH = _FME_NO_OP_
    REGEXP = YES
    SRC_ATTRS = citation.en,citation.fr
    -> JSONFlattener
    -> JSONFlattener_2

Bookmark: citation FR
JSONFlattener_2
    ERROR_LIST_ATTR = _json_error
    JSON_DOCUMENT = @Value(citation.fr)
    READ_FROM_FILE = NO
    RECURSIVE = YES
    -> AttributeExposer_11
AttributeExposer_11
    ATTR_TABLE = author{},,title,,DOI,,type,,issued{}.date-parts{},,URL,
    -> ListRenamer
ListRenamer
    LEAVE_ORIG = No
    LIST_ACTION = Rename
    LIST_COMPONENT_NAMES = author{},author_fr{}
    LIST_NAME = author{}
    -> PythonCaller_9
PythonCaller_9
    NEW_ATTRIBUTES = citation_authors_fr buffer
    PYTHONSOURCE:
      import fme
      import fmeobjects
      import re


      # ----------------------------------------------------------------------
      # Helpers for name formatting (FRENCH NAMESPACE)
      # ----------------------------------------------------------------------

      def fr_initial_from_token(token):
          """
          Return the first Unicode letter in token, uppercased.
          Preserves accents (É -> É).
          """
          for ch in token.strip():
              if ch.isalpha():
                  return ch.upper()
          return ""


      def fr_build_initials(given):
          """
          Convert given names to initials, preserving hyphens & accents.

          Examples:
            "Jean Étienne"   -> "J. É."
            "Jean-Étienne"  -> "J.-É."
            "maría josé"    -> "M. J."
          """
          if not given:
              return ""

          parts = [p for p in re.split(r"\s+", given.strip()) if p]
          out_parts = []

          for part in parts:
              subparts = [sp for sp in part.split("-") if sp]
              sub_initials = []

              for sp in subparts:
                  ini = fr_initial_from_token(sp)
                  if ini:
                      sub_initials.append(f"{ini}.")

              if sub_initials:
                  out_parts.append("-".join(sub_initials))

          return " ".join(out_parts)


      # ----------------------------------------------------------------------
      # Conjoining helpers (FRENCH)
      # ----------------------------------------------------------------------

      def fr_conjoin_people(items):
          """
          French reference list rules for people or mixed authors:

            - 1 auteur   : "A"
            - 2 auteurs  : "A, et B"
            - 3–20       : "A, B, C, et D"
            - 21+        : 19 premiers, ..., dernier
          """
          n = len(items)

          if n == 0:
              return ""
          if n == 1:
              return items[0]
          if n <= 20:
              return ", ".join(items[:-1]) + f", et {items[-1]}"

          # 21+ auteurs
          return ", ".join(items[:19]) + ", ..., " + items[-1]


      def fr_conjoin_organisations(items):
          """
          Organisation-only lists (NO comma before 'et'):

            - "Organisme A"
            - "Organisme A et Organisme B"
            - "Organisme A, Organisme B et Organisme C"
          """
          n = len(items)

          if n == 0:
              return ""
          if n == 1:
              return items[0]
          if n == 2:
              return f"{items[0]} et {items[1]}"
          return ", ".join(items[:-1]) + f" et {items[-1]}"


      # ----------------------------------------------------------------------
      # Author formatter (FRENCH)
      # ----------------------------------------------------------------------

      def fr_format_authors_person_with_org(author_tuples):
          """
          Format authors using French typography:

            - Personne seule      -> "Famille, I."
            - Organisation seule  -> "Organisation"
            - Personne + org      -> "Famille, I. (Organisation)"

          Special rule:
            If ALL authors are organisations, do NOT use a comma before 'et'.
          """
          authors = []
          all_orgs_only = True

          for family, given, organisation in author_tuples:
              family = (family or "").strip()
              given = (given or "").strip()
              organisation = (organisation or "").strip()

              person = ""
              if family or given:
                  all_orgs_only = False
                  initials = fr_build_initials(given)
                  if family and initials:
                      person = f"{family}, {initials}"
                  elif family:
                      person = family
                  elif initials:
                      person = initials

              if person and organisation:
                  authors.append(f"{person} ({organisation})")
                  all_orgs_only = False
              elif person:
                  authors.append(person)
              elif organisation:
                  authors.append(organisation)

          if all_orgs_only:
              return fr_conjoin_organisations(authors)

          return fr_conjoin_people(authors)


      # ----------------------------------------------------------------------
      # FeatureProcessor (FME entry point)
      # ----------------------------------------------------------------------

      class FeatureProcessor:
          def __init__(self):
              pass

          def input(self, feature):

              # --------------------------------------------------------------
              # 1. Discover author indices
              # --------------------------------------------------------------
              indices = set()

              for name in feature.getAllAttributeNames():
                  if name.startswith("author_fr{") and "}" in name:
                      try:
                          idx = int(name.split("{", 1)[1].split("}", 1)[0])
                          indices.add(idx)
                      except ValueError:
                          pass

              # --------------------------------------------------------------
              # 2. Collect author data
              # --------------------------------------------------------------
              author_tuples = []

              for i in sorted(indices):
                  family = feature.getAttribute(f"author_fr{{{i}}}.family")
                  given = feature.getAttribute(f"author_fr{{{i}}}.given")
                  organisation = feature.getAttribute(f"author_fr{{{i}}}.literal")

                  author_tuples.append((family, given, organisation))

              # --------------------------------------------------------------
              # 3. Build French citation author string
              # --------------------------------------------------------------
              citation_authors_fr = fr_format_authors_person_with_org(author_tuples)
              feature.setAttribute("citation_authors_fr", citation_authors_fr)

              self.pyoutput(feature)

          def close(self):
              pass
    PYTHONSYMBOL = FeatureProcessor
    -> AttributeCreator_12
AttributeCreator_12
    ATTR_TABLE:
      SET_TO data_type (varchar(200)) = FME_CONDITIONAL:DEFAULT_VALUE'_FME_NO_OP_'BOOL_OP;OR;COMPOSITE_TEST;1;CASE_INSENSITIVE_TEST @Value(type) = dataset'Data set'BOOL_OP;OR;COMPOSITE_TEST;1;CASE_INSENSITIVE_TEST @Value(type) = document'Document'BOOL_OP;OR;COMPOSITE_TEST;1;CASE_INSENSITIVE_TEST @Value(type) = software'Software'FME_NUM_CONDITIONS4___
      SET_TO Citation.Value (FR)[1] (varchar(200)) = FME_CONDITIONAL:DEFAULT_VALUE'_FME_NO_OP_'BOOL_OP;AND;COMPOSITE_TEST;1 AND 2 AND 3;CASE_INSENSITIVE_TEST DOI ATTRIBUTE_HAS_A_VALUE _FME_BLANK_STRING_;CASE_INSENSITIVE_TEST @Value(type) = dataset;CASE_INSENSITIVE_TEST @Value(citation_authors_fr) ENDS_WITH .'@Value(citation_authors_fr) (@Value(issued{0}.date-parts{0})). <i>@Value(title)</i> [@Value(data_type)]. https://doi.org/@Value(DOI)'BOOL_OP;AND;COMPOSITE_TEST;1 AND 2 AND 3;CASE_INSENSITIVE_TEST DOI ATTRIBUTE_HAS_A_VALUE _FME_BLANK_STRING_;CASE_INSENSITIVE_TEST @Value(type) = dataset;CASE_INSENSITIVE_TEST @Value(citation_authors_fr) NOT_ENDS_WITH .'@Value(citation_authors_fr). (@Value(issued{0}.date-parts{0})). <i>@Value(title)</i> [@Value(data_type)]. https://doi.org/@Value(DOI)'BOOL_OP;AND;COMPOSITE_TEST;1 AND 2 AND 3;CASE_INSENSITIVE_TEST DOI ATTRIBUTE_HAS_A_VALUE _FME_BLANK_STRING_;CASE_INSENSITIVE_TEST @Value(type) != dataset;CASE_INSENSITIVE_TEST @Value(citation_authors_fr) ENDS_WITH .'@Value(citation_authors_fr) (@Value(issued{0}.date-parts{0})). <i>@Value(title)</i>. https://doi.org/@Value(DOI)'BOOL_OP;AND;COMPOSITE_TEST;1 AND 2 AND 3;CASE_INSENSITIVE_TEST DOI ATTRIBUTE_HAS_A_VALUE _FME_BLANK_STRING_;CASE_INSENSITIVE_TEST @Value(type) != dataset;CASE_INSENSITIVE_TEST @Value(citation_authors_fr) NOT_ENDS_WITH .'@Value(citation_authors_fr). (@Value(issued{0}.date-parts{0})). <i>@Value(title)</i>. https://doi.org/@Value(DOI)'BOOL_OP;AND;COMPOSITE_TEST;1 AND 2 AND 3;CASE_INSENSITIVE_TEST DOI NOT_ATTRIBUTE_HAS_A_VALUE _FME_BLANK_STRING_;CASE_INSENSITIVE_TEST @Value(type) = dataset;CASE_INSENSITIVE_TEST @Value(citation_authors_fr) ENDS_WITH .'@Value(citation_authors_fr) (@Value(issued{0}.date-parts{0})). <i>@Value(title)</i> [@Value(data_type)]. @Value(URL)'BOOL_OP;AND;COMPOSITE_TEST;1 AND 2 AND 3;CASE_INSENSITIVE_TEST DOI NOT_ATTRIBUTE_HAS_A_VALUE _FME_BLANK_STRING_;CASE_INSENSITIVE_TEST @Value(type) = dataset;CASE_INSENSITIVE_TEST @Value(citation_authors_fr) NOT_ENDS_WITH .'@Value(citation_authors_fr). (@Value(issued{0}.date-parts{0})). <i>@Value(title)</i> [@Value(data_type)]. @Value(URL)'FME_NUM_CONDITIONS7___
      SET_TO Creator (FR) (varchar(200)) = @Value(citation_authors_fr)
    -> FeatureMerger_6 [SUPPLIER]

Bookmark: citation EN
JSONFlattener
    ERROR_LIST_ATTR = _json_error
    JSON_DOCUMENT = @Value(citation.en)
    READ_FROM_FILE = NO
    RECURSIVE = YES
    -> AttributeExposer_10
AttributeExposer_10
    ATTR_TABLE = author{},,title,,DOI,,type,,issued{}.date-parts{},,URL,
    -> PythonCaller_7
PythonCaller_7
    NEW_ATTRIBUTES = citation_authors_en buffer
    PYTHONSOURCE:
      import fme
      import fmeobjects
      import re


      # ----------------------------------------------------------------------
      # Helpers for name formatting
      # ----------------------------------------------------------------------

      def _initial_from_token(token: str) -> str:
          """
          Return the first Unicode letter in token, uppercased.
          Preserves accents (É -> É).
          """
          for ch in token.strip():
              if ch.isalpha():
                  return ch.upper()
          return ""


      def build_initials(given: str) -> str:
          """
          Convert given names to APA-style initials, preserving hyphens & accents.
          """
          if not given:
              return ""

          parts = [p for p in re.split(r"\s+", given.strip()) if p]
          out_parts = []

          for part in parts:
              subparts = [sp for sp in part.split("-") if sp]
              sub_initials = []

              for sp in subparts:
                  ini = _initial_from_token(sp)
                  if ini:
                      sub_initials.append(f"{ini}.")

              if sub_initials:
                  out_parts.append("-".join(sub_initials))

          return " ".join(out_parts)


      # ----------------------------------------------------------------------
      # Conjoining helpers (ENGLISH)
      # ----------------------------------------------------------------------

      def _conjoin_apa_people(items):
          """
          APA 7 reference list rules for people or mixed authors.

            - 1 author: "A"
            - 2 authors: "A, & B"
            - 3–20 authors: "A, B, C, & D"
            - 21+ authors: first 19, ..., last
          """
          n = len(items)

          if n == 0:
              return ""
          if n == 1:
              return items[0]
          if n <= 20:
              return ", ".join(items[:-1]) + f", & {items[-1]}"

          return ", ".join(items[:19]) + ", ..., " + items[-1]


      def _conjoin_organisations(items):
          """
          Organisation-only author lists (NO comma before &):

            - "Org A"
            - "Org A & Org B"
            - "Org A, Org B & Org C"
          """
          n = len(items)

          if n == 0:
              return ""
          if n == 1:
              return items[0]
          if n == 2:
              return f"{items[0]} & {items[1]}"
          return ", ".join(items[:-1]) + f" & {items[-1]}"


      # ----------------------------------------------------------------------
      # Author formatter: person + organisation
      # ----------------------------------------------------------------------

      def format_authors_person_with_org(author_tuples):
          """
          Formats authors and applies correct APA conjoining.

            - Person only        -> "Family, I."
            - Organisation only -> "Organisation"
            - Both              -> "Family, I. (Organisation)"

          Special rule:
            If ALL authors are organisations, no comma before '&'.
          """
          authors = []
          all_orgs_only = True

          for family, given, organisation in author_tuples:
              family = (family or "").strip()
              given = (given or "").strip()
              organisation = (organisation or "").strip()

              person = ""
              if family or given:
                  all_orgs_only = False
                  initials = build_initials(given)
                  if family and initials:
                      person = f"{family}, {initials}"
                  elif family:
                      person = family
                  elif initials:
                      person = initials

              if person and organisation:
                  authors.append(f"{person} ({organisation})")
                  all_orgs_only = False
              elif person:
                  authors.append(person)
              elif organisation:
                  authors.append(organisation)

          if all_orgs_only:
              return _conjoin_organisations(authors)

          return _conjoin_apa_people(authors)


      # ----------------------------------------------------------------------
      # FeatureProcessor (FME entry point)
      # ----------------------------------------------------------------------

      class FeatureProcessor:
          def __init__(self):
              pass

          def input(self, feature):
              # --------------------------------------------------------------
              # 1. Discover author indices
              # --------------------------------------------------------------
              indices = set()

              for name in feature.getAllAttributeNames():
                  if name.startswith("author{") and "}" in name:
                      try:
                          idx = int(name.split("{", 1)[1].split("}", 1)[0])
                          indices.add(idx)
                      except ValueError:
                          pass

              # --------------------------------------------------------------
              # 2. Collect author data + DEBUG organisation literals
              # --------------------------------------------------------------
              author_tuples = []

              for i in sorted(indices):
                  family = feature.getAttribute(f"author{{{i}}}.family")
                  given = feature.getAttribute(f"author{{{i}}}.given")
                  organisation = feature.getAttribute(f"author{{{i}}}.literal")

                  # DEBUG: expose raw organisation literal
                  if organisation:
                      feature.setAttribute(f"_DEBUG_org_literal_{i}", organisation)

                  author_tuples.append((family, given, organisation))

              # --------------------------------------------------------------
              # 3. Build citation author string
              # --------------------------------------------------------------
              citation_authors_en = format_authors_person_with_org(author_tuples)
              feature.setAttribute("citation_authors_en", citation_authors_en)

              self.pyoutput(feature)

          def close(self):
              pass
    PYTHONSYMBOL = FeatureProcessor
    -> AttributeCreator_11
AttributeCreator_11
    ATTR_TABLE:
      SET_TO data_type (varchar(200)) = FME_CONDITIONAL:DEFAULT_VALUE'_FME_NO_OP_'BOOL_OP;OR;COMPOSITE_TEST;1;CASE_INSENSITIVE_TEST @Value(type) = dataset'Data set'BOOL_OP;OR;COMPOSITE_TEST;1;CASE_INSENSITIVE_TEST @Value(type) = document'Document'BOOL_OP;OR;COMPOSITE_TEST;1;CASE_INSENSITIVE_TEST @Value(type) = software'Software'FME_NUM_CONDITIONS4___
      SET_TO Citation.Value (EN)[1] (varchar(200)) = FME_CONDITIONAL:DEFAULT_VALUE'_FME_NO_OP_'BOOL_OP;AND;COMPOSITE_TEST;1 AND 2 AND 3;CASE_INSENSITIVE_TEST DOI ATTRIBUTE_HAS_A_VALUE _FME_BLANK_STRING_;CASE_INSENSITIVE_TEST @Value(type) = dataset;CASE_INSENSITIVE_TEST @Value(citation_authors_en) ENDS_WITH .'@Value(citation_authors_en) (@Value(issued{0}.date-parts{0})). <i>@Value(title)</i> [@Value(data_type)]. https://doi.org/@Value(DOI)'BOOL_OP;AND;COMPOSITE_TEST;1 AND 2 AND 3;CASE_INSENSITIVE_TEST DOI ATTRIBUTE_HAS_A_VALUE _FME_BLANK_STRING_;CASE_INSENSITIVE_TEST @Value(type) = dataset;CASE_INSENSITIVE_TEST @Value(citation_authors_en) NOT_ENDS_WITH .'@Value(citation_authors_en). (@Value(issued{0}.date-parts{0})). <i>@Value(title)</i> [@Value(data_type)]. https://doi.org/@Value(DOI)'BOOL_OP;AND;COMPOSITE_TEST;1 AND 2 AND 3;CASE_INSENSITIVE_TEST DOI ATTRIBUTE_HAS_A_VALUE _FME_BLANK_STRING_;CASE_INSENSITIVE_TEST @Value(type) != dataset;CASE_INSENSITIVE_TEST @Value(citation_authors_en) ENDS_WITH .'@Value(citation_authors_en) (@Value(issued{0}.date-parts{0})). <i>@Value(title)</i>. https://doi.org/@Value(DOI)'BOOL_OP;AND;COMPOSITE_TEST;1 AND 2 AND 3;CASE_INSENSITIVE_TEST DOI ATTRIBUTE_HAS_A_VALUE _FME_BLANK_STRING_;CASE_INSENSITIVE_TEST @Value(type) != dataset;CASE_INSENSITIVE_TEST @Value(citation_authors_en) NOT_ENDS_WITH .'@Value(citation_authors_en). (@Value(issued{0}.date-parts{0})). <i>@Value(title)</i>. https://doi.org/@Value(DOI)'BOOL_OP;AND;COMPOSITE_TEST;1 AND 2 AND 3;CASE_INSENSITIVE_TEST DOI NOT_ATTRIBUTE_HAS_A_VALUE _FME_BLANK_STRING_;CASE_INSENSITIVE_TEST @Value(type) = dataset;CASE_INSENSITIVE_TEST @Value(citation_authors_en) ENDS_WITH .'@Value(citation_authors_en) (@Value(issued{0}.date-parts{0})). <i>@Value(title)</i> [@Value(data_type)]. @Value(URL)'BOOL_OP;AND;COMPOSITE_TEST;1 AND 2 AND 3;CASE_INSENSITIVE_TEST DOI NOT_ATTRIBUTE_HAS_A_VALUE _FME_BLANK_STRING_;CASE_INSENSITIVE_TEST @Value(type) = dataset;CASE_INSENSITIVE_TEST @Value(citation_authors_en) NOT_ENDS_WITH .'@Value(citation_authors_en). (@Value(issued{0}.date-parts{0})). <i>@Value(title)</i> [@Value(data_type)]. @Value(URL)'FME_NUM_CONDITIONS7___
      SET_TO Creator (EN) (varchar(200)) = @Value(citation_authors_en)
    -> FeatureMerger_5 [SUPPLIER]

Bookmark: Manage attributes
AttributeRemover_3
    REMOVE_ATTRS = notes_translated.en,notes_translated.fr
    -> ATTRIBUTE_VALUE_TEXT_CLEANER
ATTRIBUTE_VALUE_TEXT_CLEANER
    -> FeatureMerger_3 [REQUESTOR]
AttributeKeeper_6
    CREATE_BULK_MODE_FEATURES = NO
    KEEP_ATTRS = notes_translated.en,notes_translated.fr,id
    -> FeatureMerger_3 [SUPPLIER]
FeatureMerger_3
    ATTR_ACCUM_MODE = Merge Supplier
    ATTR_CONFLICT_RES_LOOKUP = REQUESTOR_IF_CONFLICT
    IGNORE_NULLS = No
    JOIN_KEYS = @Value(id) @Value(id) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> DEFAULT_ATTRIBUTE_MAPPER_NG
DEFAULT_ATTRIBUTE_MAPPER_NG
    FEATURE_TYPE = Default_OGSL
    IN_CSV_LOOKUP_TABLES_DIR = $(IN_CSV_LOOKUP_TABLES_DIR)
    P-T_ABBR = $(P-T_ABBR)
    -> ATTRIBUTE_MANAGER_NG
ATTRIBUTE_MANAGER_NG
    IN_YAML_TEXT:
      Identifier.Artifact:
           action: attribute_overwrite
           attr2set:  id

      Title (EN):
           action: attribute_overwrite
           attr2set: title_translated.en

      Title (FR):
           action: attribute_overwrite
           attr2set: title_translated.fr

      Description (EN):
           action: attribute_overwrite
           attr2set: notes_translated.en

      Description (FR):
           action: attribute_overwrite
           attr2set: notes_translated.fr

      Date.LastUpdate:
           action: attribute_overwrite
           attr2set: metadata_modified

      Date.Start:
           action: attribute_overwrite
           attr2set: temporal-extent{0}.begin

      Date.End:
           action: attribute_overwrite
           attr2set: temporal-extent{0}.end

      Rights.License:
           action: attribute_overwrite
           attr2set: license_id

      UpdateFrequency:
           action: attribute_overwrite
           attr2set: frequency-of-update

      Creator (EN) 2:
           action: attribute_overwrite
           attr2set: organization.title_translated.en

      Creator (FR) 2:
           action: attribute_overwrite
           attr2set: organization.title_translated.fr
    -> AttributeExposer_4

Bookmark: Manage keywords
AttributeExposer_4
    ATTR_TABLE = keywords.en{},,keywords.fr{},,"Description (EN)",,"Description (FR)",,metadata_modified,,temporal-extent{}.begin,,temporal-extent{}.end,,extras{}.key,,extras{}.value,,unique-resource-identifier-full{}.code,,"Creator (EN)",,"Creator (FR)",,resources{},,metadata-language,,citation.en,,citation.fr,,Identifier.Artifact,,bbox-east-long,,bbox-north-lat,,bbox-south-lat,,bbox-west-long,,"Contributor System",,DOI,,ecv{},,eov{},
    -> ListDuplicateRemover
ListDuplicateRemover
    SRC_LIST = keywords.en{}
    -> ListConcatenator
ListConcatenator
    DROP_EMPTY_PARTS = No
    LIST_ATTR = keywords.en{}
    SEP = "; "
    VAL_ATTR = Keywords (EN)
    -> ListDuplicateRemover_2
ListDuplicateRemover_2
    SRC_LIST = keywords.fr{}
    -> ListConcatenator_2
ListConcatenator_2
    DROP_EMPTY_PARTS = No
    LIST_ATTR = keywords.fr{}
    SEP = "; "
    VAL_ATTR = Keywords (FR)
    -> AttributeCreator_6
AttributeCreator_6
    ATTR_TABLE = SET_TO _order (varchar(200)) = 2
    -> ListDuplicateRemover_3

Bookmark: New Bookmark
ListDuplicateRemover_3
    SRC_LIST = ecv{}
    -> ListDuplicateRemover_4
ListDuplicateRemover_4
    SRC_LIST = eov{}
    -> ListConcatenator_3
ListConcatenator_3
    DROP_EMPTY_PARTS = No
    LIST_ATTR = ecv{}
    SEP = "; "
    VAL_ATTR = ecv
    -> ListConcatenator_4
ListConcatenator_4
    DROP_EMPTY_PARTS = No
    LIST_ATTR = eov{}
    SEP = "; "
    VAL_ATTR = eov
    -> AttributeCreator_23
AttributeCreator_23
    ATTR_TABLE:
      SET_TO _order (varchar(200)) = 3
      SET_TO _debug_crosswalk (varchar(200)) = yes
    -> Sorter

Bookmark: Managr topics and keywords
Note: eov/ecv to topics
LOOKUP_TABLES_READER_NG_2
    CSV_ENCODING = utf-8
    CSV_PATH = $(IN_CSV_LOOKUP_TABLES_DIR)
    FEATURE_TYPE = eov_ecv_crosswalk
    PT = $(P-T_ABBR)
    -> AttributeExposer_15
AttributeExposer_15
    ATTR_TABLE = eov_ecv,,topics,
    -> AttributeCreator_5
AttributeCreator_5
    ATTR_TABLE:
      SET_TO _order (varchar(200)) = 1
      SET_TO _debug_crosswalk (varchar(200)) = yes
      SET_TO ogsl_path (varchar(200)) = @Value(topics)
    -> Sorter
Note: keywords to topics
LOOKUP_TABLES_READER_NG_3
    CSV_ENCODING = utf-8
    CSV_PATH = $(IN_CSV_LOOKUP_TABLES_DIR)
    FEATURE_TYPE = keywords_crosswalk
    PT = $(P-T_ABBR)
    -> AttributeExposer_16
AttributeExposer_16
    ATTR_TABLE = keywords_en,,topics,
    -> AttributeCreator_24
AttributeCreator_24
    ATTR_TABLE:
      SET_TO _order (varchar(200)) = 2
      SET_TO _debug_crosswalk (varchar(200)) = yes
      SET_TO ogsl_path (varchar(200)) = @Value(topics)
      SET_TO keyword (varchar(200)) = @Value(keywords_en)
    -> Sorter
AttributeCreator_25
    ATTR_TABLE = SET_TO _order (varchar(200)) = 2
    -> Sorter_3
Sorter_3
    SORT_PARM = _order NUMERIC ASCENDING
    SORTED -> PythonCaller_12
PythonCaller_12
    NEW_ATTRIBUTES = Keywords (EN) buffer Keywords (FR) buffer
    PYTHONSOURCE:
      # -*- coding: utf-8 -*-
      import fme, fmeobjects
      import unicodedata, html, re

      # -------------------------------------------------------------------
      # Shared state
      # -------------------------------------------------------------------
      KW_RULES = {}   # eov/ecv token -> {add_en, add_fr, rm_en}

      # -------------------------------------------------------------------
      # Normalization helpers
      # -------------------------------------------------------------------
      def fold(s):
          if not isinstance(s, str):
              return ""
          s = html.unescape(s)
          s = unicodedata.normalize("NFKD", s)
          s = "".join(c for c in s if not unicodedata.combining(c))
          return s.casefold().strip()

      def split_semis(s):
          return [p.strip() for p in str(s or "").split(";") if p.strip()]

      def join_semis(items):
          return "; ".join(items)

      # -------------------------------------------------------------------
      # FeatureProcessor
      # -------------------------------------------------------------------
      class FeatureProcessor(object):

          def input(self, feature):

              try:
                  order = int(feature.getAttribute("_order"))
              except:
                  self.pyoutput(feature)
                  return

              # -----------------------------------------------------------
              # ORDER 1 — LOAD KEYWORD RULES
              # -----------------------------------------------------------
              if order == 1:
                  eov_ecv = fold(feature.getAttribute("eov_ecv"))

                  if not eov_ecv:
                      return

                  add_en = split_semis(feature.getAttribute("keywords_en"))
                  add_fr = split_semis(feature.getAttribute("keywords_fr"))
                  rm_en  = split_semis(feature.getAttribute("keywords_en_remove"))

                  rule = KW_RULES.setdefault(
                      eov_ecv,
                      {"add_en": set(), "add_fr": set(), "rm_en": set()}
                  )

                  rule["add_en"].update(add_en)
                  rule["add_fr"].update(add_fr)
                  rule["rm_en"].update(rm_en)

                  return

              # -----------------------------------------------------------
              # ORDER 2 — APPLY RULES TO METADATA
              # -----------------------------------------------------------
              if order == 2:

                  # --- parse drivers ---
                  eov = split_semis(feature.getAttribute("eov"))
                  ecv = split_semis(feature.getAttribute("ecv"))
                  drivers = [fold(x) for x in (eov + ecv) if x]

                  # --- parse keywords ---
                  kw_en = split_semis(feature.getAttribute("Keywords (EN)"))
                  kw_fr = split_semis(feature.getAttribute("Keywords (FR)"))

                  kw_en_norm = {fold(k): k for k in kw_en}
                  kw_fr_norm = {fold(k): k for k in kw_fr}

                  # --- apply rules ---
                  for d in drivers:
                      rule = KW_RULES.get(d)
                      if not rule:
                          continue

                      # REMOVE EN keywords
                      for r in rule["rm_en"]:
                          kw_en_norm.pop(fold(r), None)

                      # ADD EN keywords
                      for a in rule["add_en"]:
                          kw_en_norm.setdefault(fold(a), a)

                      # ADD FR keywords
                      for a in rule["add_fr"]:
                          kw_fr_norm.setdefault(fold(a), a)

                  # --- write back ---
                  feature.setAttribute(
                      "Keywords (EN)",
                      join_semis(kw_en_norm.values())
                  )
                  feature.setAttribute(
                      "Keywords (FR)",
                      join_semis(kw_fr_norm.values())
                  )

                  self.pyoutput(feature)
                  return

              # passthrough
              self.pyoutput(feature)

          def close(self):
              pass
    PYTHONSYMBOL = FeatureProcessor
    -> AttributeCreator

Bookmark: add topics from eov/ecv + keywords
Sorter
    SORT_PARM = _order NUMERIC ASCENDING
    SORTED -> PythonCaller_6
PythonCaller_6
    NEW_ATTRIBUTES = cx_topics_leaves buffer
    PYTHONSOURCE:
      # -*- coding: utf-8 -*-
      """
      Unified OGSL Crosswalk PythonCaller – EXACT MATCH (+ OCEANS ALWAYS)

      Orders:
        _order = 1 : ingest EOV / ECV crosswalk rows
        _order = 2 : ingest Keyword crosswalk rows
        _order = 3 : apply crosswalk to metadata (EOV + ECV + Keywords)

      RULES:
        • Match keywords exactly as written (case-insensitive, trimmed)
        • Map ALL EOV, ECV and Keywords
        • Remove a topic ONLY if one of its children exists
        • Oceans is ALWAYS included
        • No normalization beyond strip() + casefold()

      Outputs:
        cx_tokens           : lookup tokens used
        cx_topics_paths     : surviving OGSL paths (<pipe> separated)
        cx_topics_leaves    : leaves derived from surviving paths
        cx_leaves_count     : number of leaves
      """

      import fme, fmeobjects
      import html

      # -------------------------------------------------------------------
      # Constants
      # -------------------------------------------------------------------
      OCEANS_PATH = "Physical Environment; Marine Geology; Oceans"
      OCEANS_LEAF = "Oceans"

      # -------------------------------------------------------------------
      # Shared state
      # -------------------------------------------------------------------
      CWALK = {
          "map": {},       # lookup_key -> set(OGSL canonical paths)
          "loaded": False
      }

      COUNTS = {
          "rows_ingested": 0,
          "keys_total": 0,
          "keys_unique": 0,
          "skipped": 0
      }

      # -------------------------------------------------------------------
      # Debug helper
      # -------------------------------------------------------------------
      def _is_debug(feature):
          return str(feature.getAttribute("_debug_crosswalk") or "").lower() in (
              "1", "true", "yes"
          )

      # -------------------------------------------------------------------
      # Exact key logic (CASEFOLD + TRIM ONLY)
      # -------------------------------------------------------------------
      def key_exact(s):
          if not isinstance(s, str):
              return ""
          return s.strip().casefold()

      def split_semis(s):
          if not isinstance(s, str):
              return []
          s = html.unescape(s)
          return [p.strip() for p in s.split(";") if p.strip()]

      def split_tokens(s):
          return [key_exact(p) for p in split_semis(s)]

      def _to_semicolon_string(v):
          if v is None:
              return ""
          if isinstance(v, (list, tuple)):
              out = []
              for x in v:
                  out.extend(split_semis(str(x)))
              return "; ".join(out)
          return str(v)

      # -------------------------------------------------------------------
      # OGSL path utilities
      # -------------------------------------------------------------------
      def normalize_path(p):
          if not isinstance(p, str):
              return ""
          return ";".join(x.strip() for x in p.split(";") if x.strip())

      def split_path(p):
          return normalize_path(p).split(";") if p else []

      def is_parent(parent, child):
          p = split_path(parent)
          c = split_path(child)
          return len(p) < len(c) and c[:len(p)] == p

      def keep_only_non_parents(paths):
          """
          Remove a path ONLY if a true child exists.
          """
          normed = []
          for p in paths:
              p = normalize_path(p)
              if p and p not in normed:
                  normed.append(p)

          dropped = set()
          for a in normed:
              for b in normed:
                  if is_parent(a, b):
                      dropped.add(a)
                      break

          return [p for p in normed if p not in dropped]

      def paths_to_leaves(paths):
          leaves = []
          seen = set()

          for p in paths:
              leaf = split_path(p)[-1]
              if leaf not in seen:
                  leaves.append(leaf)
                  seen.add(leaf)

          # ALWAYS put Oceans first
          if OCEANS_LEAF in seen:
              leaves = [OCEANS_LEAF] + [l for l in leaves if l != OCEANS_LEAF]
          else:
              leaves = [OCEANS_LEAF] + leaves

          return leaves

      # -------------------------------------------------------------------
      # OGSL path reader (FME-safe)
      # -------------------------------------------------------------------
      def read_ogsl_paths(feature):
          s = feature.getAttribute("ogsl_paths")
          if isinstance(s, str) and s.strip():
              if " <pipe> " in s:
                  return [normalize_path(p) for p in s.split(" <pipe> ") if p.strip()]
              if "\n" in s:
                  return [normalize_path(p) for p in s.splitlines() if p.strip()]
              return [normalize_path(s)]

          s = feature.getAttribute("ogsl_path")
          if isinstance(s, str) and s.strip():
              return [normalize_path(s)]

          return []

      def pick_exact(feature, name, default=""):
          try:
              v = feature.getAttribute(name)
              return _to_semicolon_string(v) if v else default
          except:
              return default

      # -------------------------------------------------------------------
      # Processor
      # -------------------------------------------------------------------
      class FeatureProcessor(object):

          def input(self, feature):

              try:
                  order = int(feature.getAttribute("_order"))
              except:
                  COUNTS["skipped"] += 1
                  self.pyoutput(feature)
                  return

              # -----------------------------------------------------------
              # ORDER 1 — EOV / ECV CROSSWALK INGESTION
              # -----------------------------------------------------------
              if order == 1:
                  keys = split_tokens(feature.getAttribute("eov_ecv"))
                  paths = read_ogsl_paths(feature)

                  if not keys or not paths:
                      COUNTS["skipped"] += 1
                      return

                  for k in keys:
                      CWALK["map"].setdefault(k, set()).update(paths)

                  COUNTS["rows_ingested"] += 1
                  COUNTS["keys_total"] += len(keys)
                  COUNTS["keys_unique"] = len(CWALK["map"])
                  CWALK["loaded"] = True
                  return

              # -----------------------------------------------------------
              # ORDER 2 — KEYWORD CROSSWALK INGESTION
              # -----------------------------------------------------------
              if order == 2:
                  keys = split_tokens(feature.getAttribute("keyword"))
                  paths = read_ogsl_paths(feature)

                  if not keys or not paths:
                      COUNTS["skipped"] += 1
                      return

                  for k in keys:
                      CWALK["map"].setdefault(k, set()).update(paths)

                  COUNTS["rows_ingested"] += 1
                  COUNTS["keys_total"] += len(keys)
                  COUNTS["keys_unique"] = len(CWALK["map"])
                  CWALK["loaded"] = True
                  return

              # -----------------------------------------------------------
              # ORDER 3 — METADATA RESOLUTION
              # -----------------------------------------------------------
              if order == 3:

                  eov = pick_exact(feature, "eov")
                  ecv = pick_exact(feature, "ecv")
                  kwd = pick_exact(feature, "Keywords (EN)")

                  tokens = (
                      split_tokens(eov) +
                      split_tokens(ecv) +
                      split_tokens(kwd)
                  )
                  tokens = [t for t in tokens if t and t != "other"]

                  found_paths = []

                  for t in tokens:
                      found_paths.extend(CWALK["map"].get(t, []))

                  # ALWAYS include Oceans path
                  found_paths.append(OCEANS_PATH)

                  surviving = keep_only_non_parents(found_paths)
                  leaves = paths_to_leaves(surviving)

                  feature.setAttribute("cx_tokens", "; ".join(sorted(set(tokens))))
                  feature.setAttribute("cx_topics_paths", " <pipe> ".join(surviving))
                  feature.setAttribute("cx_topics_leaves", "; ".join(leaves))
                  feature.setAttribute("cx_leaves_count", len(leaves))

                  if _is_debug(feature):
                      feature.setAttribute(
                          "_cx_matched_tokens",
                          "; ".join(t for t in tokens if t in CWALK["map"])
                      )

                  self.pyoutput(feature)
                  return

              # -----------------------------------------------------------
              # PASS-THROUGH
              # -----------------------------------------------------------
              COUNTS["skipped"] += 1
              self.pyoutput(feature)

          def close(self):
              f = fmeobjects.FMEFeature()
              for k, v in COUNTS.items():
                  f.setAttribute(f"_cx_{k}", v)
              f.setAttribute("_cx_keys_unique", len(CWALK["map"]))
              self.pyoutput(f)
    PYTHONSYMBOL = FeatureProcessor
    -> Tester_4
Tester_4
    BOOL_OP = OR
    TEST_CLAUSE = TEST @Value(_order) = 3
    TEST_MODE = TEST
    PASSED -> AttributeCreator_19
AttributeCreator_19
    ATTR_TABLE = SET_TO Subject Topic (varchar(200)) = @Value(cx_topics_leaves)
    -> AttributeRemover
AttributeRemover
    REMOVE_ATTRS = _debug_crosswalk,_order,cx_topics_leaves
    -> AttributeCreator_25

Bookmark: Add /remove keywords from ecv and eov lists
LOOKUP_TABLES_READER_NG_4
    CSV_ENCODING = windows-1252
    CSV_PATH = $(IN_CSV_LOOKUP_TABLES_DIR)
    FEATURE_TYPE = eov_ecv_crosswalk_keywords
    PT = $(P-T_ABBR)
    -> AttributeExposer_12
AttributeExposer_12
    ATTR_TABLE = eov_ecv,,keywords_en,,keywords_fr,,keywords_en_remove,
    -> AttributeCreator_26
AttributeCreator_26
    ATTR_TABLE = SET_TO _order (varchar(200)) = 1
    -> Sorter_3

Bookmark: Manage Dates
Note: Date.LastUpdate, Date.Start, Date.End
AttributeCreator
    ATTR_TABLE:
      SET_TO Date.LastUpdate (varchar(200)) = @Substring(@Value(metadata_modified), 0, 23)Z
      SET_TO Date.Start (varchar(200)) = FME_CONDITIONAL:DEFAULT_VALUE'@Value(temporal-extent{0}.begin)'BOOL_OP;OR;COMPOSITE_TEST;1 OR 2 OR 3;TEST temporal-extent{0}.begin NOT_ATTRIBUTE_HAS_A_VALUE _FME_BLANK_STRING_;CASE_INSENSITIVE_TEST @Value(temporal-extent{0}.begin) CONTAINS null;TEST @Value(temporal-extent{0}.begin) = 001-01-01'FME_NULL_VALUE'FME_NUM_CONDITIONS2___
      SET_TO Date.End (varchar(200)) = FME_CONDITIONAL:DEFAULT_VALUE'@Value(temporal-extent{0}.end)'BOOL_OP;OR;COMPOSITE_TEST;1 OR 2 OR 3;TEST temporal-extent{0}.end NOT_ATTRIBUTE_HAS_A_VALUE _FME_BLANK_STRING_;CASE_INSENSITIVE_TEST @Value(temporal-extent{0}.end) CONTAINS null;TEST @Value(temporal-extent{0}.end) = 001-01-01'FME_NULL_VALUE'FME_NUM_CONDITIONS2___
    -> PythonCaller_2
Note: Date.Published
PythonCaller_2
    NEW_ATTRIBUTES = Date.Published buffer
    PYTHONSOURCE:
      def processFeature(feature):
          # Default fallback
          published = feature.getAttribute("metadata_created")

          # Get list length
          count = feature.getAttribute("metadata-reference-date{}")

          if count is None:
              # No list at all → use fallback
              feature.setAttribute("Date.Published", published)
              return

          # Loop through list elements
          for i in range(int(count)):
              type_attr = f"metadata-reference-date{{{i}}}.type"
              value_attr = f"metadata-reference-date{{{i}}}.value"

              ref_type = feature.getAttribute(type_attr)
              ref_value = feature.getAttribute(value_attr)

              if ref_type == "publication" and ref_value not in (None, ""):
                  published = ref_value
                  break

          # Set final output
          feature.setAttribute("Date.Published", published)
    PYTHONSYMBOL = processFeature
    -> DateTimeConverter
DateTimeConverter
    DATETIME_ATTR = Date.Published
    OUT_FORMAT = %Y-%m-%d
    PASSTHROUGH = YES
    REPAIR_INPUT = YES
    -> PythonCaller_13

Bookmark: Coverage.Geometry
PythonCaller_13
    NEW_ATTRIBUTES = Coverage.Geometry buffer Coverage.Geometry.SpatialValid buffer Coverage.Geometry.SpatialUsed buffer Coverage.Geometry.Source buffer
    PYTHONSOURCE:
      import fme
      import fmeobjects

      def processFeature(feature):

          # =====================================================
          # Helpers
          # =====================================================

          def to_float(val):
              try:
                  return float(val)
              except:
                  return None
          def fmt(v):
              return f"{v:.6f}".rstrip("0").rstrip(".")

          def build_polygon(coords):
              return (
                  "POLYGON (("
                  + ", ".join(f"{fmt(x)} {fmt(y)}" for x, y in coords)
                  + "))"
              )


          def build_point_polygon(x, y, offset=0.05):
              coords = [
                  (x, y),
                  (x - offset, y + offset),
                  (x + offset, y + offset),
                  (x, y)
              ]
              return build_polygon(coords)

          def remove_consecutive_duplicates(coords):

              cleaned = []

              for p in coords:
                  if not cleaned or p != cleaned[-1]:
                      cleaned.append(p)

              return cleaned

          def unique_points(coords):

              seen = set()
              unique = []

              for p in coords:
                  if p not in seen:
                      unique.append(p)
                      seen.add(p)

              return unique

          def is_valid_polygon(coords):

              if len(coords) < 4:
                  return False

              unique = set(coords)

              is_closed = coords[0] == coords[-1]

              return len(unique) >= 3 and is_closed

          def has_non_consecutive_duplicates(coords):

              seen = set()

              for i, p in enumerate(coords):

                  # Ignore closing coordinate
                  if i == len(coords) - 1 and p == coords[0]:
                      continue

                  if p in seen:
                      returnen.add(p)

              return False
          # =====================================================
          # Self-intersection detection
          # =====================================================

          def ccw(A, B, C):

              return (
                  (C[1] - A[1]) * (B[0] - A[0]) >
                  (B[1] - A[1]) * (C[0] - A[0])
              )

          def segments_intersect(A, B, C, D):

              return (
                  ccw(A, C, D) != ccw(B, C, D)
                  and
                  ccw(A, B, C) != ccw(A, B, D)
              )

          def has_self_intersection(coords):

              n = len(coords)

              for i in range(n - 1):

                  A = coords[i]
                  B = coords[i + 1]

                  for j in range(i + 1, n - 1):

                      C = coords[j]
                      D = coords[j + 1]

                      # Skip adjacent segments
                      if abs(i - j) <= 1:
                          continue

                      # Skip first/last shared closure edge
                      if i == 0 and j == n - 2:
                          continue

                      if segments_intersect(A, B, C, D):
                          return True

              return False

          # =====================================================
          # Containers
          # =====================================================

          geometries = []

          geom_type = feature.getAttribute("spatial.type")

          spatial_used = False
          spatial_valid = False

          all_spatial_points = []

          # =====================================================
          # 1. SPATIAL POLYGONS
          # =====================================================

          if geom_type == "Polygon":

              ring_index = 0

              while True:

                  coords = []

                  i = 0

                  while True:

                      x = to_float(
                          feature.getAttribute(
                              f"spatial.coordinates{{{ring_index}}}.array{{{i}}}.array{{0}}"
                          )
                      )

                      y = to_float(
                          feature.getAttribute(
                              f"spatial.coordinates{{{ring_index}}}.array{{{i}}}.array{{1}}"
                          )
                      )

                      if x is None or y is None:
                          break

                      point = (x, y)

                      coords.append(point)
                      all_spatial_points.append(point)

                      i += 1

                  if not coords:
                      break

                  spatial_used = True

                  coords = remove_consecutive_duplicates(coords)

                  unique_coords = unique_points(coords)

                  # Must have at least 3 unique points
                  if len(unique_coords) >= 3:

                      polygon_valid = (
                          is_valid_polygon(coords)
                          and not has_non_consecutive_duplicates(coords)
                          and not has_self_intersection(coords)
                      )

                      if polygon_valid:

                          geometries.append(
                              build_polygon(coords)
                          )

                          spatial_valid = True

                          feature.setAttribute(
                              "Coverage.Geometry.Source",
                              "SPATIAL_POLYGON"
                          )

                  ring_index += 1

          # =====================================================
          # 2. SPATIAL POINTS
          # =====================================================

          elif geom_type == "Point":

              spatial_used = True

              i = 0

              while True:

                  x = to_float(
                      feature.getAttribute(
                          f"spatial.coordinates.array{{{i}}}.array{{0}}"
                      )
                  )

                  y = to_float(
                      feature.getAttribute(
                          f"spatial.coordinates.array{{{i}}}.array{{1}}"
                      )
                  )

                  if x is None or y is None:
                      break

                  all_spatial_points.append((x, y))

                  i += 1

          # =====================================================
          # 3. FALLBACK CHAIN
          # =====================================================

          if not geometries:

              west = to_float(feature.getAttribute("bbox-west-long"))
              east = to_float(feature.getAttribute("bbox-east-long"))
              south = to_float(feature.getAttribute("bbox-south-lat"))
              north = to_float(feature.getAttribute("bbox-north-lat"))

              bbox_coords = None
              bbox_valid = False

              # -------------------------------------------------
              # Try bbox polygon
              # -------------------------------------------------

              if None not in (west, east, south, north):

                  bbox_coords = [
                      (west, south),
                      (east, south),
                      (east, north),
                      (west, north),
                      (west, south)
                  ]

                  bbox_unique = set(bbox_coords[:-1])

                  if (
                      is_valid_polygon(bbox_coords)
                      and len(bbox_unique) >= 3
                      and not has_self_intersection(bbox_coords)
                  ):

                      geometries = [
                          build_polygon(bbox_coords)
                      ]

                      bbox_valid = True

                      feature.setAttribute(
                          "Coverage.Geometry.Source",
                          "BBOX"
                      )

              # -------------------------------------------------
              # No valid bbox polygon
              # -------------------------------------------------

              if not bbox_valid:

                  # First preference:
                  # use spatial points if spatial geometry existed
                  spatial_pts = unique_points(all_spatial_points)

                  if len(spatial_pts) in (1, 2):

                      geometries = [
                          build_point_polygon(x, y)
                          for (x, y) in spatial_pts
                      ]

                      feature.setAttribute(
                          "Coverage.Geometry.Source",
                          "SPATIAL_POINT_POLYGON_FALLBACK"
                      )

                  # Second preference:
                  # use bbox points if bbox exists but cannot
                  # form a valid polygon

                  elif bbox_coords:

                      bbox_pts = unique_points(bbox_coords[:-1])

                      if len(bbox_pts) in (1, 2):

                          geometries = [
                              build_point_polygon(x, y)
                              for (x, y) in bbox_pts
                          ]

                          feature.setAttribute(
                              "Coverage.Geometry.Source",
                              "BBOX_POINT_POLYGON_FALLBACK"
                          )

          # =====================================================
          # 4. Output
          # =====================================================

          if geometries:

              feature.setAttribute(
                  "Coverage.Geometry",
                  "; ".join(geometries)
              )

          else:

              feature.setAttribute(
                  "Coverage.Geometry",
                  None
              )

          # =====================================================
          # 5. QA flags
          # =====================================================

          feature.setAttribute(
              "Coverage.Geometry.SpatialUsed",
              "YES" if spatial_used else "NO"
          )

          feature.setAttribute(
              "Coverage.Geometry.SpatialValid",
              "YES" if spatial_valid else "NO"
          )
    PYTHONSYMBOL = processFeature
    -> PythonCaller

Bookmark: Notes/disclaimer
PythonCaller_5
    NEW_ATTRIBUTES = disclaimer buffer
    PYTHONSOURCE:
      import fme
      import fmeobjects

      def processFeature(feature):

          # Get both lists
          keys = feature.getAttribute('extras{}.key')
          values = feature.getAttribute('extras{}.value')

          # If no lists exist
          if not keys or not values:
              feature.setAttribute("disclaimer", '')
              return

          disclaimer = ''

          # Loop through keys with index
          for i, key in enumerate(keys):
              if key == "licence":
                  value = values[i]   # matching value at same index
                  print(value)
                  if value not in (None, ""):
                      disclaimer = value
                  break

          feature.setAttribute("disclaimer", disclaimer)
    PYTHONSYMBOL = processFeature
    -> TestFilter
TestFilter
    DEFAULT_VALUE = no disclaimer
    PASSED_TEST_GROUP_OUTPUT = FIRST
    TEST_LIST:
      "BOOL_OP,AND,COMPOSITE_TEST,""""""1 AND 2"""""",TEST_CLAUSE,TEST disclaimer ATTRIBUTE_HAS_A_VALUE ""
      TEST @Value(metadata-language) = en",disclaimer en,"BOOL_OP,AND,COMPOSITE_TEST,""""""1 AND 2"""""",TEST_CLAUSE,TEST disclaimer ATTRIBUTE_HAS_A_VALUE ""
      TEST @Value(metadata-language) = fr",disclaimer fr
    disclaimer en -> AWS_TRANSLATE
    disclaimer fr -> AWS_TRANSLATE_2
    no disclaimer -> AttributeCreator_10
AWS_TRANSLATE
    ACTIVATE_TRANSLATION = $(ACTIVATE_TRANSLATION)
    ATTR_2_TRANSLATE = disclaimer
    MODE = English-->French
    -> AttributeExposer_5
    TRANSLATION_PROBLEM -> AWS_translate_errors (writer XLSXW_1)
AttributeExposer_5
    ATTR_TABLE = disclaimer,,disclaimer_fr,
    -> AttributeCreator_4
AttributeCreator_4
    ATTR_TABLE:
      SET_TO Note Total (varchar(200)) = 1
      SET_TO Note.Type[1] (varchar(200)) = DISCLAIMER
      SET_TO Note.Title (EN)[1] (varchar(200)) = Saint Lawrence Global Observatory - Disclaimer
      SET_TO Note.Title (FR)[1] (varchar(200)) = Observatoire Global du Saint-Laurent - Avertissement
      SET_TO Note.Desc (EN)[1] (varchar(200)) = @Value(disclaimer)
      SET_TO Note.Desc (FR)[1] (varchar(200)) = @Value(disclaimer_fr)
    -> Tester_3
AWS_TRANSLATE_2
    ACTIVATE_TRANSLATION = $(ACTIVATE_TRANSLATION)
    ATTR_2_TRANSLATE = disclaimer
    MODE = French-->English
    -> AttributeExposer_7
    TRANSLATION_PROBLEM -> AWS_translate_errors (writer XLSXW_1)
AttributeExposer_7
    ATTR_TABLE = disclaimer,,disclaimer_en,
    -> AttributeCreator_9
AttributeCreator_9
    ATTR_TABLE:
      SET_TO Note Total (varchar(200)) = 1
      SET_TO Note.Type[1] (varchar(200)) = DISCLAIMER
      SET_TO Note.Title (EN)[1] (varchar(200)) = Saint Lawrence Global Observatory - Disclaimer
      SET_TO Note.Title (FR)[1] (varchar(200)) = Observatoire Global du Saint-Laurent - Avertissement
      SET_TO Note.Desc (EN)[1] (varchar(200)) = @Value(disclaimer_en)
      SET_TO Note.Desc (FR)[1] (varchar(200)) = @Value(disclaimer)
    -> Tester_3
AttributeCreator_10
    ATTR_TABLE:
      SET_TO Note Total (varchar(200)) = 0
      SET_TO Note.Type[1] (varchar(200))
      SET_TO Note.Title (EN)[1] (varchar(200))
      SET_TO Note.Title (FR)[1] (varchar(200))
      SET_TO Note.Desc (EN)[1] (varchar(200))
      SET_TO Note.Desc (FR)[1] (varchar(200))
    -> Tester_3

Bookmark: Content Category, PublishedFor
Tester_3
    BOOL_OP = OR
    TEST_CLAUSE = CASE_INSENSITIVE_TEST @Value(DOI) CONTAINS 10.
    TEST_MODE = CASE_INSENSITIVE_TEST
    PASSED -> AttributeCreator_2
    FAILED -> AttributeCreator_3
AttributeCreator_2
    ATTR_TABLE:
      SET_TO Content Category (varchar(200)) = Science
      SET_TO PublishedFor (varchar(200)) = Author
      SET_TO Identifier.Artifact (DOI) (varchar(200)) = @Value(DOI)
    -> AttributeCreator_16
AttributeCreator_3
    ATTR_TABLE:
      SET_TO Content Category (varchar(200)) = Dataset
      SET_TO PublishedFor (varchar(200)) = Partner
    -> AttributeCreator_16

Bookmark: UpdateFrequency
AttributeExposer_13
    ATTR_TABLE = UpdateFrequency,
    -> METADATA_VALUE_MAPPER_NG [DATA_INPUT]
METADATA_VALUE_MAPPER_NG
    ATT_TO_MAP = UpdateFrequency
    CODE_REFRESH = YES
    ENGLISH_REFRESH = YES
    ERROR_NOT_MAPPED = YES
    FEATURE_TYPE = UpdateFrequency_OGSL
    FRENCH_REFRESH = YES
    IN_CSV_LOOKUP_TABLES_DIR = $(IN_CSV_LOOKUP_TABLES_DIR)
    P-T_ABBR = $(P-T_ABBR)
    -> METADATA_VALUE_MAPPER_ERROR_MANAGER
METADATA_VALUE_MAPPER_ERROR_MANAGER
    ERROR_OUTPUT -> UNKNOWN_UpdateFrequency (writer XLSXW_1)
    DATA_OUTPUT -> AttributeExposer_14
AttributeExposer_14
    ATTR_TABLE = UpdateFrequency,,UpdateFrequency_code,
    -> AttributeCreator_20
AttributeCreator_20
    ATTR_TABLE = SET_TO UpdateFrequency (varchar(200)) = @Value(UpdateFrequency_code)
    -> AttributeExposer_6
UNKNOWN_UpdateFrequency (writer XLSXW_1)
    attributes: error string(200), id string(200)

Bookmark: manage resources
AttributeExposer_6
    ATTR_TABLE = resources{}.url,,resources{}.format,,resources{}.name_translated.en,,resources{}.name_translated.fr,,id,,metadata-language,,"Identifier.Artifact (DOI)",
    -> AttributeKeeper
    -> FeatureMerger_4 [REQUESTOR]
AttributeKeeper
    CREATE_BULK_MODE_FEATURES = NO
    KEEP_ATTRS = id
    KEEP_LIST = resources{}.format resources{}.name_translated.en resources{}.name_translated.fr resources{}.url
    -> ListExploder
ListExploder
    ATTR_CONFLICT_RES_LOOKUP = INCOMING_IF_CONFLICT
    INDEX_ATTR = _element_index
    LIST_ATTR = resources{}
    ATTR_ACCUM_MODE = Merge List Attributes
    ATTR_CONFLICT_RES = Use List Attribute Values
    ELEMENTS -> AttributeCreator_15
AttributeCreator_15
    ATTR_TABLE = SET_TO name2 (varchar(200)) = @Value(url)
    -> StringReplacer_3
StringReplacer_3
    CASE = NO
    FIND_TEXT = ^.*/
    NO_MATCH = _FME_NO_OP_
    REGEXP = YES
    SRC_ATTRS = name2
    -> AttributeCreator_17
AttributeCreator_17
    ATTR_TABLE:
      SET_TO name_translated.en (varchar(200)) = FME_CONDITIONAL:DEFAULT_VALUE'_FME_NO_OP_'BOOL_OP;OR;COMPOSITE_TEST;1 OR 2 OR 3 OR 4;TEST name_translated.en NOT_ATTRIBUTE_HAS_A_VALUE _FME_BLANK_STRING_;TEST name_translated.en ATTRIBUTE_VALUE_NULL _FME_BLANK_STRING_;TEST name_translated.en ATTRIBUTE_IS_EMPTY _FME_BLANK_STRING_;TEST name_translated.en ATTRIBUTE_IS_MISSING _FME_BLANK_STRING_'@Value(name2)'FME_NUM_CONDITIONS2___
      SET_TO name_translated.fr (varchar(200)) = FME_CONDITIONAL:DEFAULT_VALUE'_FME_NO_OP_'BOOL_OP;OR;COMPOSITE_TEST;1 OR 2 OR 3 OR 4;TEST name_translated.fr NOT_ATTRIBUTE_HAS_A_VALUE _FME_BLANK_STRING_;TEST name_translated.fr ATTRIBUTE_VALUE_NULL _FME_BLANK_STRING_;TEST name_translated.fr ATTRIBUTE_IS_EMPTY _FME_BLANK_STRING_;TEST name_translated.fr ATTRIBUTE_IS_MISSING _FME_BLANK_STRING_'@Value(name2)'FME_NUM_CONDITIONS2___
      SET_TO format (varchar(200)) = FME_CONDITIONAL:DEFAULT_VALUE'_FME_NO_OP_'BOOL_OP;OR;COMPOSITE_TEST;1;TEST @Value(format) = JPEG'JPG'FME_NUM_CONDITIONS2___
    -> AttributeCreator_18
AttributeCreator_18
    ATTR_TABLE:
      SET_TO name_translated.en (varchar(200)) = FME_CONDITIONAL:DEFAULT_VALUE'_FME_NO_OP_'BOOL_OP;OR;COMPOSITE_TEST;1 OR 2 OR 3 OR 4;TEST name_translated.en NOT_ATTRIBUTE_HAS_A_VALUE _FME_BLANK_STRING_;TEST name_translated.en ATTRIBUTE_VALUE_NULL _FME_BLANK_STRING_;TEST name_translated.en ATTRIBUTE_IS_EMPTY _FME_BLANK_STRING_;TEST name_translated.en ATTRIBUTE_IS_MISSING _FME_BLANK_STRING_'@Value(url)'FME_NUM_CONDITIONS2___
      SET_TO name_translated.fr (varchar(200)) = FME_CONDITIONAL:DEFAULT_VALUE'_FME_NO_OP_'BOOL_OP;OR;COMPOSITE_TEST;1 OR 2 OR 3 OR 4;TEST name_translated.fr NOT_ATTRIBUTE_HAS_A_VALUE _FME_BLANK_STRING_;TEST name_translated.fr ATTRIBUTE_VALUE_NULL _FME_BLANK_STRING_;TEST name_translated.fr ATTRIBUTE_IS_EMPTY _FME_BLANK_STRING_;TEST name_translated.fr ATTRIBUTE_IS_MISSING _FME_BLANK_STRING_'@Value(url)'FME_NUM_CONDITIONS2___
    -> StatisticsCalculator
StatisticsCalculator
    ATTR_ACCUM_MODE = None
    CALCULATION_MODE = NUMERIC
    FEAT_STATS = _element_index,NUMERIC_MODE,,MAX,COUNT,SUM,,,,,,,,,
    GROUP_BY = id
    SUMMARY -> FeatureMerger_4 [SUPPLIER]
    COMPLETE -> ListBuilder
FeatureMerger_4
    ATTR_ACCUM_MODE = Merge Supplier
    ATTR_CONFLICT_RES_LOOKUP = REQUESTOR_IF_CONFLICT
    IGNORE_NULLS = No
    JOIN_KEYS = @Value(id) @Value(id) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeRemover_2
AttributeRemover_2
    LIST_ATTRS = resources{}.format resources{}.name_translated.en resources{}.name_translated.fr resources{}.url
    -> FeatureMerger_8 [REQUESTOR]
ListBuilder
    GROUP_BY = id
    LIST_ATTRS_TO_INCLUDE = format name_translated.en name_translated.fr url
    LIST_NAME = resources
    -> FeatureMerger_8 [SUPPLIER]
FeatureMerger_8
    ATTR_ACCUM_MODE = Merge Supplier
    ATTR_CONFLICT_RES_LOOKUP = REQUESTOR_IF_CONFLICT
    IGNORE_NULLS = No
    JOIN_KEYS = @Value(id) @Value(id) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeCreator_8
AttributeCreator_8
    ATTR_TABLE = SET_TO doi (varchar(200)) = FME_CONDITIONAL:DEFAULT_VALUE'@Value(Identifier.Artifact (DOI))'BOOL_OP;OR;COMPOSITE_TEST;1;TEST Identifier.Artifact (DOI) NOT_ATTRIBUTE_HAS_A_VALUE _FME_BLANK_STRING_'FME_NULL_VALUE'FME_NUM_CONDITIONS2___
    -> PythonCaller_8
Note: Add new resource to this pythoncaller
PythonCaller_8
    NEW_ATTRIBUTES = new_format buffer
    PYTHONSOURCE:
      import fme
      import fmeobjects
      import re

      # Template Function interface:
      # When using this function, make sure its name is set as the value of
      # the 'Class or Function to Process Features' transformer parameter
      def processFeature(feature):
          id = feature.getAttribute('id')
          doi = feature.getAttribute('doi')
          print(doi)
          language_id = feature.getAttribute('metadata-language')
          resource_total = int(feature.getAttribute('_element_index.max'))
          max_index=feature.getAttribute('_element_index.total_count')

          for j in range(max_index):
              url_en = f"{'https://catalogue.ogsl.ca/en/dataset/ca-cioos_'}{id}"
              url_fr = f"{'https://catalogue.ogsl.ca/fr/dataset/ca-cioos_'}{id}"
              feature.setAttribute('Resource{%i}.Format'%(1),'HTML')
              feature.setAttribute('Resource{%i}.Type'%(1),'Website')
              feature.setAttribute('Resource{%i}.ServiceProtocol'%(1),'HTTPS')
              feature.setAttribute('Resource{%i}.URL (EN)'%(1),url_en)
              feature.setAttribute('Resource{%i}.URL (FR)'%(1),url_fr)
              feature.setAttribute('Resource{%i}.Name (EN)'%(1),'Source Material')
              feature.setAttribute('Resource{%i}.Name (FR)'%(1),"Métadonnée Source")
              feature.setAttribute('Resource{%i}.Language'%(1),'eng; fre')

              if doi:
                  feature.setAttribute('Resource Total',max_index+2)
                  k = j+3

                  url_en_doi = f"{'https://doi.org/'}{doi}"
                  url_fr_doi = f"{'https://doi.org/'}{doi}"
                  feature.setAttribute('Resource{%i}.Format'%(2),'HTML')
                  feature.setAttribute('Resource{%i}.Type'%(2),'Website')
                  feature.setAttribute('Resource{%i}.ServiceProtocol'%(2),'HTTPS')
                  feature.setAttribute('Resource{%i}.URL (EN)'%(2),url_en_doi)
                  feature.setAttribute('Resource{%i}.URL (FR)'%(2),url_fr_doi)
                  feature.setAttribute('Resource{%i}.Name (EN)'%(2),'Publication Web Page')
                  feature.setAttribute('Resource{%i}.Name (FR)'%(2),'Page Web de la publication')
                  feature.setAttribute('Resource{%i}.Language'%(2),'fre')
              else:
                  feature.setAttribute('Resource Total',max_index+1)
                  k = j+2
              url = feature.getAttribute('resources{%i}.url'%(j))
              format = feature.getAttribute('resources{%i}.format'%(j))
              if format not in ('CSV','ERDDAP','HTML','JPG','KMZ','MP4','OBIS','ODS','ODT','PDF','PNG','TIFF','WCS','XLS','XLSX','ZIP'):
                  feature.setAttribute('new_format',format)
              name_en = feature.getAttribute('resources{%i}.name_translated.en'%(j))
              name_fr = feature.getAttribute('resources{%i}.name_translated.fr'%(j))
              ne = (name_en or '').lower()
              nf = (name_fr or '').lower()

              language = language_id
              if format in ('ERDDAP','OBIS'):
                  feature.setAttribute('Resource{%i}.Format'%(k),'Other')
              else:
                  feature.setAttribute('Resource{%i}.Format'%(k),format)
              if url.startswith('https'):
                  feature.setAttribute('Resource{%i}.ServiceProtocol'%(k),'HTTPS')
              else:
                  feature.setAttribute('Resource{%i}.ServiceProtocol'%(k),'HTTP')
              feature.setAttribute('Resource{%i}.URL (EN)'%(k),url)
              feature.setAttribute('Resource{%i}.URL (FR)'%(k),url)
              feature.setAttribute('Resource{%i}.Name (EN)'%(k),name_en)
              feature.setAttribute('Resource{%i}.Name (FR)'%(k),name_fr)

              if 'english' in ne or 'anglais' in nf:
                  feature.setAttribute('Resource{%i}.Language'%(k),'eng')
              elif 'french' in ne or 'francais' in nf or 'français' in nf:
                  feature.setAttribute('Resource{%i}.Language'%(k),'fre')
              elif language == 'en':
                  feature.setAttribute('Resource{%i}.Language'%(k),'eng')
              elif language == 'fr':
                  feature.setAttribute('Resource{%i}.Language'%(k),'fre')

              if format in ('PDF','ODT'):
                  feature.setAttribute('Resource{%i}.Type'%(k),'Report')
              elif format in ('HTML'):
                  feature.setAttribute('Resource{%i}.Type'%(k),'Website')
              elif format in ('WCS'):
                  feature.setAttribute('Resource{%i}.Type'%(k),'Web Service')
              elif format in ('CSV','ODS','XLS','XLSX','ZIP'):
                  feature.setAttribute('Resource{%i}.Type'%(k),'Dataset')
              else:
                  feature.setAttribute('Resource{%i}.Type'%(k),'Supporting Document')

      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> Tester_6
Tester_6
    BOOL_OP = OR
    TEST_CLAUSE = TEST new_format ATTRIBUTE_HAS_A_VALUE ""
    TEST_MODE = TEST
    PASSED -> AttributeKeeper_5
    FAILED -> FeatureMerger_9 [REQUESTOR]
AttributeKeeper_5
    CREATE_BULK_MODE_FEATURES = NO
    KEEP_ATTRS = id,new_format
    -> New_Resource_Format (writer XLSXW_1)
New_Resource_Format (writer XLSXW_1)
    attributes: id string(200), new_format string(20)

Bookmark: Read old geodcat file
Note: Creator_3 : Created
Junction_2
    -> FeatureReader [INITIATOR]
FeatureReader
    ATTR_ACCUM_MODE = Only Use Result
    CLIP_TO_ENVELOPE = NO
    COMBINE_GEOM = Use Result
    CSV2_CASE_SENSITIVE_FIELD_NAMES = Yes
    CSV2_CHUNK_SIZE = 100000
    CSV2_DATA_START_LINE = 2
    CSV2_DELIMITER = ,
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 10000
    CSV2_SCAN_TYPES = Yes
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = $(OUT_old_geodcat_DIR)\Last_SLGO_file.csv
    FORMAT = CSV2
    INITIATOR_FIRST_OUTPUT = default
    INTERACT = NONE
    ORDER_RESULTS = No
    OUTPUT_ADD_SCHEMA_ATTRIBUTES = NO
    OUTPUT_FEATURES_DISPLAY = Schema and Data Features
    <OTHER> -> AttributeExposer_17
AttributeExposer_17
    ATTR_TABLE = Action,,Identifier.Artifact,,"Record Type",,"Contributor System",,"Contributor Org",,"Content Category",,Date.LastUpdate,,RecordKeeper.Organization,,RecordKeeper.System,,RecordKeeper.LastUserToModify,,RecordKeeper.LastSyncTS,,"Resource Total",
    -> Tester_5
Tester_5
    BOOL_OP = OR
    TEST_CLAUSE = CASE_INSENSITIVE_TEST @Value(Action) CONTAINS U
    TEST_MODE = CASE_INSENSITIVE_TEST
    PASSED -> FeatureMerger_11 [REQUESTOR]
FeatureMerger_11
    ATTR_ACCUM_MODE = Merge Supplier
    ATTR_CONFLICT_RES_LOOKUP = REQUESTOR_IF_CONFLICT
    IGNORE_NULLS = No
    JOIN_KEYS = @Value(Identifier.Artifact) @Value(Identifier.Artifact) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    UNMERGED_REQUESTOR -> AttributeKeeper_4
    USED_SUPPLIER -> StatisticsCalculator_3
    UNUSED_SUPPLIER -> StatisticsCalculator_3
AttributeKeeper_4
    CREATE_BULK_MODE_FEATURES = NO
    KEEP_ATTRS = Action,Content Category,Contributor Org,Contributor System,Date.LastUpdate,Identifier.Artifact,Record Type,RecordKeeper.LastSyncTS,RecordKeeper.LastUserToModify,RecordKeeper.Organization,RecordKeeper.System,Resource Total
    -> AttributeManager
AttributeManager
    ATTR_TABLE:
      SET_TO Action (varchar(200)) = D
      SET_TO Resource Total (varchar(200)) = 0
    -> StatisticsCalculator_3

Bookmark: Ajout d'un TimeStamp
AttributeCreator_22
    ATTR_TABLE:
      SET_TO RecordKeeper.LastSyncTS (varchar(200)) = @DateTimeFormat(@DateTimeNow(utc),%Y-%m-%d)T@DateTimeFormat(@Substring(@DateTimeAdd(@DateTimeNow(utc),PT0.5S),0,14),%H:%M:%S)Z
      SET_TO _timestamp (varchar(200)) = @DateTimeFormat(@DateTimeNow(utc),%Y%m%d)T@DateTimeFormat(@Substring(@DateTimeAdd(@DateTimeNow(utc),PT0.5S),0,14),%H%M%S)
    -> FeatureMerger_7 [SUPPLIER]
    -> FeatureMerger_9 [SUPPLIER]
    -> FeatureMerger_10 [SUPPLIER]

Bookmark: New Bookmark
ATTRIBUTE_UNEXPOSER
    -> AttributeExposer_8
AttributeExposer_8
    ATTR_TABLE = Action,,"Record Type",,"Contributor System",,"Contributor Org",,"Content Category",,"Publisher (EN)",,"Publisher (FR)",,PublishedFor,,"Creator (EN)",,"Creator (FR)",,"Subject Area",,"Subject Topic",,Identifier.Bundle,,Identifier.Artifact,,"Identifier.Artifact (DOI)",,Identifier.Child,,"Title (EN)",,"Title (FR)",,"Description (EN)",,"Description (FR)",,"Keywords (EN)",,"Keywords (FR)",,Date.LastUpdate,,Date.Published,,Date.Start,,Date.End,,Coverage.Geometry,,Coverage.ProvinceCd,,"Coverage.PlaceName (EN)",,"Coverage.PlaceName (FR)",,Coverage.Country,,Coverage.Region,,External.DatasetCategory,,External.ProjectCategory,,Rights.License,,Rights.Disposition,,UpdateFrequency,,RecordKeeper.Organization,,RecordKeeper.System,,RecordKeeper.LastUserToModify,,RecordKeeper.LastSyncTS,,Citation.Format[1],,"Citation.Value (EN)[1]",,"Citation.Value (FR)[1]",,Note.Type[1],,"Note.Title (EN)[1]",,"Note.Title (FR)[1]",,"Note.Desc (EN)[1]",,"Note.Desc (FR)[1]",,"Resource Total",,"Note Total",
    -> FeatureMerger_11 [SUPPLIER]

Bookmark: New Bookmark
StatisticsCalculator_3
    ATTR_ACCUM_MODE = None
    CALCULATION_MODE = NUMERIC
    FEAT_STATS = Resource Total,NUMERIC_MODE,,MAX,,,,,,,,,,,
    SUMMARY -> PythonCaller_10
    COMPLETE -> PythonCaller_11
Note: Create the geoDCAT header from the max # of resources
PythonCaller_10
    NEW_ATTRIBUTES = text_line_data buffer _order buffer
    PYTHONSOURCE:
      import fme
      import fmeobjects

      # Template Function interface:
      # When using this function, make sure its name is set as the value of
      # the 'Class or Function to Process Features' transformer parameter
      def processFeature(feature):

          header_reg=['Action','Record Type','Contributor System','Contributor Org','Content Category','Publisher (EN)','Publisher (FR)','PublishedFor','Creator (EN)','Creator (FR)',
          'Subject Area','Subject Topic','Identifier.Bundle','Identifier.Artifact','Identifier.Artifact (DOI)','Identifier.Child','Title (EN)','Title (FR)','Description (EN)','Description (FR)',
          'Keywords (EN)','Keywords (FR)','Date.LastUpdate','Date.Published','Date.Start','Date.End','Coverage.Geometry','Coverage.ProvinceCd','Coverage.PlaceName (EN)','Coverage.PlaceName (FR)',
          'Coverage.Country','Coverage.Region','External.DatasetCategory','External.ProjectCategory','Rights.License','Rights.Disposition','UpdateFrequency','RecordKeeper.Organization','RecordKeeper.System',
          'RecordKeeper.LastUserToModify','RecordKeeper.LastSyncTS','Citation Total','Citation.Format[1]','Citation.Value (EN)[1]','Citation.Value (FR)[1]','Note Total', 'Note.Type[1]', 'Note.Title (EN)[1]',
          'Note.Title (FR)[1]', 'Note.Desc (EN)[1]', 'Note.Desc (FR)[1]', 'Resource Total']

          header_res=['Type','Format','ServiceProtocol','Language','Name (EN)','Name (FR)','URL (EN)','URL (FR)']

          header=''

          for items in header_reg:
              header='%s,"%s"'%(header,items)



          for i in range(1,int(feature.getAttribute('Resource Total.max'))+1):
              for subitem in header_res:


                  header='%s,"Resource.%s[%i]"'%(header,subitem,i)

          feature.setAttribute('text_line_data',header.lstrip(','))
          feature.setAttribute('_order',1)

          """
          max_index=FME_utils.max_index_attribute_list(feature,'Resource{}')
          for j in range(max_index+1):
               feature.setAttribute('Resource.Type['+str(j+1)+']',feature.getAttribute('Resource{%i}.Type'%(j)))
               feature.setAttribute('Resource.Format['+str(j+1)+']',feature.getAttribute('Resource{%i}.Format'%(j)))
               feature.setAttribute('Resource.ServiceProtocol['+str(j+1)+']',feature.getAttribute('Resource{%i}.ServiceProtocol'%(j)))
               feature.setAttribute('Resource.Language['+str(j+1)+']',feature.getAttribute('Resource{%i}.Language'%(j)))
               feature.setAttribute('Resource.Name (EN)['+str(j+1)+']',feature.getAttribute('Resource{%i}.Name (EN)'%(j)))
               feature.setAttribute('Resource.Name (FR)['+str(j+1)+']',feature.getAttribute('Resource{%i}.Name (FR)'%(j)))
               feature.setAttribute('Resource.URL (EN)['+str(j+1)+']',feature.getAttribute('Resource{%i}.URL (EN)'%(j)))
               feature.setAttribute('Resource.URL (FR)['+str(j+1)+']',feature.getAttribute('Resource{%i}.URL (FR)'%(j)))
          """
    PYTHONSYMBOL = processFeature
    -> Sorter_2
Note: Create the geoDCAT rows from the max # of resources
PythonCaller_11
    NEW_ATTRIBUTES = text_line_data buffer nb_res buffer _order buffer
    PYTHONSOURCE:
      import fme
      import fmeobjects


      def csv_value(value):
          """
          Return a CSV-safe quoted value.
          - None (NULL) -> ""
          - Quotes are escaped per RFC 4180
          """
          if value is None:
              return '""'
          return '"%s"' % str(value).replace('"', r'""')


      def processFeature(feature):

          ###########################################################################
          # Attributes in geoDCAT.csv expected order (excluding resources)
          ###########################################################################
          attributes = [
              'Action', 'Record Type', 'Contributor System', 'Contributor Org',
              'Content Category', 'Publisher (EN)', 'Publisher (FR)', 'PublishedFor',
              'Creator (EN)', 'Creator (FR)', 'Subject Area', 'Subject Topic',
              'Identifier.Bundle', 'Identifier.Artifact', 'Identifier.Artifact (DOI)',
              'Identifier.Child', 'Title (EN)', 'Title (FR)', 'Description (EN)',
              'Description (FR)', 'Keywords (EN)', 'Keywords (FR)', 'Date.LastUpdate',
              'Date.Published', 'Date.Start', 'Date.End', 'Coverage.Geometry',
              'Coverage.ProvinceCd', 'Coverage.PlaceName (EN)',
              'Coverage.PlaceName (FR)', 'Coverage.Country', 'Coverage.Region',
              'External.DatasetCategory', 'External.ProjectCategory',
              'Rights.License', 'Rights.Disposition', 'UpdateFrequency',
              'RecordKeeper.Organization', 'RecordKeeper.System',
              'RecordKeeper.LastUserToModify', 'RecordKeeper.LastSyncTS',
              'Citation Total', 'Citation.Format[1]', 'Citation.Value (EN)[1]',
              'Citation.Value (FR)[1]', 'Note Total', 'Note.Type[1]', 'Note.Title (EN)[1]',
              'Note.Title (FR)[1]', 'Note.Desc (EN)[1]', 'Note.Desc (FR)[1]', 'Resource Total'
          ]

          text_line_data = ''

          # -------------------------------------------------------------------------
          # Main attributes
          # -------------------------------------------------------------------------
          for att in attributes:
              value = feature.getAttribute(att)
              text_line_data = '%s,%s' % (text_line_data, csv_value(value))

          ###########################################################################
          # Resources
          ###########################################################################
          max_index = int(feature.getAttribute('Resource Total'))

          res_att = [
              'Type', 'Format', 'ServiceProtocol', 'Language',
              'Name (EN)', 'Name (FR)', 'URL (EN)', 'URL (FR)'
          ]

          for j in range(1,max_index+1):
              for att in res_att:
                  value = feature.getAttribute('Resource{%i}.%s' % (j, att))
                  text_line_data = '%s,%s' % (text_line_data, csv_value(value))

          ###########################################################################
          # Output attributes
          ###########################################################################
          feature.setAttribute('text_line_data', text_line_data.lstrip(','))
          feature.setAttribute('nb_res', max_index + 1)
          feature.setAttribute('_order', 2)
    PYTHONSYMBOL = processFeature
    -> Sorter_2
Sorter_2
    SORT_PARM = _order NUMERIC ASCENDING Resource Total NUMERIC ASCENDING
    SORTED -> FeatureMerger_7 [REQUESTOR]
Note: faire un action2do si un des champs de geoDcat est vide (et doit avoir une valeur)
FeatureMerger_7
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = 1 1 AUTO
    MERGE_TYPE_VAL = ATTRIBUTES
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes Only
    MERGED -> AttributeKeeper_3
AttributeKeeper_3
    CREATE_BULK_MODE_FEATURES = NO
    KEEP_ATTRS = _timestamp,text_line_data
    -> FeatureWriter [text_line]
FeatureWriter
    DATASET = $(OUT_geodcat_DIR)\NRCAN-SLGO-@Value(_timestamp).csv
    DATASET_ATTR = _dataset
    FEATURE_TYPE_LIST_ATTR = _feature_type
    FORMAT = TEXTLINE
    TEXTLINE_COORDINATE_SYSTEM_GRANULARITY = FEATURE
    TEXTLINE_DESTINATION_DATASETTYPE_VALIDATION = Yes
    TEXTLINE_ENCODING = UTF-8
    TEXTLINE_END_OF_LINE = Windows
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    SUMMARY -> FeatureMerger_10 [REQUESTOR]

Bookmark: Upload to OSDP S3 bucket
FeatureMerger_10
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Execute_Python_Library
Note: Création du Last OGSL
Execute_Python_Library
    EXECUTION_TRACE = +Execute_Python_fileCopy
    Execution_Parameters:
      [
      {"parametersAreAttributeNames":False},
      {
        "source":"$(OUT_geodcat_DIR)\NRCAN-SLGO-@Value(_timestamp).csv",
        "destination":"$(OUT_old_geodcat_DIR)\Last_SLGO_file.csv"
      },
      ]
    Function_Name = fileCopy
    -> AttributeExposer_19
AttributeExposer_19
    ATTR_TABLE = ddr_iam_role,,osdp_bucket_owner_id,,S3_file_upload.iam_role,,S3_file_upload.bucket_owner_id,,_feature_type{0}._datestamp,,_timestamp,
    -> AttributeCreator_7
AttributeCreator_7
    ATTR_TABLE:
      SET_TO name (varchar(200)) = s3FileUploadACL
      SET_TO region (varchar(200)) = ca-central-1
      SET_TO s3_ftp_bucket (varchar(200)) = FME_CONDITIONAL:DEFAULT_VALUE'osdp-lz-prod-sftp-files'BOOL_OP;OR;COMPOSITE_TEST;1;TEST $(ENV) = STAGING'osdp-lz-dev-sftp-files'FME_NUM_CONDITIONS2___
      SET_TO destination_path (varchar(200)) = Project/Request/NRCAN-SLGO-@Value(_timestamp).csv
      SET_TO source_file (varchar(200)) = $(OUT_geodcat_DIR)\NRCAN-SLGO-@Value(_timestamp).csv
    -> Execute_decrypt
Execute_decrypt: Execute_Python_Library
    EXECUTION_TRACE = +Execute_decrypt
    Execution_Parameters:
      {
      "name":"name",
      "region":"region",
      "key_list" :
          [{
            "inputAttribute":"ddr_iam_role",
            "outputAttribute":"S3_file_upload.iam_role"
            },
           {
            "inputAttribute":"osdp_bucket_owner_id",
            "outputAttribute":"S3_file_upload.bucket_owner_id"
            }
           ]
      }
    Function_Name = decryptSecret
    -> Execute_s3FileUploadACL
Execute_s3FileUploadACL: Execute_Python_Library
    EXECUTION_TRACE = $(WORKSPACE_NAME)+Execute_s3FileUploadACL
    Execution_Parameters:
      {
      'iam_role':'S3_file_upload.iam_role',
      'ftp_path':'destination_path',
      'fme_server_path':'source_file',
      's3_ftp_bucket':'s3_ftp_bucket',
      'bucket_owner_id':'S3_file_upload.bucket_owner_id'
      }
    Function_Name = s3FileUploadACL
