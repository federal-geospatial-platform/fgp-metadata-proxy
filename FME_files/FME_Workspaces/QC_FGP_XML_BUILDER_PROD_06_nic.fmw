FME workspace QC_FGP_XML_BUILDER_PROD_06_nic.fmw

Parameters:
- ACTIVATE_GEO = Yes
- ACTIVATE_NON_GEO = No
- ACTIVATE_TRANSLATION = No
- CATALOGUE_READER_SELECT = Yes
- OUT_XML_FAILED_DIR = C:\Data\PT_Harvester\QC\XML_FAILED
- OUT_XML_PASSED_DIR = C:\Data\PT_Harvester\QC\XML_PASSED
- IN_FFS_TESTING_FILE = C:\Data\PT_Harvester\QC\FFS\QC_14Aug.ffs
- IN_GMD_XML_TEMPLATE_DIR = C:\Data\PT_Harvester
- IN_XLS_LOOKUP_TABLE_FILE = C:\Data\PT_Harvester\P-T_ETL_LOOKUP_TABLES.xlsx
- LOCAL_WRITER = Yes
- LOG_FILE = C:\Data\PT_Harvester\QC\LOG\QC.log
- OPEN_DATA_ENV = STAGING
- OUT_JSON_FAILED_DIR = C:\Data\PT_Harvester\QC\JSON_PASSED
- OUT_JSON_LOCAL_DIR = C:\Data\PT_Harvester\QC\JSON_LOCAL
- OUT_FFS_MAPPING_ERROR = C:\Data\PT_Harvester\QC\FFS\AttributeMappingErrors.ffs
- OUT_JSON_PASSED_DIR = C:\Data\PT_Harvester\QC\JSON_PASSED
- OUT_XLS_NOTIFICATION_DIR = C:\Data\PT_Harvester\QC\XLS
- OUT_XML_LOCAL_DIR = C:\Data\PT_Harvester\QC\XML_LOCAL
- P-T_ABBR = QC
- PYCSW_CKAN_OVERWRITE = YES
- FORCED_PYCSW_URL =   # http://127.0.0.1:8080/pycsw FORCED_PYCSW_URL
- SAMPLE_SELECT = No
- SAMPLE_SIZE = 10
- FME_SHAREDRESOURCE_DATA = C:\Data   # FME Server Resource Data

Readers:
- XLSXR_1: XLSXR from $(IN_XLS_LOOKUP_TABLE_FILE)

Writers:
- TEXTLINE_1: TEXTLINE to $(OUT_XML_PASSED_DIR)
- TEXTLINE_2: TEXTLINE to $(OUT_XML_FAILED_DIR)
- FFS_1: FFS to $(OUT_FFS_MAPPING_ERROR)
- TEXTLINE_3: TEXTLINE to $(OUT_XML_LOCAL_DIR)
- XLSXW_1: XLSXW to $(OUT_XLS_NOTIFICATION_DIR)
- TEXTLINE_4: TEXTLINE to $(OUT_JSON_LOCAL_DIR)
- TEXTLINE_5: TEXTLINE to $(OUT_JSON_PASSED_DIR)
- TEXTLINE_6: TEXTLINE to $(OUT_JSON_FAILED_DIR)

Note: Adding DonneesQuebec web link
QC_GEOPORTAL_WEBLINK_ADDER
    -> QC_SECTOR_MAPPER_AND_FILTER
Junction
    -> AttributeExposer_2
Tester_9
    BOOL_OP = OR
    COMPOSITE_TEST = 1
    TEST_CLAUSE = TEST @Value(id) = 8069f29c-8b64-4632-8628-dae28e18fdc6
    TEST_MODE = TEST
    PASSED -> Tester_2
WMS_URL_QC (reader XLSXR_1)
    attributes: id char(37), name char(71), url char(271)
    -> QC_WMS_URL_SETTER [LOOKUP_TABLE_INPUT]
Note: Corrects WMS URL to access layers
QC_WMS_URL_SETTER
    -> REMOVE_BROKEN_URL_WMS_ESRI_REST
AttributeCreator_4
    ATTR_TABLE = SET_TO _typedatasets = nongeo
    -> AttributeExposer
PyCSW_config (reader XLSXR_1)
    attributes: pt char(3), url_fmeserver char(30), url_desktop char(43)
    -> PYCSW_URL_MAPPER [PYCSW_CONFIG]
PYCSW_URL_MAPPER
    FORCED_PYCSW_URL = $(FORCED_PYCSW_URL)
    PROVIDER = $(P-T_ABBR)
    -> METADATA_DELTA_FINDER
Note: Searches existing PyCSW for new, updated or obsolete data
METADATA_DELTA_FINDER
    ABSTRACT_ATT_NEW = notes
    ABSTRACT_ATT_REF = MD_Metadata.identificationInfo.MD_DataIdentification.abstract.PT_FreeText.textGroup.LocalisedCharacterString
    CUSTOM_CSW_CKAN_URL = @Value(csw_url)
    DATESTAMP_ATT_NEW = record_last_modified
    DATESTAMP_ATT_REF = MD_Metadata.dateStamp.Date
    ID_ATT_NEW = id
    ID_ATT_REF = MD_Metadata.fileIdentifier.CharacterString
    RES_NAME_ATT_NEW = resources{}.name
    RES_NAME_ATT_REF = MD_Metadata.distributionInfo.MD_Distribution.transferOptions{}.MD_DigitalTransferOptions.onLine.CI_OnlineResource.name.PT_FreeText.textGroup.LocalisedCharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.PT_FreeText.textGroup.LocalisedCharacterString
    -> AttributeCreator_3
AttributeCreator_3
    ATTR_TABLE = SET_TO _typedatasets = geo
    -> AttributeExposer
Tester_4
    BOOL_OP = OR
    COMPOSITE_TEST = 1
    TEST_CLAUSE = TEST @Value(_typedatasets) = geo
    TEST_MODE = TEST
    PASSED -> XML_PUBLISHER
    FAILED -> ListRenamer
QC_JSON_CONFIG (reader XLSXR_1)
    attributes: TBS_ATTRIBUTES char(29), FEATURE_ATTRIBUTES char(27), SECTION char(15)
    -> JSON_PUBLISHER [CONFIG_FILE]
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer

Bookmark: Reading QC Geoportal datasets
Creator
    GEOMTYPE = Geometry Object
    NUM = 1
    CREATED -> DateTimeStamper
DateTimeStamper
    DATETIME_ATTR = _toto
    STAMP_TYPE = date
    TIMEZONE = local
    -> VariableSetter
VariableSetter
    SCOPE = Global
    VALUE = @Value(_toto)
    VARNAME = _timestamp
    -> Tester_3
Tester_3
    BOOL_OP = OR
    COMPOSITE_TEST = 1
    TEST_CLAUSE = TEST $(CATALOGUE_READER_SELECT) = Yes
    TEST_MODE = TEST
    PASSED -> Catalogue_Reader
    FAILED -> FeatureReader [INITIATOR]
Note: Reading QC CKAN-API
Catalogue_Reader: Catalogue Reader
    CUSTOM_CSW_LIST_NAME = DefaultNoList{}
    CUSTOM_URL = https://www.donneesquebec.ca/recherche/api/action
    SOURCE_URL = Manuel
    Résultats -> ATTRIBUTE_VALUE_TEXT_CLEANER
FeatureReader
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> ATTRIBUTE_VALUE_TEXT_CLEANER

Bookmark: Filtering and convertion to inhouse model.
ATTRIBUTE_VALUE_TEXT_CLEANER
    -> QC_ATTRIBUTE_MAPPER
Note: Exposes and sets attribute names extracted from CKAN-API
QC_ATTRIBUTE_MAPPER
    -> QC_LICENSE_FILTER
License_QC (reader XLSXR_1)
    attributes: license_id_value char(16), fgp_publish char(4)
    -> QC_LICENSE_FILTER [LOOKUP_TABLE_INPUT]
Note: Filters license_id values by their code referencing lookup table
QC_LICENSE_FILTER
    LICENCE_FILTERED_PASSED -> QC_DATE_FORMATTER
    UNKNOWN_LICENCE -> VariableRetriever
Note: Formats required date values to HNAP requirements
QC_DATE_FORMATTER
    -> RESOURCES_VALIDATOR
VariableRetriever
    SCOPE = Global
    VALUE_ATTR = _timestamp
    VARNAME = _timestamp
    -> LICENSE_ID_NOT_MAPPED (writer XLSXW_1)
LICENSE_ID_NOT_MAPPED (writer XLSXW_1)
    attributes: license_id auto(20), id auto(20)

Bookmark: Attribute Validation
Note: Validates url, name and format on resources{} list items
RESOURCES_VALIDATOR
    -> FORMAT_VALIDATOR
Note: Verfication if URL is valid WMS call for WMS formats
FORMAT_VALIDATOR
    -> EMAIL_FORMAT_TESTER
Note: Tests for '@' in email addresses
EMAIL_FORMAT_TESTER
    -> DEFAULT_ATTRIBUTE_MAPPER

Bookmark: Default value
Default_QC (reader XLSXR_1)
    attributes: default_key char(39), default_value char(192)
    -> DEFAULT_ATTRIBUTE_MAPPER [LOOKUP_TABLE_INPUT]
Note: Sets default attribute values
DEFAULT_ATTRIBUTE_MAPPER
    -> QC_MISSING_EMAIL_MAPPER

Bookmark: QC Missing eMail Mapper
Note: Creates missing email for a sector identified as missing email information
QC_MISSING_EMAIL_MAPPER: QC_MISSING_EMAIL_SETTER
    DATA_OUTPUT_PASSED -> QC_GEOPORTAL_WEBLINK_ADDER

Bookmark: Sector Mapper
Sector_QC (reader XLSXR_1)
    attributes: original_sector_value char(79), hnap_sector_value char(79), graphic_link char(128), fgp_publish char(4), jurisdiction char(11)
    -> QC_SECTOR_MAPPER_AND_FILTER [LOOKUP_TABLE_INPUT]
Note: Maps sector values and filters for publishing by referencing lookup table. Creates graphic thumbnail output
QC_SECTOR_MAPPER_AND_FILTER
    OUTPUT_SECTOR_PASSED -> GEOSPATIAL_DATA_VALIDATOR
    UNKNOWN_SECTOR -> VariableRetriever_2
VariableRetriever_2
    SCOPE = Global
    VALUE_ATTR = _timestamp
    VARNAME = _timestamp
    -> SECTORS_NOT_MAPPED (writer XLSXW_1)
SECTORS_NOT_MAPPED (writer XLSXW_1)
    attributes: sector auto(20), id auto(20)

Bookmark: spatial data type management
Geospatial_QC (reader XLSXR_1)
    attributes: fgp_publish char(4), format char(8), spatial_type char(12)
    -> GEOSPATIAL_DATA_VALIDATOR [LOOKUP_TABLE_INPUT]
GEOSPATIAL_DATA_VALIDATOR
    KEYWORD_SEARCH = Photographie aérienne|Toponyme|Toponymie|photogrammétrie|GPS|cartographie
    GEOSPATIAL -> Tester_7
    NON-GEOSPATIAL -> Tester_6
    UNKNOWN_FORMAT -> VariableRetriever_3
Tester_7
    BOOL_OP = OR
    COMPOSITE_TEST = 1
    TEST_CLAUSE = TEST @UpperCase($(ACTIVATE_GEO)) = YES
    TEST_MODE = TEST
    PASSED -> SPATIAL_TYPE_MAPPER [DATA_INPUT]
VariableRetriever_3
    SCOPE = Global
    VALUE_ATTR = _timestamp
    VARNAME = _timestamp
    -> GEOSPATIAL_FORMAT_NOT_MAPPED (writer XLSXW_1)
GEOSPATIAL_FORMAT_NOT_MAPPED (writer XLSXW_1)
    attributes: format string(8)
Tester_6
    BOOL_OP = OR
    COMPOSITE_TEST = 1
    TEST_CLAUSE = TEST @UpperCase($(ACTIVATE_NON_GEO)) = YES
    TEST_MODE = TEST
    PASSED -> Tester_8
UUID_Spatial_QC (reader XLSXR_1)
    attributes: uuid char(37), spatial_representation_type char(10)
    -> SPATIAL_TYPE_MAPPER [LOOKUP_TABLE_INPUT]
Note: Uses algorithm to determine spatial_representation_type of dataset
SPATIAL_TYPE_MAPPER
    DATA_OUTPUT_FAILED -> VariableRetriever_4
    DATA_OUTPUT_PASSED -> Tester_9
VariableRetriever_4
    SCOPE = Global
    VALUE_ATTR = _timestamp
    VARNAME = _timestamp
    -> SPATIALTYPE_NOT_MAPPED (writer XLSXW_1)
SPATIALTYPE_NOT_MAPPED (writer XLSXW_1)
    attributes: notes auto(20), title auto(20), id auto(20)

Bookmark: Sampler
Tester_8
    BOOL_OP = OR
    COMPOSITE_TEST = 1
    TEST_CLAUSE = TEST @UpperCase($(SAMPLE_SELECT)) = YES
    TEST_MODE = TEST
    PASSED -> Sampler_2
    FAILED -> Junction
Sampler_2
    RATE = $(SAMPLE_SIZE)
    SAMPLE_MODE = No
    SAMPLE_TYPE_LONG = First N Features
    SAMPLED -> Junction

Bookmark: Non-geospatial processing
AttributeExposer_2
    ATTR_LIST = author,author_email,groups{}.name,id,license_id,metadata_created,metadata_modified,notes,organization.title,resources{}.id,resources{}.name,resources{}.url,tags{}.display_name,temporal,title,update_frequency
    -> QC_TBS_ATTRIBUTE_VALUE_MAPPER
Format_TBS_QC (reader XLSXR_1)
    attributes: QC_value char(8), TBS_value char(7)
    -> QC_TBS_ATTRIBUTE_VALUE_MAPPER [LOOKUP_TABLE_FORMAT]
UpdateFrequency_TBS_QC (reader XLSXR_1)
    attributes: QC_value char(13), TBS_value char(12)
    -> QC_TBS_ATTRIBUTE_VALUE_MAPPER [LOOKUP_TABLE_FREQUENCY]
ResourceType_TBS_QC (reader XLSXR_1)
    attributes: QC_value char(8), TBS_value char(12)
    -> QC_TBS_ATTRIBUTE_VALUE_MAPPER [LOOKUP_TABLE_TYPE]
SubjectNTopic_TBS_QC (reader XLSXR_1)
    attributes: QC_value char(44), TBS_topic char(12), TBS_subject char(24)
    -> QC_TBS_ATTRIBUTE_VALUE_MAPPER [LOOKUP_TABLE_SUBJECT_TOPIC]
QC_TBS_ATTRIBUTE_VALUE_MAPPER
    -> ListElementCounter_2
    UNKNOWN_FREQUENCY -> update_frequency_new_values_tbs (writer XLSXW_1)
    UNKNOWN_SUBJECT -> subject_new_values_tbs (writer XLSXW_1)
    UNKNOWN_FORMAT -> format_new_values_tbs (writer XLSXW_1)
    UNKNOWN_TYPE -> restype_new_values_tbs (writer XLSXW_1)
AttributeCreator_7
    ATTR_TABLE = SET_TO _env_ckan_tbs = @UpperCase($(OPEN_DATA_ENV))
    -> AttributeFilter_2
AttributeFilter_2
    ATTR_NAME = _env_ckan_tbs
    ATTR_VALUES = <Empty>,<Missing>,<Null>,<Unfiltered>,PROD,STAGING
    PROD -> AttributeCreator_8
    STAGING -> AttributeCreator_9
AttributeCreator_8
    ATTR_TABLE = SET_TO _url_ckan_api = https://open.canada.ca/data/api/action
    -> AttributeExposer_5
AttributeCreator_9
    ATTR_TABLE = SET_TO _url_ckan_api = https://staging.open.canada.ca/data/api/action
    -> AttributeExposer_5
AttributeExposer_5
    ATTR_LIST = tbs_owner_org_id
    -> METADATA_DELTA_FINDER_2
METADATA_DELTA_FINDER_2
    ABSTRACT_ATT_NEW = notes
    ABSTRACT_ATT_REF = notes_translated.fr
    CKAN_FILTER = fq=owner_org:@Value(tbs_owner_org_id)
    CUSTOM_CSW_CKAN_URL = @Value(_url_ckan_api)
    DATESTAMP_ATT_NEW = record_last_modified
    DATESTAMP_ATT_REF = federated_date_modified
    ID_ATT_NEW = id
    ID_ATT_REF = id
    RES_NAME_ATT_NEW = resources{}.name
    RES_NAME_ATT_REF = resources{}.name_translated.fr
    RES_URL_ATT_NEW = resources{}.url
    RES_URL_ATT_REF = resources{}.url
    TITLE_ATT_NEW = title
    TITLE_ATT_REF = title_translated.fr
    -> AttributeCreator_4
update_frequency_new_values_tbs (writer XLSXW_1)
    attributes: update_frequency string(20), id string(20)
subject_new_values_tbs (writer XLSXW_1)
    attributes: name string(20), id string(20)
format_new_values_tbs (writer XLSXW_1)
    attributes: id string(20), format string(20)
restype_new_values_tbs (writer XLSXW_1)
    attributes: id string(20), restype string(20)
ListRenamer
    LEAVE_ORIG = No
    LIST_ACTION = Rename
    LIST_COMPONENT_NAMES = tags{},tags{},display_name,display_name_fr
    LIST_NAME = tags{}.display_name
    -> ListRenamer_2
ListRenamer_2
    LEAVE_ORIG = No
    LIST_ACTION = Rename
    LIST_COMPONENT_NAMES = resources{},resources{},name,name_fr
    LIST_NAME = resources{}.name
    -> AttributeExposer_3
AttributeExposer_3
    ATTR_LIST = p-t_entity_fr,p-t_entity_en
    -> AttributeCreator_5
AttributeCreator_5
    ATTR_TABLE:
      SET_TO nom_organisation_fr = @Value(p-t_entity_fr);@Value(p-t_entity_fr);@Value(sector)
      SET_TO nom_organisation_en = @Value(p-t_entity_en);@Value(p-t_entity_en);@Value(sector)
    -> JSON_PUBLISHER
JSON_PUBLISHER
    CKAN_API_EXE = C:\Python27\Scripts\ckanapi.exe
    CKAN_ENV = $(OPEN_DATA_ENV)
    LOCAL_WRITER = $(LOCAL_WRITER)
    TEMP_REP = C:\FME_TEMP
    UPLOAD_FAILED -> AttributeExposer_7
    OUTPUT_LOCAL -> AttributeExposer_4
    UPLOAD_PASSED -> AttributeExposer_6
AttributeExposer_4
    ATTR_LIST = json_file,id
    -> AttributeCreator_6
AttributeCreator_6
    ATTR_TABLE = SET_TO text_line_data = @Value(json_file)
    -> text_line (writer TEXTLINE_4)
text_line (writer TEXTLINE_4)
    attributes: text_line_data buffer
AttributeExposer_6
    ATTR_LIST = json_file,id
    -> AttributeCreator_11
AttributeCreator_11
    ATTR_TABLE = SET_TO text_line_data = @Value(json_file)
    -> text_line (writer TEXTLINE_5)
text_line (writer TEXTLINE_5)
    attributes: text_line_data buffer
AttributeExposer_7
    ATTR_LIST = json_file,id
    -> AttributeCreator_12
AttributeCreator_12
    ATTR_TABLE = SET_TO text_line_data = @Value(json_file)
    -> text_line (writer TEXTLINE_6)
text_line (writer TEXTLINE_6)
    attributes: text_line_data buffer

Bookmark: Sampler
Tester_2
    BOOL_OP = OR
    COMPOSITE_TEST = 1
    TEST_CLAUSE = TEST @UpperCase($(SAMPLE_SELECT)) = YES
    TEST_MODE = TEST
    PASSED -> Sampler
    FAILED -> QC_PROJECTION_GEOEXTENTS_EXTRACTOR
Sampler
    RATE = $(SAMPLE_SIZE)
    SAMPLE_MODE = No
    SAMPLE_TYPE_LONG = First N Features
    SAMPLED -> QC_PROJECTION_GEOEXTENTS_EXTRACTOR

Bookmark: Projection and GeoExtents Management
Note: Extracts projection values and bounding box coordinates from url, wms or esri rest, where they exist. Missing projection values are set to unknown
QC_PROJECTION_GEOEXTENTS_EXTRACTOR
    DATA_OUTPUT -> GEO_EXTENTS_MAPPER
Coord_QC (reader XLSXR_1)
    attributes: location char(20), south_bound_latitude number(6,2), west_bound_longitude number(7,2), east_bound_longitude x_coordinate, north_bound_latitude y_coordinate
    -> GEO_EXTENTS_MAPPER [LOOKUP_TABLE]
Note: Sets geoextents not created in previous transformer based on lookup table values
GEO_EXTENTS_MAPPER
    LATITUDE_MAX = 64
    LATITUDE_MIN = 44
    LONGITUDE_MAX = -56
    LONGITUDE_MIN = -80
    EXTENT_DEFINED -> METADATA_VALUE_MAPPER [DATA_INPUT]
    UNKNOWN_EXTENT -> VariableRetriever_6
VariableRetriever_6
    SCOPE = Global
    VALUE_ATTR = _timestamp
    VARNAME = _timestamp
    -> GEO_EXTENTS_NOT_MAPPED (writer XLSXW_1)
GEO_EXTENTS_NOT_MAPPED (writer XLSXW_1)
    attributes: location string(20), id auto(20)

Bookmark: Attribute value mapper
Note: This section utilizes mulitple instances of the METADATA_VALUE_MAPPER to correct values to valid English values and to add the valid French equivalents and RI_CODES where applicable. It can be utilized for mulitple metadata items by accessing custom look up tables applicable to specific items. / Turn the error mapping options and the data items to be mapped on or off by clicking on the transformer and selecting yes/no. / - ERROR_NOT_MAPPED: enables mapping of data item values that cannot be found in the lookup tables. / - ENGLISH_REFRESH: enables updating of English attribute values. / - FRENCH_REFRESH: enables updating of French attribute values. / - CODE_REFRESH: enables updating of RI_CODE values. / Enter the attribute key name by clicking on the transformer and selecting the drop down menu next to the 'att_to_map' text box and selecting the 'Open text editor...' option. Explicitly enter the attribute key name in the text editor (ie: contacts{}.role). / IMPORTANT: Do not select the 'Attribute Value' option from the drop down menu to select the attribute key name.
Update (reader XLSXR_1)
    attributes: original_value char(13), real_value_english char(12), real_value_french char(14), code_value char(7)
    -> METADATA_VALUE_MAPPER [LOOKUP_TABLE_INPUT]
Note: Maps update cycle to HNAP standards
METADATA_VALUE_MAPPER
    ATT_TO_MAP = update_frequency
    CODE_REFRESH = YES
    ENGLISH_REFRESH = YES
    ERROR_NOT_MAPPED = YES
    FRENCH_REFRESH = YES
    -> MAPPING_ERROR_LIST_CREATOR
    -> METADATA_VALUE_MAPPER_2 [DATA_INPUT]
Progress (reader XLSXR_1)
    attributes: original_value char(18), real_value_english char(18), real_value_french char(18), code_value char(7)
    -> METADATA_VALUE_MAPPER_2 [LOOKUP_TABLE_INPUT]
Note: Maps progress code to HNAP standards
METADATA_VALUE_MAPPER_2
    ATT_TO_MAP = progress_code
    CODE_REFRESH = YES
    ENGLISH_REFRESH = YES
    ERROR_NOT_MAPPED = YES
    FRENCH_REFRESH = YES
    -> METADATA_VALUE_MAPPER_3 [DATA_INPUT]
    -> MAPPING_ERROR_LIST_CREATOR
SpatialRepresentation (reader XLSXR_1)
    attributes: original_value char(12), real_value_english char(12), real_value_french char(13), code_value char(7)
    -> METADATA_VALUE_MAPPER_3 [LOOKUP_TABLE_INPUT]
Note: Maps spatial_representation_type to HNAP standards
METADATA_VALUE_MAPPER_3
    ATT_TO_MAP = spatial_representation_type
    CODE_REFRESH = YES
    ENGLISH_REFRESH = YES
    ERROR_NOT_MAPPED = YES
    FRENCH_REFRESH = YES
    -> METADATA_FORMAT_MAPPER [DATA_INPUT]
    -> MAPPING_ERROR_LIST_CREATOR

Bookmark: Format value mapper
Note: This section utilizes the METADATA_FORMAT_MAPPER to correct data format values to valid data format values and to associate and add the French and English 'Resource Type' attribute to each data format type. It accesses a custom look up table applicable to data formats. / Turn the error mapping options and the data items to be mapped on or off by clicking on the transformer and selecting yes/no. / - ERROR_NOT_MAPPED: enables mapping of data item values that cannot be found in the lookup tables. / - REAL_VALUE_REFRESH: enables updating of data format attribute values. / - RES_TYPE_FR_REFRESH: enables mapping of French resource types. / - RES_TYPE_EN_REFRESH: enables mapping of English resource types. / Enter the attribute key name by clicking on the transformer and selecting the drop down menu next to the 'att_to_map' text box and selecting the 'Open text editor...' option. Explicitly enter the attribute key name in the text editor (ie: resources{}.format). / IMPORTANT: Do not select the 'Attribute Value' option from the drop down menu to select the attribute key name.
Format (reader XLSXR_1)
    attributes: original_value char(163), real_value char(10), resource_type_fr char(20), resource_type_en char(20), date_added date, province char(3)
    -> METADATA_FORMAT_MAPPER [LOOKUP_TABLE_INPUT]
METADATA_FORMAT_MAPPER
    ATT_TO_MAP = resources{}.format
    ERROR_NOT_MAPPED = YES
    REAL_VALUE_REFRESH = YES
    RES_TYPE_EN_REFRESH = YES
    RES_TYPE_FR_REFRESH = YES
    -> MAPPING_ERROR_LIST_CREATOR
    -> URL_CHARACTER_ENCODER

Bookmark: Mapping error list creator
Note: Creates list of errors found and corrected in mapping
MAPPING_ERROR_LIST_CREATOR
    LIST_ATTR = mapping_errors{}
    LIST_NAME = mapping_errors{}
    -> ATTRIBUTE_MAPPING_ERRORS (writer FFS_1)
ATTRIBUTE_MAPPING_ERRORS (writer FFS_1)
    attributes: error varchar(200), _element_index varchar(200)

Bookmark: URL Character Encoder
Note: URL's containing {} will not validate. UTF8 value is substituted where they exist.
URL_CHARACTER_ENCODER
    DATA_OUTPUT -> QC_WMS_URL_SETTER [DATA_INPUT]

Bookmark: Data cleanup. Dropping broken web services
Note: Tests WMS/ESRI_REST resource URL's and removes them where broken
REMOVE_BROKEN_URL_WMS_ESRI_REST
    -> WMS_REST_LANGUAGE_FORMATTER
    FAULTY_URL_OUTPUT -> VariableRetriever_7
VariableRetriever_7
    SCOPE = Global
    VALUE_ATTR = _timestamp
    VARNAME = _timestamp
    -> MAP_SERVICE_URL_ERROR (writer XLSXW_1)
MAP_SERVICE_URL_ERROR (writer XLSXW_1)
    attributes: id auto(20), format string(8), url auto(20), _url_failure_message auto(20)

Bookmark: HNAP Rules- 1 web service per language.
Note: Formats WMS and ESRI REST resources to add French versions and formats French and English versions with valid supporting attributes
WMS_REST_LANGUAGE_FORMATTER
    -> DUPLICATE_SERVICE_REMOVER
Note: Removes duplicate WMS or ESRI REST resources where they exist, that would otherwise invalidate the dataset
DUPLICATE_SERVICE_REMOVER
    -> RESOURCE_NAME_UNDERSCORE_REMOVER

Bookmark: Data preparation for metadata section
Note: Removes all underscores from resources{}.name attributes. Long compounded names joined by underscores in this field can cause display formatting issues when published to the FGP.
RESOURCE_NAME_UNDERSCORE_REMOVER
    DATA_OUTPUT -> ListCopier
    ERROR_OUTPUT -> VariableRetriever_8
ListCopier
    DEST_LIST = distributionList
    SRC_LIST = resources{}
    -> GMD_SECTION_DATA_EXTRACTION
Note: Creates lists and removes duplicates for GMD_Section
GMD_SECTION_DATA_EXTRACTION
    -> MORE_INFO_MANAGER
Note: Tests the more_info{}.link list for valid attribute values and filters them out where missing
MORE_INFO_MANAGER
    -> MapResourceAttributionRemover
VariableRetriever_8
    SCOPE = Global
    VALUE_ATTR = _timestamp
    VARNAME = _timestamp
    -> RESOURCE_NAME_UNDERSCORE_ERROR (writer XLSXW_1)
RESOURCE_NAME_UNDERSCORE_ERROR (writer XLSXW_1)
    attributes: id auto(20)
QC_MAP_RES_REMOVE (reader XLSXR_1)
    attributes: url char(213)
    -> MapResourceAttributionRemover [URL]
MapResourceAttributionRemover
    -> PYCSW_URL_MAPPER

Bookmark: Adjusting number of tags
ListElementCounter_2
    CNT_ATTR = _element_count_tags
    LIST_NAME = tags{}
    -> Tester_5
Tester_5
    BOOL_OP = OR
    COMPOSITE_TEST = 1
    TEST_CLAUSE = TEST @Value(_element_count_tags) = 0
    TEST_MODE = TEST
    PASSED -> AttributeCreator_10
    FAILED -> Junction_2
AttributeCreator_10
    ATTR_TABLE = SET_TO tags{0}.display_name = données ouvertes
    -> Junction_2
Junction_2
    -> AttributeCreator_7

Bookmark: New Bookmark
Note: Exposes PyCSW_Transaction attribute
AttributeExposer
    ATTR_LIST = PyCSW_Transaction
    -> AttributeFilter
Note: Filters items by PyCSW transaction type
AttributeFilter
    ATTR_NAME = PyCSW_Transaction
    ATTR_VALUES = <Empty>,<Missing>,<Null>,<Unfiltered>,No change,Update,Insert,Delete
    <EMPTY> -> Terminator
    <MISSING> -> Terminator
    <NULL> -> Terminator
    <UNFILTERED> -> Terminator
    No change -> Tester
    Update -> AWS_TRANSLATE
    Insert -> AWS_TRANSLATE
    Delete -> VariableRetriever_9
Terminator
    MESSAGE = ERROR: Unknown _event value from Metadata_Delta
Note: Selects items with no change for publishing, overwriting all existing data
Tester
    BOOL_OP = OR
    COMPOSITE_TEST = 1
    TEST_CLAUSE = TEST $(PYCSW_CKAN_OVERWRITE) = YES
    TEST_MODE = TEST
    PASSED -> AttributeCreator
    FAILED -> StatisticsCalculator
Note: Reset to update
AttributeCreator
    ATTR_TABLE = SET_TO PyCSW_Transaction = Update
    -> AWS_TRANSLATE
VariableRetriever_9
    SCOPE = Global
    VALUE_ATTR = _timestamp
    VARNAME = _timestamp
    -> DELETED_RECORDS (writer XLSXW_1)
DELETED_RECORDS (writer XLSXW_1)
    attributes: id auto(20)
Creator_2
    GEOMTYPE = Geometry Object
    NUM = 1
    CREATED -> StatisticsCalculator
StatisticsCalculator
    COMPUTE_HISTOGRAM = NO
    COUNT_ATTR = _count
    PREPEND_ATTR_NAME_CHOICE = For multiple results only
    STATS_ATTRS = id
    SUMMARY -> AttributeCreator_2
AttributeCreator_2
    ATTR_TABLE = SET_TO _real_count = @Evaluate(@Value(_count)-1)
    -> StatisticsCalculator_Summary
StatisticsCalculator_Summary: Logger
    LOG_FEATURE = NONE
    MAXFEATS = 20
    MESSAGE:
      ************************
      **** Unchanged Report ****
      ************************

      @Value(_real_count) features were unchanged

      ************************
      ************************
      ************************
    SEVERITY = INFO

Bookmark: Language Translation
Note: Translates specific items from French to English
AWS_TRANSLATE
    ACTIVATE_TRANSLATION = $(ACTIVATE_TRANSLATION)
    MODE = French-->English
    -> Tester_4
    TRANSLATION_PROBLEM -> VariableRetriever_5
VariableRetriever_5
    SCOPE = Global
    VALUE_ATTR = _timestamp
    VARNAME = _timestamp
    -> translation_problems (writer XLSXW_1)
translation_problems (writer XLSXW_1)
    attributes: id auto(20)

Bookmark: XML CREATION AND WRITING
Note: Excel config file to map QC attributes to those required by XML templates
Config_QC (reader XLSXR_1)
    attributes: HNAP_ATTRIBUTES char(54), FEATURE_ATTRIBUTES char(60), METADATA_SECTION char(191)
    -> XML_PUBLISHER [CONFIG_FILE]
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
XML_PUBLISHER
    LOCAL_WRITER = $(LOCAL_WRITER)
    TEMPLATE_GMD_CITEDRESPONSIBLEPARTY = $(IN_GMD_XML_TEMPLATE_DIR)\GMD_CITEDRESPONSIBLEPARTY.xml
    TEMPLATE_GMD_CONTACT = $(IN_GMD_XML_TEMPLATE_DIR)\GMD_CONTACT.xml
    TEMPLATE_GMD_DISTRIBUTIONFORMAT = $(IN_GMD_XML_TEMPLATE_DIR)\GMD_DISTRIBUTIONFORMAT.xml
    TEMPLATE_GMD_DISTRIBUTOR = $(IN_GMD_XML_TEMPLATE_DIR)\GMD_DISTRIBUTOR.xml
    TEMPLATE_GMD_KEYWORDS = $(IN_GMD_XML_TEMPLATE_DIR)\GMD_KEYWORDS.xml
    TEMPLATE_GMD_MDMETADATA = $(IN_GMD_XML_TEMPLATE_DIR)\GMD_MDMETADATA.xml
    TEMPLATE_GMD_REFERENCESYSTEMINFO = $(IN_GMD_XML_TEMPLATE_DIR)\GMD_REFERENCESYSTEMINFO.xml
    TEMPLATE_GMD_RESOURCEMAINTENANCE = $(IN_GMD_XML_TEMPLATE_DIR)\GMD_RESOURCEMAINTENANCE.xml
    TEMPLATE_GMD_TOPICCATEGORY = $(IN_GMD_XML_TEMPLATE_DIR)\GMD_TOPICCATEGORY.xml
    TEMPLATE_GMD_TRANSFEROPTIONS = $(IN_GMD_XML_TEMPLATE_DIR)\GMD_TRANSFEROPTIONS.xml
    LOCAL -> text_line (writer TEXTLINE_3)
    INSERT_PASSED -> text_line (writer TEXTLINE_1)
    INSERT_FAILED -> text_line (writer TEXTLINE_2)
    UPDATE_PASSED -> text_line (writer TEXTLINE_1)
    UPDATE_FAILED -> text_line (writer TEXTLINE_2)

FME custom transformer AWS_TRANSLATE

Parameters:
- ACTIVATE_TRANSLATION =
- MODE =

Note: This custom transformer sends API queries with English language attribute text and returns and extracts French translations from JSON response string. Also tests for empty strings in some attributes, that would cause translation to fail. It is universal to all workspaces.
INPUT (input)
    -> AttributeExposer
OUTPUT (output)
TRANSLATION_PROBLEM (output)
Sampler
    RATE = 5
    SAMPLE_MODE = No
    SAMPLE_TYPE_LONG = Every Nth Feature
    SAMPLED -> Counter
Counter
    CNT_ATTR = _count
    DOMAIN = counter
    SCOPE = Local
    START = 1
    -> AttributeCreator_2
AttributeCreator_2
    ATTR_TABLE = SET_TO _nb_features = @Evaluate(@Value(_count)*5)
    -> Logger
Logger
    LOG_FEATURE = NONE
    MAXFEATS = 99999
    MESSAGE = @Value(_nb_features) / @Value(_total_number) translated
    SEVERITY = INFO

Bookmark: DeepL Translate
AttributeExposer
    ATTR_LIST = title,notes,sector,tags{}.display_name,resources{}.name
    -> AttributeCreator_4
AttributeCreator_4
    ATTR_TABLE = SET_TO notes_copy = @Value(notes)
    -> PythonCaller_4
PythonCaller_4
    NEW_ATTRIBUTES = urls_https{} urls_http{} urls_ftp{}
    PYTHONSOURCE:
      import fme
      import fmeobjects
      import re
      # Template Function interface:
      # When using this function, make sure its name is set as the value of
      # the 'Class or Function to Process Features' transformer parameter
      def processFeature(feature):

          abstract=feature.getAttribute('notes')


          urls_https = re.findall(r'https?://\S+',abstract)
          urls_http = re.findall(r'http?://\S+',abstract)
          urls_ftp = re.findall(r'ftp?://\S+',abstract)

          feature.setAttribute('urls_https',urls_https)
          feature.setAttribute('urls_http',urls_http)
          feature.setAttribute('urls_ftp',urls_ftp)

          indice_https=0
          indice_http=0
          indice_ftp=0

          for url in urls_https:

              abstract=abstract.replace(url,'$U$S%d$'%(indice_https))

              indice_https=indice_https+1
          for url in urls_http:
              abstract=abstract.replace(url,'$U$P%d$'%(indice_http))
              indice_http=indice_http+1
          for url in urls_ftp:
              abstract=abstract.replace(url,'$U$F%d$'%(indice_ftp))
              indice_ftp=indice_ftp+1

          feature.setAttribute('notes',abstract)
    PYTHONSYMBOL = processFeature
    -> StringLengthCalculator
Note: Calculates string length of notes attribute
StringLengthCalculator
    LENGTH_ATTR = _length
    SRC_ATTR = notes
    -> Tester
Note: Filters 'notes' attribute for string length <= 4950 characters - approximate max allowed for AWS Translate
Tester
    BOOL_OP = OR
    COMPOSITE_TEST = 1
    TEST_CLAUSE = TEST @Value(_length) <= 4950
    TEST_MODE = TEST
    PASSED -> AttributeCreator
    FAILED -> SubstringExtractor
Note: Extracts first 4950 characters of filtered out 'notes' attribute to become 'notes_temp'
SubstringExtractor
    END = 4949
    RESULT_ATTR = notes_temp
    SRC_STRING = @Value(notes)
    START = 0
    -> AttributeRenamer
AttributeRenamer
    ATTR_TABLE = RENAME_SET_DEFAULT notes_temp > notes
    -> AttributeCreator
AttributeCreator
    ATTR_TABLE:
      SET_TO _aws_activation = $(ACTIVATE_TRANSLATION)
      SET_TO _mode = $(MODE)
    -> StatisticsCalculator
StatisticsCalculator
    COMPUTE_HISTOGRAM = NO
    COUNT_ATTR = _total_number
    PREPEND_ATTR_NAME_CHOICE = For multiple results only
    STATS_ATTRS = notes
    COMPLETE -> AttributeCreator_3
AttributeCreator_3
    ATTR_TABLE = SET_TO _iteration = 1
    -> Interative_translation [PythonCaller_Input]
Interative_translation
    TRANSLATED -> Sampler
    TRANSLATED -> AttributeCreator_5
    FAILED -> TRANSLATION_PROBLEM (output)
AttributeCreator_5
    ATTR_TABLE = SET_TO notes = @Value(notes_copy)
    -> OUTPUT (output)

FME custom transformer Interative_translation

PythonCaller_Input (input)
    -> AttributeExposer
AttributeExposer
    ATTR_LIST = _iteration
    -> Logger_2
Logger_2
    LOG_FEATURE = LOG_ONLY
    MAXCOORDS = 20
    MAXFEATS = 20
    MESSAGE = Feature is:APAPAPAPAPAPAPAPA
    SEVERITY = INFO
    LOGGED -> PythonCaller
Note: Translation with AWS
PythonCaller
    NEW_ATTRIBUTES = _translation_problem
    PYTHONSOURCE:
      import fme
      import fmeobjects
      import time

      def translate_attributes(inText,inlang,outlang):
          try:
              import boto3



              translate = boto3.client('translate', 'ca-central-1', use_ssl=True)
              result = translate.translate_text(Text=inText,SourceLanguageCode=inlang, TargetLanguageCode=outlang).get('TranslatedText')
              return result
          except:
              print ('NE FONCTIONNE PAS DU PREMIER COUP')
              print('PROBLEME _________________________________')
              print(inText)
              raise


      # Template Function interface:
      # When using this function, make sure its name is set as the value of
      # the 'Class or Function to Process Features' transformer parameter
      def processFeature(feature):
          attributestranslation=[r'notes',r'title',r'sector']
          list_atttranslation=[[r'tags',r'display_name'],[r'resources',r'name']]

          try:

              if feature.getAttribute('_mode')==r'English-->French':
                  in_lang="en"
                  out_lang="fr"
                  out_suffix=r'_fr'
              else:
                  in_lang="fr"
                  out_lang="en"
                  out_suffix=r'_en'




              for i in attributestranslation:
                  text = feature.getAttribute(i)
                  if text:
                      if feature.getAttribute('_aws_activation').lower()=='yes':
                          translated_text = translate_attributes(text,in_lang,out_lang)
                      else:
                          translated_text='Translation of '+text
                      if translated_text:
                          feature.setAttribute('%s%s'%(i,out_suffix),translated_text)

              for j in list_atttranslation:
                  #Evaluation list length
                  list_length=len(feature.getAttribute(j[0]+r'{}.'+j[1]))
                  for k in range(int(list_length)):
                      text = feature.getAttribute(j[0]+r'{'+str(k)+r'}.'+j[1])
                      if text:
                          if feature.getAttribute('_aws_activation').lower()=='yes':
                              translated_text = translate_attributes(text,in_lang,out_lang)
                          else:
                              translated_text='Translation of '+text
                          if translated_text:
                              feature.setAttribute(j[0]+r'{'+str(k)+r'}.'+j[1]+out_suffix,translated_text)


              feature.setAttribute('_translation_problem',0)
          except:
              feature.setAttribute('_translation_problem',1)
    PYTHONSYMBOL = processFeature
    -> Tester_2
Tester_2
    BOOL_OP = OR
    COMPOSITE_TEST = 1
    TEST_CLAUSE = TEST @Value(_translation_problem) = 0
    TEST_MODE = TEST
    PASSED -> Logger
    FAILED -> Tester
Logger
    LOG_FEATURE = LOG_ONLY
    MAXCOORDS = 20
    MAXFEATS = 20
    MESSAGE = Feature is: TOTOTOTTTTTTTTTTTTTTTTTTTTTTTTTTTTTTTTTTTTTTTTTTTTTTTTTTTTTTTTTTT
    SEVERITY = INFO
    LOGGED -> PythonCaller_5
PythonCaller_5
    PYTHONSOURCE:
      import fme
      import fmeobjects
      # Template Function interface:
      # When using this function, make sure its name is set as the value of
      # the 'Class or Function to Process Features' transformer parameter
      def processFeature(feature):
          try:
              indice_https=0
              indice_http=0
              indice_ftp=0

              if feature.getAttribute('_mode')==r'English-->French':
                  out_suffix=r'_fr'
              else:
                  out_suffix=r'_en'


              abstract=feature.getAttribute('notes%s'%(out_suffix))

              list_urls_https=feature.getAttribute('urls_https{}')
              list_urls_http=feature.getAttribute('urls_http{}')
              list_urls_ftp=feature.getAttribute('urls_ftp{}')


              if list_urls_https:
                  for url in list_urls_https:
                      abstract=abstract.replace(r'$U$S%d$'%(indice_https),url)
                      indice_https=indice_https+1

              if list_urls_http:
                  for url in list_urls_http:

                      abstract=abstract.replace(r'$U$P%d$'%(indice_http),url)
                      indice_http=indice_http+1

              if list_urls_ftp:
                  for url in list_urls_ftp:

                      abstract=abstract.replace(r'$U$F%d$'%(indice_ftp),url)
                      indice_ftp=indice_ftp+1

              feature.setAttribute('notes%s'%(out_suffix),abstract)
              feature.setAttribute('_translation_problem',0)
          except:
              feature.setAttribute('_translation_problem',1)
    PYTHONSYMBOL = processFeature
    -> Tester_3
Tester_3
    BOOL_OP = OR
    COMPOSITE_TEST = 1
    TEST_CLAUSE = TEST @Value(_translation_problem) = 0
    TEST_MODE = TEST
    PASSED -> TRANSLATED (output)
    FAILED -> Tester
TRANSLATED (output)
Tester
    BOOL_OP = OR
    COMPOSITE_TEST = 1
    TEST_CLAUSE = TEST @Value(_iteration) = 10
    TEST_MODE = TEST
    PASSED -> FAILED (output)
    FAILED -> AttributeCreator
FAILED (output)
AttributeCreator
    ATTR_TABLE = SET_TO _iteration = @Evaluate(@Value(_iteration)+1)
    -> PythonCaller_2
PythonCaller_2
    PYTHONSOURCE:
      import fme
      import fmeobjects
      import time

      # Template Function interface:
      # When using this function, make sure its name is set as the value of
      # the 'Class or Function to Process Features' transformer parameter
      def processFeature(feature):
          print('Attente de 60 secondes pour essai no %d'%(feature.getAttribute('_iteration')))
          time.sleep(60)
    PYTHONSYMBOL = processFeature
    -> PythonCaller_Input (output)
PythonCaller_Input (output)
