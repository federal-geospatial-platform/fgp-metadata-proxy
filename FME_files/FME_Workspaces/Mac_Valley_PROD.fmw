FME workspace Mac_Valley_PROD.fmw
Title: NL_FGP_BUILDER_PRO
Description: Description 
This workbench read and trasform all the metadata for the province of NewFoundLand & Labrador (NL)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
P_T_ABBR: Two letter abbreviation code of the province or terrirtory (ex.: ON, QC, ...).
METADATA_OVERWRITE: Enable the overwite of the PyCSW.  Can take two values: Yes: Overwrite the contentof the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: C:\Data\PT_Harvester\QC\LOG\QC.log
OUT_JSON_LOCAL_DIR: Source directory to output JSON files. Defined as: C:\Data\PT_Harvester\QC\JSON_LOCAL
OUT_XLS_NOTIFICATION: Source directory to output excel files. Defined as: C:\Data\PT_Harvester\QC\XLS
OUT_XML_FAILED_DIR: Source directory to output failed XML files. Defined as: C:\Data\PT_Harvester\QC\XML_FAILED
OUT_XML_LOCAL_DIR: Source directory to output Local Source XML files. Defined as: C:\Data\PT_Harvester\QC\XML_LOCAL
OUT_XML_PASSED_DIR: Source directory to output passedXML files. Defined as: C:\Data\PT_Harvester\QC\XML_PASSED
SAMPLE_SIZE: Number of features to process. Zero (0) means process all the features. A number n greater than 0 means sample or process only the first n features.
URL_VALIDATION : Indicates to validate or not created URL. (Should be Yes for prod)

Parameters:
- ACTIVATE_GEO = Yes
- ACTIVATE_NON_GEO = Yes
- ACTIVATE_TRANSLATION = Yes
- CATALOGUE_READER_SELECT = Yes
- FORCED_PYCSW_URL =
- IN_FFS_TESTING_FILE =
- LOCAL_SOURCE_METADATA_DELTA_FINDER = No
- LOCAL_WRITER = No
- METADATA_OVERWRITE = NO
- IN_OUT_WORKING_DIR = C:\Data\PT_Harvester
- SAMPLE_SIZE = 0
- URL_VALIDATION = Yes
- IN_CSV_LOOKUP_TABLES_DIR = $(IN_OUT_WORKING_DIR)\LOOKUP_TABLES   # DEFAULT_IN_CSV_LOOKUP_TABLES_DIR
- IN_GMD_XML_TEMPLATE_DIR = $(IN_OUT_WORKING_DIR)\XML_TEMPLATES
- LOG_FILE = $(IN_OUT_WORKING_DIR)\$(P-T_ABBR)\LOG\$(P-T_ABBR).log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- FME_SHAREDRESOURCE_DATA = C:\Data   # FME Flow Data Directory

Writers:
- XLSXW_1: XLSXW to $(OUT_XLS_NOTIFICATION_DIR)

Bookmark: Reading NL Datasets and creating attributes
Creator
    GEOMTYPE = Geometry Object
    NUM = 1
    CREATED -> Tester_3
Tester_3
    BOOL_OP = OR
    TEST_CLAUSE = TEST $(CATALOGUE_READER_SELECT) = Yes
    TEST_MODE = TEST
    PASSED -> MV_CATALOGUE_READER
    FAILED -> FeatureReader [INITIATOR]
Note: Read pre-recorded NL catalogue data
FeatureReader
    ATTR_ACCUM_MODE = Only Use Result
    CLIP_TO_ENVELOPE = NO
    COMBINE_GEOM = Use Result
    DATASET = $(IN_FFS_TESTING_FILE)
    FFS_USE_SEARCH_ENVELOPE = NO
    FORMAT = FFS
    INITIATOR_FIRST_OUTPUT = default
    INTERACT = NONE
    ORDER_RESULTS = No
    OUTPUT_ADD_SCHEMA_ATTRIBUTES = NO
    OUTPUT_FEATURES_DISPLAY = Schema and Data Features
    <OTHER> -> ATTRIBUTE_VALUE_TEXT_CLEANER_2
    <REJECTED> -> Terminator
Terminator
    MESSAGE = Translation Terminated
Note: Read MV catalogue
MV_CATALOGUE_READER
    URL_DATASET_GEO = https://reviewboard.ca/registry
    URL_ROOT = https://reviewboard.ca
    -> ATTRIBUTE_VALUE_TEXT_CLEANER_2
    -> Recorder
Note: Clean all attribute from extra white spaces, \n, ...
ATTRIBUTE_VALUE_TEXT_CLEANER_2
    -> AttributeExposer_5
AttributeExposer_5
    ATTR_TABLE = data_collection_start_date,
Recorder
    COMPRESSION_METHOD = ZSTD
    CREATE_SPATIAL_INDEX = No
    MODE = RECORD_PASS_THROUGH
    RECFILE = $(FME_MF_DIR)NL_Catalogue_Reader.ffs
    STORE_SCANNED_METADATA = No
    STORE_SCANNED_SCHEMA = No
    ZSTD_COMPRESSION_LEVEL = 6
BROKEN_GEOHUB_URL (writer XLSXW_1)

FME custom transformer MV_CATALOGUE_READER
Description
This Custom Transformer is used to read the metadata of the NewFoundLand & Labrador open data portal.  The portal is not offering a public APi to access the metdata information so, this custom transformer is reading all the XHTML code and flatten it in order to parse it and extract the needed metadata information.  The metadata extraction is done is two passes. The first passes to extrat the name and the url of each dataset.  A second pass is done to read the complete set of  metadata of each url (one url per dataset).
Note: There is no option to read only one record with a specific identifier.
Input Ports
Input: One feature to start the extraction of all the records from the NewFoundLand & Labrador open data portal.
Output Ports
Résultats: All the records read from the NewFoundLand & Labrador open data portal
Parameters
URL_ROOT: URL of the  NewFoundLand & Labrador open data portal.
URL_DATASET_GEO: URL prefix of the metadata of the geospatial datasets.
URL_DATASET_NON_GEO: URL prefix of the metadata of the non geospatial datasets.

Parameters:
- URL_ROOT = https://reviewboard.ca/registry
- URL_DATASET_GEO = https://reviewboard.ca/registry

INPUT (input)
    -> AttributeCreator_2
OUTPUT (output)
BROKEN_URL (output)

Bookmark: Reading of the HTML catalog of Mackenzie Valley
Note: Transform puplished parameters into attributes
AttributeCreator_2
    ATTR_TABLE:
      SET_TO _url_dataset_geo = $(URL_DATASET_GEO)
      SET_TO _url_root = $(URL_ROOT)
    -> PythonCaller
Note: Read the html code from MV web site
PythonCaller
    NEW_ATTRIBUTES = _html_geo_full _html_non_geo_full _url_error
    PYTHONSOURCE:
      import fme
      import fmeobjects
      from Python.MV_CATALOGUE_READER import CatalogueReaderMacValley
    PYTHONSYMBOL = CatalogueReaderMacValley
    -> TestFilter
Note: Test if primary reading is valid
TestFilter
    DEFAULT_VALUE = Invalid URL
    PASSED_TEST_GROUP_OUTPUT = FIRST
    TEST_LIST = "BOOL_OP,OR,COMPOSITE_TEST,""""""1"""""",TEST_CLAUSE,TEST _url_error ATTRIBUTE_IS_MISSING """,Valid URL
    Valid URL -> XMLFlattener_5
    Invalid URL -> BROKEN_URL (output)
Note: Flatten the XHTMLcode (<tbody> tags)
XMLFlattener_5
    ATTRIBUTE_XML = _html_geo_full
    EMBEDDED_EXPRESSIONS = *
    FEATURE_TYPES_FORMAT_NAME = XML
    FLATTEN_OPTIONS = <structure separator="." map-empty-elements="yes" matched-prefix="attributes" matched-attributes="yes" cardinality="+{?}" structure-prefix="_html_p_" child-position-attribute="" except-expression="script" ui-mode="basic" matched-ancestor-attributes=""/>
    IGNORE_DATASET_EXTERNAL_DTD = No
    XML_SOURCE_TYPE = Attribute with XML document
    -> PythonCaller_3
Note: Read the HTML code for each of the dataset
PythonCaller_3
    NEW_ATTRIBUTES = company _html_date project code year url_suffix _html_desc _html_doc_all _html_def
    PYTHONSOURCE:
      import fme
      import fmeobjects
      from Python.MV_CATALOGUE_READER import MackenzieValleySecondary
    PYTHONSYMBOL = MackenzieValleySecondary
    -> XMLFlattener_2
Note: Flatten the geospatial XHTML code
XMLFlattener_2
    ATTRIBUTE_XML = _html_desc
    EMBEDDED_EXPRESSIONS = *
    FEATURE_TYPES_FORMAT_NAME = XML
    FLATTEN_OPTIONS = <structure separator="." map-empty-elements="yes" matched-prefix="attributes" matched-attributes="yes" cardinality="+{?}" structure-prefix="_html_pd_" child-position-attribute="" except-expression="script" ui-mode="basic" matched-ancestor-attributes=""/>
    IGNORE_DATASET_EXTERNAL_DTD = No
    XML_SOURCE_TYPE = Attribute with XML document
    -> PythonCaller_2
    <REJECTED> -> PythonCaller_2
Note: Extract information from the flatten HTML code
PythonCaller_2
    NEW_ATTRIBUTES = company project code year url_suffix _html_desc _html_ref
    PYTHONSOURCE:
      import fme
      import fmeobjects
      from Python.MV_CATALOGUE_READER import MackenzieValleyDetail
    PYTHONSYMBOL = MackenzieValleyDetail
    -> BulkAttributeRemover
Note: Remove unneeded attributes
BulkAttributeRemover
    ATTR_EXP = _html*
    -> OUTPUT (output)

FME custom transformer ON_TopicExtractor

Parameters:
- DEFAULT_TOPIC =

Topic (input)
    -> AttributeExposer_2
AttributeExposer_2
    ATTR_LIST = original_value
    -> AttributeCreator
AttributeCreator
    ATTR_TABLE:
      SET_TO _odre = 1
      SET_TO topic = @Value(original_value)
    -> Sorter
Input (input)
    -> AttributeExposer
AttributeExposer
    ATTR_LIST = keywords.en{}
    -> AttributeCreator_2
AttributeCreator_2
    ATTR_TABLE:
      SET_TO _odre = 2
      SET_TO DEFAULT_TOPIC = $(DEFAULT_TOPIC)
    -> Sorter
Sorter
    SORT_PARM = _odre NUMERIC ASCENDING
    SORTED -> PythonCaller
PythonCaller
    PYTHONSOURCE:
      import fme
      import fmeobjects
      # Template Function interface:
      # When using this function, make sure its name is set as the value of
      # the 'Class or Function to Process Features' transformer parameter


      # Template Class Interface:
      # When using this class, make sure its name is set as the value of
      # the 'Class or Function to Process Features' transformer parameter
      class FeatureProcessor(object):
          def __init__(self):
              self.topic=[]

          def input(self,feature):
              if int(feature.getAttribute('_odre'))==1:
                  #Ajouter le topic à la liste
                  self.topic.append(feature.getAttribute('topic'))

              else:

                 #Extraire le topic des keywords
                 extracted_topic=[feature.getAttribute('DEFAULT_TOPIC')]
                 feature_keywords=feature.getAttribute('keywords.en{}')

                 real_topic=False

                 for topics in self.topic:

                     if topics in feature_keywords:

                         if not real_topic:
                             #Reset de la liste pour vraie valeur
                             extracted_topic=[]
                             real_topic=True

                         extracted_topic.append(topics)

                 feature.setAttribute('extracted_topic{}.value',extracted_topic)




                 self.pyoutput(feature)
          def close(self):
              pass
    PYTHONSYMBOL = FeatureProcessor
    -> AttributeRemover
AttributeRemover
    REMOVE_ATTRS = _odre,DEFAULT_TOPIC
    -> ATTRIBUTE_UNEXPOSER
ATTRIBUTE_UNEXPOSER
    -> Output (output)
Output (output)

FME custom transformer ATTRIBUTE_VALUE_TEXT_CLEANER
Description 
This custom transformer cleans all string attributes by performing the followin tasks: 
Remove html directive (ex.: <p>bla bla bla <\p>) so that the string contains only plain text    
Replace special character (carriage return, line feed, tab) by white spaces
Replace curly braces {} by parenthesis
Removing front and trailing white spaces
Replace multiple white spaces by only one white space
Input Ports 
INPUT: The input metadata records to clean
Output Ports 
OUTPUT: The cleaned output metdata records
Parameters 
None

Input (input)
    -> PythonCaller
PythonCaller
    PYTHONSOURCE = from Python.ATTRIBUTE_VALUE_TEXT_CLEANER import *
    PYTHONSYMBOL = processFeature
    -> Output (output)
Output (output)
