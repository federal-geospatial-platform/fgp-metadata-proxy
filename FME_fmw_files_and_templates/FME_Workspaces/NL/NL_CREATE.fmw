FME workspace NL_CREATE.fmw

Parameters:
- SourceDataset_XLSXR = Z:\FME\Data\NL\NL-Datasets-Attributes.xlsx   # Source Microsoft Excel File(s)
- CSW_URL_AWS_SELECT_AB = http://ec2-35-183-211-115.ca-central-1.compute.amazonaws.com:80/csw   # CSW URL AWS
- FANOUT_DIRECTORY_PASSED = C:\Data\nl_xml_result   # Fanout Directory

Readers:
- XLSXR_1: XLSXR from $(SourceDataset_XLSXR)

Writers:
- TEXTLINE_1: TEXTLINE to $(FANOUT_DIRECTORY_PASSED)

Sheet1 (reader XLSXR_1)
    attributes: title char(144), contact_email_0 char(31), contact_email_1 char(31), contact_name_0 char(28), contact_name_1 char(28), contact_role_0 char(15), contact_role_0_fr char(9), contact_role_1 char(15), contact_role_1_fr char(9), data_collection_start_date_0 char(11), data_collection_end_date_0 date, distribution_format_0 char(10), distribution_format_version_0 char(8), distribution_format_1 char(6), distribution_format_version_1 char(8), distribution_format_2 char(4), distribution_format_version_2 char(8), west_bound_longitude number(7,2), south_bound_latitude number(6,2), graphic_link char(69), iso_topic_string char(57), metadata_standard_version string, more_info.link_0 char(92), notes char(3246), online_resource_protocol char(6), p-t_entity char(41), p-t_entity_fr char(40), p-t_license char(119), p-t_license_fr char(124), record_create_date date,
      record_last_modified date, record_publish_date date, resource_update_cycle_0 char(9), resource_format_0 char(10), resource_language_0a char(4), resource_language_0b char(4), resource_locale_0a char(5), resource_locale_0b char(5), resource_name_0 char(79), resource_protocol_0 char(6), resource_service_0a char(12), resource_service_0b char(12), resource_url_0 char(159), resource_xlink_role_0 char(21), resource_format_1 char(6), resource_language_1a char(4), resource_language_1b char(4), resource_locale_1a char(5), resource_locale_1b char(5), resource_name_1 char(79), resource_protocol_1 char(6), resource_service_1a char(12), resource_service_1b char(12), resource_url_1 char(160), resource_xlink_role_1 string, resource_format_2 char(4), resource_language_2a char(4), resource_language_2b char(4), resource_locale_2a char(5), resource_locale_2b char(5),
      resource_name_2 char(78), resource_protocol_2 char(6), resource_service_2a char(12), resource_service_2b char(12), resource_url_2 char(158), resource_xlink_role_2 string, resource_format_3 char(4), resource_language_3a char(4), resource_language_3b char(4), resource_locale_3a char(5), resource_locale_3b char(5), resource_name_3 char(78), resource_protocol_3 char(6), resource_service_3a char(12), resource_service_3b char(12), resource_url_3 char(172), resource_xlink_role_3 string, resource_format_4 char(6), resource_language_4a char(4), resource_language_4b char(4), resource_locale_4a char(5), resource_locale_4b char(5), resource_name_4 char(72), resource_protocol_4 char(6), resource_service_4a char(12), resource_service_4b char(12), resource_url_4 char(165), resource_xlink_role_4 string, resource_format_5 char(6), resource_language_5a char(4),
      resource_language_5b char(4), resource_locale_5a char(5), resource_locale_5b char(5), resource_name_5 char(63), resource_protocol_5 char(6), resource_service_5a char(12), resource_service_5b char(12), resource_url_5 char(166), resource_xlink_role_5 string, resource_format_6 char(4), resource_language_6a char(4), resource_language_6b char(4), resource_locale_6a char(5), resource_locale_6b char(5), resource_name_6 char(54), resource_protocol_6 char(6), resource_service_6a char(12), resource_service_6b char(12), resource_url_6 char(149), resource_xlink_role_6 string, resource_format_7 char(4), resource_language_7a char(4), resource_language_7b char(4), resource_locale_7a char(5), resource_locale_7b char(5), resource_name_7 char(54), resource_protocol_7 char(6), resource_service_7a char(12), resource_service_7b char(12), resource_url_7 char(124),
      resource_xlink_role_7 string, resource_format_8 char(4), resource_language_8a char(4), resource_language_8b char(4), resource_locale_8a char(5), resource_locale_8b char(5), resource_name_8 char(48), resource_protocol_8 char(6), resource_service_8a char(12), resource_service_8b char(12), resource_url_8 char(72), resource_xlink_role_8 string, RI_code_role_0 char(7), RI_code_role_1 char(7), RI_code_update char(7), RI_spatial_representation_code char(7), sector char(67), spatial_representation_type char(7), spatial_representation_type_fr char(8), tags_0 char(21), tags_1 char(25), tags_2 char(25), tags_3 char(32), tags_4 char(16), tags_5 char(16), tags_6 char(18), tags_7 char(23), tags_8 char(15), east_bound_longitude x_coordinate, north_bound_latitude y_coordinate
    -> NL_PRETRANSLATE
NL_PRETRANSLATE
    DATA_COLLECTION_END_DATE_0 = @Value(data_collection_end_date_0)
    DATA_COLLECTION_START_DATE_0 = @Value(data_collection_start_date_0)
    RECORD_CREATE_DATE = @Value(record_create_date)
    RECORD_LAST_MODIFIED = @Value(record_last_modified)
    RECORD_PUBLISH_DATE = @Value(record_publish_date)
    -> AWS_TRANSLATE
AWS_TRANSLATE
    CSW_URL_AWS_SELECT_BC = http://ec2-35-182-113-175.ca-central-1.compute.amazonaws.com:80/csw
    DEEPL_KEY = ca46773d-f5a7-d659-8c2e-41c43bad0b71
    NOTES = @Value(notes)
    RESOURCE_NAME_0 = @Value(resource_name_0)
    RESOURCE_NAME_1 = @Value(resource_name_1)
    RESOURCE_NAME_2 = @Value(resource_name_2)
    RESOURCE_NAME_3 = @Value(resource_name_3)
    RESOURCE_NAME_4 = @Value(resource_name_4)
    RESOURCE_NAME_5 = @Value(resource_name_5)
    RESOURCE_NAME_6 = @Value(resource_name_6)
    RESOURCE_NAME_7 = @Value(resource_name_7)
    RESOURCE_NAME_8 = @Value(resource_name_8)
    RESOURCE_NAME_9 = @Value(resource_name_9)
    TAGS_0 = @Value(tags_0)
    TAGS_1 = @Value(tags_1)
    TAGS_2 = @Value(tags_2)
    TAGS_3 = @Value(tags_3)
    TAGS_4 = @Value(tags_4)
    TAGS_5 = @Value(tags_5)
    TAGS_6 = @Value(tags_6)
    TAGS_7 = @Value(tags_7)
    TAGS_8 = @Value(tags_8)
    TITLE = @Value(title)
    -> NL_POSTTRANSLATE
NL_POSTTRANSLATE
    CSW_URL_AWS_SELECT_AB = http://ec2-35-183-211-115.ca-central-1.compute.amazonaws.com:80/csw
    DISTRIBUTION_FORMAT_0 = @Value(distribution_format_0)
    DISTRIBUTION_FORMAT_1 = @Value(distribution_format_1)
    DISTRIBUTION_FORMAT_2 = @Value(distribution_format_2)
    DISTRIBUTION_FORMAT_3 = @Value(distribution_format_3)
    DISTRIBUTION_FORMAT_4 = @Value(distribution_format_4)
    DISTRIBUTION_FORMAT_5 = @Value(distribution_format_5)
    METHOD = @Value(method)
    MORE_INFO.LINK_0 = @Value(more_info.link_0)
    RESOURCE_FORMAT_0 = @Value(resource_format_0)
    RESOURCE_FORMAT_2 = @Value(resource_format_2)
    RESOURCE_FORMAT_3 = @Value(resource_format_3)
    RESOURCE_FORMAT_4 = @Value(resource_format_4)
    RESOURCE_FORMAT_5 = @Value(resource_format_5)
    RESOURCE_NAME_3 = @Value(resource_name_3)
    RESOURCE_NAME_3_FR = @Value(resource_name_3_fr)
    RESOURCE_NAME_4 = @Value(resource_name_4)
    RESOURCE_NAME_4_FR = @Value(resource_name_4_fr)
    RESOURCE_NAME_5 = @Value(resource_name_5)
    RESOURCE_NAME_5_FR = @Value(resource_name_5_fr)
    RESOURCE_URL_0 = @Value(resource_url_0)
    RESOURCE_URL_1 = @Value(resource_url_1)
    RESOURCE_URL_2 = @Value(resource_url_2)
    RESOURCE_URL_3 = @Value(resource_url_3)
    RESOURCE_URL_4 = @Value(resource_url_4)
    RESOURCE_URL_5 = @Value(resource_url_5)
    SRC_LIST = resource{}.format
    TAGS_0 = @Value(tags_0)
    TAGS_0_FR = @Value(tags_0_fr)
    TAGS_1 = @Value(tags_1)
    TAGS_1_FR = @Value(tags_1_fr)
    TAGS_2 = @Value(tags_2)
    TAGS_2_FR = @Value(tags_2_fr)
    TAGS_3 = @Value(tags_3)
    TAGS_3_FR = @Value(tags_3_fr)
    TAGS_4 = @Value(tags_4)
    TAGS_4_FR = @Value(tags_4_fr)
    TAGS_5 = @Value(tags_5)
    TAGS_5_FR = @Value(tags_5_fr)
    TAGS_6 = @Value(tags_6)
    TAGS_6_FR = @Value(tags_6_fr)
    TAGS_7 = @Value(tags_7)
    TAGS_7_FR = @Value(tags_7_fr)
    TAGS_8 = @Value(tags_8)
    TAGS_8_FR = @Value(tags_8_fr)
    TITLE = @Value(title)
    TITLE_FR = @Value(title_fr)
    INSERT -> XML_CREATOR_LOCAL
XML_CREATOR_LOCAL
    CSW_URL_AWS_SELECT_AB = http://ec2-35-183-211-115.ca-central-1.compute.amazonaws.com:80/csw
    CSW_URL_AWS_SELECT_BC = http://ec2-35-182-113-175.ca-central-1.compute.amazonaws.com:80/csw
    XML_INSERT_TEMPLATE_0-0 = Z:\FME\FME_fmw_files_and_templates\XML_Templates\FGP_XML_Insert_Template_0-0.xml
    XML_INSERT_TEMPLATE_1-0 = Z:\FME\FME_fmw_files_and_templates\XML_Templates\FGP_XML_Insert_Template_1-0.xml
    XML_INSERT_TEMPLATE_1-1 = Z:\FME\FME_fmw_files_and_templates\XML_Templates\FGP_XML_Insert_Template_1-1.xml
    XML_INSERT_TEMPLATE_10-0 = Z:\FME\FME_fmw_files_and_templates\XML_Templates\FGP_XML_Insert_Template_10-0.xml
    XML_INSERT_TEMPLATE_10-1 = Z:\FME\FME_fmw_files_and_templates\XML_Templates\FGP_XML_Insert_Template_10-1.xml
    XML_INSERT_TEMPLATE_10-2 = Z:\FME\FME_fmw_files_and_templates\XML_Templates\FGP_XML_Insert_Template_10-2.xml
    XML_INSERT_TEMPLATE_10-3 = Z:\FME\FME_fmw_files_and_templates\XML_Templates\FGP_XML_Insert_Template_10-3.xml
    XML_INSERT_TEMPLATE_10-4 = Z:\FME\FME_fmw_files_and_templates\XML_Templates\FGP_XML_Insert_Template_10-4.xml
    XML_INSERT_TEMPLATE_10-5 = Z:\FME\FME_fmw_files_and_templates\XML_Templates\FGP_XML_Insert_Template_10-5.xml
    XML_INSERT_TEMPLATE_2-0 = Z:\FME\FME_fmw_files_and_templates\XML_Templates\FGP_XML_Insert_Template_2-0.xml
    XML_INSERT_TEMPLATE_2-1 = Z:\FME\FME_fmw_files_and_templates\XML_Templates\FGP_XML_Insert_Template_2-1.xml
    XML_INSERT_TEMPLATE_2-2 = Z:\FME\FME_fmw_files_and_templates\XML_Templates\FGP_XML_Insert_Template_2-2.xml
    XML_INSERT_TEMPLATE_3-0 = Z:\FME\FME_fmw_files_and_templates\XML_Templates\FGP_XML_Insert_Template_3-0.xml
    XML_INSERT_TEMPLATE_3-1 = Z:\FME\FME_fmw_files_and_templates\XML_Templates\FGP_XML_Insert_Template_3-1.xml
    XML_INSERT_TEMPLATE_3-2 = Z:\FME\FME_fmw_files_and_templates\XML_Templates\FGP_XML_Insert_Template_3-2.xml
    XML_INSERT_TEMPLATE_3-3 = Z:\FME\FME_fmw_files_and_templates\XML_Templates\FGP_XML_Insert_Template_3-3.xml
    XML_INSERT_TEMPLATE_4-0 = Z:\FME\FME_fmw_files_and_templates\XML_Templates\FGP_XML_Insert_Template_4-0.xml
    XML_INSERT_TEMPLATE_4-1 = Z:\FME\FME_fmw_files_and_templates\XML_Templates\FGP_XML_Insert_Template_4-1.xml
    XML_INSERT_TEMPLATE_4-2 = Z:\FME\FME_fmw_files_and_templates\XML_Templates\FGP_XML_Insert_Template_4-2.xml
    XML_INSERT_TEMPLATE_4-3 = Z:\FME\FME_fmw_files_and_templates\XML_Templates\FGP_XML_Insert_Template_4-3.xml
    XML_INSERT_TEMPLATE_4-4 = Z:\FME\FME_fmw_files_and_templates\XML_Templates\FGP_XML_Insert_Template_4-4.xml
    XML_INSERT_TEMPLATE_5-0 = Z:\FME\FME_fmw_files_and_templates\XML_Templates\FGP_XML_Insert_Template_5-0.xml
    XML_INSERT_TEMPLATE_5-1 = Z:\FME\FME_fmw_files_and_templates\XML_Templates\FGP_XML_Insert_Template_5-1.xml
    XML_INSERT_TEMPLATE_5-2 = Z:\FME\FME_fmw_files_and_templates\XML_Templates\FGP_XML_Insert_Template_5-2.xml
    XML_INSERT_TEMPLATE_5-3 = Z:\FME\FME_fmw_files_and_templates\XML_Templates\FGP_XML_Insert_Template_5-3.xml
    XML_INSERT_TEMPLATE_5-4 = Z:\FME\FME_fmw_files_and_templates\XML_Templates\FGP_XML_Insert_Template_5-4.xml
    XML_INSERT_TEMPLATE_5-5 = Z:\FME\FME_fmw_files_and_templates\XML_Templates\FGP_XML_Insert_Template_5-5.xml
    XML_INSERT_TEMPLATE_6-0 = Z:\FME\FME_fmw_files_and_templates\XML_Templates\FGP_XML_Insert_Template_6-0.xml
    XML_INSERT_TEMPLATE_6-1 = Z:\FME\FME_fmw_files_and_templates\XML_Templates\FGP_XML_Insert_Template_6-1.xml
    XML_INSERT_TEMPLATE_6-2 = Z:\FME\FME_fmw_files_and_templates\XML_Templates\FGP_XML_Insert_Template_6-2.xml
    XML_INSERT_TEMPLATE_6-3 = Z:\FME\FME_fmw_files_and_templates\XML_Templates\FGP_XML_Insert_Template_6-3.xml
    XML_INSERT_TEMPLATE_6-4 = Z:\FME\FME_fmw_files_and_templates\XML_Templates\FGP_XML_Insert_Template_6-4.xml
    XML_INSERT_TEMPLATE_6-5 = Z:\FME\FME_fmw_files_and_templates\XML_Templates\FGP_XML_Insert_Template_6-5.xml
    XML_INSERT_TEMPLATE_7-0 = Z:\FME\FME_fmw_files_and_templates\XML_Templates\FGP_XML_Insert_Template_7-0.xml
    XML_INSERT_TEMPLATE_7-1 = Z:\FME\FME_fmw_files_and_templates\XML_Templates\FGP_XML_Insert_Template_7-1.xml
    XML_INSERT_TEMPLATE_7-2 = Z:\FME\FME_fmw_files_and_templates\XML_Templates\FGP_XML_Insert_Template_7-2.xml
    XML_INSERT_TEMPLATE_7-3 = Z:\FME\FME_fmw_files_and_templates\XML_Templates\FGP_XML_Insert_Template_7-3.xml
    XML_INSERT_TEMPLATE_7-4 = Z:\FME\FME_fmw_files_and_templates\XML_Templates\FGP_XML_Insert_Template_7-4.xml
    XML_INSERT_TEMPLATE_7-5 = Z:\FME\FME_fmw_files_and_templates\XML_Templates\FGP_XML_Insert_Template_7-5.xml
    XML_INSERT_TEMPLATE_8-0 = Z:\FME\FME_fmw_files_and_templates\XML_Templates\FGP_XML_Insert_Template_8-0.xml
    XML_INSERT_TEMPLATE_8-1 = Z:\FME\FME_fmw_files_and_templates\XML_Templates\FGP_XML_Insert_Template_8-1.xml
    XML_INSERT_TEMPLATE_8-2 = Z:\FME\FME_fmw_files_and_templates\XML_Templates\FGP_XML_Insert_Template_8-2.xml
    XML_INSERT_TEMPLATE_8-3 = Z:\FME\FME_fmw_files_and_templates\XML_Templates\FGP_XML_Insert_Template_8-3.xml
    XML_INSERT_TEMPLATE_8-4 = Z:\FME\FME_fmw_files_and_templates\XML_Templates\FGP_XML_Insert_Template_8-4.xml
    XML_INSERT_TEMPLATE_8-5 = Z:\FME\FME_fmw_files_and_templates\XML_Templates\FGP_XML_Insert_Template_8-5.xml
    XML_INSERT_TEMPLATE_9-0 = Z:\FME\FME_fmw_files_and_templates\XML_Templates\FGP_XML_Insert_Template_9-0.xml
    XML_INSERT_TEMPLATE_9-1 = Z:\FME\FME_fmw_files_and_templates\XML_Templates\FGP_XML_Insert_Template_9-1.xml
    XML_INSERT_TEMPLATE_9-2 = Z:\FME\FME_fmw_files_and_templates\XML_Templates\FGP_XML_Insert_Template_9-2.xml
    XML_INSERT_TEMPLATE_9-3 = Z:\FME\FME_fmw_files_and_templates\XML_Templates\FGP_XML_Insert_Template_9-3.xml
    XML_INSERT_TEMPLATE_9-4 = Z:\FME\FME_fmw_files_and_templates\XML_Templates\FGP_XML_Insert_Template_9-4.xml
    XML_INSERT_TEMPLATE_9-5 = Z:\FME\FME_fmw_files_and_templates\XML_Templates\FGP_XML_Insert_Template_9-5.xml
    -> text_line (writer TEXTLINE_1)
text_line (writer TEXTLINE_1)
    attributes: text_line_data buffer
