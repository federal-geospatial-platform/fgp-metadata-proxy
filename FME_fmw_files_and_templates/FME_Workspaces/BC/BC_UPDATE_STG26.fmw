FME workspace BC_UPDATE_STG26.fmw

Parameters:
- CSW_URL = $(CSW_URL_AWS_SELECT_BC)   # CSW URL
- CSW_URL_AWS_SELECT_BC = http://ec2-35-182-113-175.ca-central-1.compute.amazonaws.com:80/csw   # CSW URL AWS
- LOOP_ITERATIONS = 10   # Enter number of loops to query source data
- P-T_ABBR = BC   # Province-Territory Abbreviation
- QUERY_ITERATIONS = 1000   # Enter number of rows per iteration to query source data
- TIME_FILTER_DAYS = 1   # Enter preceding number of days to filter
- TIME_FILTER_MONTHS = 0   # Enter preceding number of months to filter
- XML_DELETE_RECORDS_TEMPLATE = Z:\FME\FME_fmw_files_and_templates\XML_Templates\FGP_DeleteByID.xml   # Delete Template
- XML_GET_RECORDS_TEMPLATE = Z:\FME\FME_fmw_files_and_templates\XML_Templates\FGP_GetRecords.xml   # Get Records Template
- XML_INSERT_TEMPLATE_0-0 = Z:\FME\FME_fmw_files_and_templates\XML_Templates\FGP_XML_Insert_Template_0-0.xml   # Insert Template 0-0
- XML_INSERT_TEMPLATE_1-0 = Z:\FME\FME_fmw_files_and_templates\XML_Templates\FGP_XML_Insert_Template_1-0.xml   # Insert Template 1-0
- XML_INSERT_TEMPLATE_1-1 = Z:\FME\FME_fmw_files_and_templates\XML_Templates\FGP_XML_Insert_Template_1-1.xml   # Insert Template 1-1
- XML_INSERT_TEMPLATE_2-0 = Z:\FME\FME_fmw_files_and_templates\XML_Templates\FGP_XML_Insert_Template_2-0.xml   # Insert Template 2-0
- XML_INSERT_TEMPLATE_2-1 = Z:\FME\FME_fmw_files_and_templates\XML_Templates\FGP_XML_Insert_Template_2-1.xml   # Insert Template 2-1
- XML_INSERT_TEMPLATE_2-2 = Z:\FME\FME_fmw_files_and_templates\XML_Templates\FGP_XML_Insert_Template_2-2.xml   # Insert Template 2-2
- XML_INSERT_TEMPLATE_3-0 = Z:\FME\FME_fmw_files_and_templates\XML_Templates\FGP_XML_Insert_Template_3-0.xml   # Insert Template 3-0
- XML_INSERT_TEMPLATE_3-1 = Z:\FME\FME_fmw_files_and_templates\XML_Templates\FGP_XML_Insert_Template_3-1.xml   # Insert Template 3-1
- XML_INSERT_TEMPLATE_3-2 = Z:\FME\FME_fmw_files_and_templates\XML_Templates\FGP_XML_Insert_Template_3-2.xml   # Insert Template 3-2
- XML_INSERT_TEMPLATE_3-3 = Z:\FME\FME_fmw_files_and_templates\XML_Templates\FGP_XML_Insert_Template_3-3.xml   # Insert Template 3-3
- XML_INSERT_TEMPLATE_4-0 = Z:\FME\FME_fmw_files_and_templates\XML_Templates\FGP_XML_Insert_Template_4-0.xml   # Insert Template 4-0
- XML_INSERT_TEMPLATE_4-1 = Z:\FME\FME_fmw_files_and_templates\XML_Templates\FGP_XML_Insert_Template_4-1.xml   # Insert Template 4-1
- XML_INSERT_TEMPLATE_4-2 = Z:\FME\FME_fmw_files_and_templates\XML_Templates\FGP_XML_Insert_Template_4-2.xml   # Insert Template 4-2
- XML_INSERT_TEMPLATE_4-3 = Z:\FME\FME_fmw_files_and_templates\XML_Templates\FGP_XML_Insert_Template_4-3.xml   # Insert Template 4-3
- XML_INSERT_TEMPLATE_4-4 = Z:\FME\FME_fmw_files_and_templates\XML_Templates\FGP_XML_Insert_Template_4-4.xml   # Insert Template 4-4
- XML_INSERT_TEMPLATE_5-0 = Z:\FME\FME_fmw_files_and_templates\XML_Templates\FGP_XML_Insert_Template_5-0.xml   # Insert Template 5-0
- XML_INSERT_TEMPLATE_5-1 = Z:\FME\FME_fmw_files_and_templates\XML_Templates\FGP_XML_Insert_Template_5-1.xml   # Insert Template 5-1
- XML_INSERT_TEMPLATE_5-2 = Z:\FME\FME_fmw_files_and_templates\XML_Templates\FGP_XML_Insert_Template_5-2.xml   # Insert Template 5-2
- XML_INSERT_TEMPLATE_5-3 = Z:\FME\FME_fmw_files_and_templates\XML_Templates\FGP_XML_Insert_Template_5-3.xml   # Insert Template 5-3
- XML_INSERT_TEMPLATE_5-4 = Z:\FME\FME_fmw_files_and_templates\XML_Templates\FGP_XML_Insert_Template_5-4.xml   # Insert Template 5-4
- XML_INSERT_TEMPLATE_5-5 = Z:\FME\FME_fmw_files_and_templates\XML_Templates\FGP_XML_Insert_Template_5-5.xml   # Insert Template 5-5
- XML_INSERT_TEMPLATE_6-0 = Z:\FME\FME_fmw_files_and_templates\XML_Templates\FGP_XML_Insert_Template_6-0.xml   # Insert Template 6-0
- XML_INSERT_TEMPLATE_6-1 = Z:\FME\FME_fmw_files_and_templates\XML_Templates\FGP_XML_Insert_Template_6-1.xml   # Insert Template 6-1
- XML_INSERT_TEMPLATE_6-2 = Z:\FME\FME_fmw_files_and_templates\XML_Templates\FGP_XML_Insert_Template_6-2.xml   # Insert Template 6-2
- XML_INSERT_TEMPLATE_6-3 = Z:\FME\FME_fmw_files_and_templates\XML_Templates\FGP_XML_Insert_Template_6-3.xml   # Insert Template 6-3
- XML_INSERT_TEMPLATE_6-4 = Z:\FME\FME_fmw_files_and_templates\XML_Templates\FGP_XML_Insert_Template_6-4.xml   # Insert Template 6-4
- XML_INSERT_TEMPLATE_6-5 = Z:\FME\FME_fmw_files_and_templates\XML_Templates\FGP_XML_Insert_Template_6-5.xml   # Insert Template 6-5
- XML_INSERT_TEMPLATE_7-0 = Z:\FME\FME_fmw_files_and_templates\XML_Templates\FGP_XML_Insert_Template_7-0.xml   # Insert Template 7-0
- XML_INSERT_TEMPLATE_7-1 = Z:\FME\FME_fmw_files_and_templates\XML_Templates\FGP_XML_Insert_Template_7-1.xml   # Insert Template 7-1
- XML_INSERT_TEMPLATE_7-2 = Z:\FME\FME_fmw_files_and_templates\XML_Templates\FGP_XML_Insert_Template_7-2.xml   # Insert Template 7-2
- XML_INSERT_TEMPLATE_7-3 = Z:\FME\FME_fmw_files_and_templates\XML_Templates\FGP_XML_Insert_Template_7-3.xml   # Insert Template 7-3
- XML_INSERT_TEMPLATE_7-4 = Z:\FME\FME_fmw_files_and_templates\XML_Templates\FGP_XML_Insert_Template_7-4.xml   # Insert Template 7-4
- XML_INSERT_TEMPLATE_7-5 = Z:\FME\FME_fmw_files_and_templates\XML_Templates\FGP_XML_Insert_Template_7-5.xml   # Insert Template 7-5
- XML_INSERT_TEMPLATE_8-0 = Z:\FME\FME_fmw_files_and_templates\XML_Templates\FGP_XML_Insert_Template_8-0.xml   # Insert Template 8-0
- XML_INSERT_TEMPLATE_8-1 = Z:\FME\FME_fmw_files_and_templates\XML_Templates\FGP_XML_Insert_Template_8-1.xml   # Insert Template 8-1
- XML_INSERT_TEMPLATE_8-2 = Z:\FME\FME_fmw_files_and_templates\XML_Templates\FGP_XML_Insert_Template_8-2.xml   # Insert Template 8-2
- XML_INSERT_TEMPLATE_8-3 = Z:\FME\FME_fmw_files_and_templates\XML_Templates\FGP_XML_Insert_Template_8-3.xml   # Insert Template 8-3
- XML_INSERT_TEMPLATE_8-4 = Z:\FME\FME_fmw_files_and_templates\XML_Templates\FGP_XML_Insert_Template_8-4.xml   # Insert Template 8-4
- XML_INSERT_TEMPLATE_8-5 = Z:\FME\FME_fmw_files_and_templates\XML_Templates\FGP_XML_Insert_Template_8-5.xml   # Insert Template 8-5
- XML_INSERT_TEMPLATE_9-0 = Z:\FME\FME_fmw_files_and_templates\XML_Templates\FGP_XML_Insert_Template_9-0.xml   # Insert Template 9-0
- XML_INSERT_TEMPLATE_9-1 = Z:\FME\FME_fmw_files_and_templates\XML_Templates\FGP_XML_Insert_Template_9-1.xml   # Insert Template 9-1
- XML_INSERT_TEMPLATE_9-2 = Z:\FME\FME_fmw_files_and_templates\XML_Templates\FGP_XML_Insert_Template_9-2.xml   # Insert Template 9-2
- XML_INSERT_TEMPLATE_9-3 = Z:\FME\FME_fmw_files_and_templates\XML_Templates\FGP_XML_Insert_Template_9-3.xml   # Insert Template 9-3
- XML_INSERT_TEMPLATE_9-4 = Z:\FME\FME_fmw_files_and_templates\XML_Templates\FGP_XML_Insert_Template_9-4.xml   # Insert Template 9-4
- XML_INSERT_TEMPLATE_9-5 = Z:\FME\FME_fmw_files_and_templates\XML_Templates\FGP_XML_Insert_Template_9-5.xml   # Insert Template 9-5
- XML_INSERT_TEMPLATE_10-0 = Z:\FME\FME_fmw_files_and_templates\XML_Templates\FGP_XML_Insert_Template_10-0.xml   # Select XML Insert Template
- XML_INSERT_TEMPLATE_10-1 = Z:\FME\FME_fmw_files_and_templates\XML_Templates\FGP_XML_Insert_Template_10-1.xml   # Select XML Insert Template
- XML_INSERT_TEMPLATE_10-2 = Z:\FME\FME_fmw_files_and_templates\XML_Templates\FGP_XML_Insert_Template_10-2.xml   # Select XML Insert Template
- XML_INSERT_TEMPLATE_10-3 = Z:\FME\FME_fmw_files_and_templates\XML_Templates\FGP_XML_Insert_Template_10-3.xml   # Select XML Insert Template
- XML_INSERT_TEMPLATE_10-4 = Z:\FME\FME_fmw_files_and_templates\XML_Templates\FGP_XML_Insert_Template_10-4.xml   # Select XML Insert Template
- XML_INSERT_TEMPLATE_10-5 = Z:\FME\FME_fmw_files_and_templates\XML_Templates\FGP_XML_Insert_Template_10-5.xml   # Select XML Insert Template
- XML_UPDATE_TEMPLATE_0-0 = Z:\FME\FME_fmw_files_and_templates\XML_Templates\FGP_XML_Update_Template_0-0.xml   # Update Template 0-0
- XML_UPDATE_TEMPLATE_1-0 = Z:\FME\FME_fmw_files_and_templates\XML_Templates\FGP_XML_Update_Template_1-0.xml   # Update Template 1-0
- XML_UPDATE_TEMPLATE_1-1 = Z:\FME\FME_fmw_files_and_templates\XML_Templates\FGP_XML_Update_Template_1-1.xml   # Update Template 1-1
- XML_UPDATE_TEMPLATE_2-0 = Z:\FME\FME_fmw_files_and_templates\XML_Templates\FGP_XML_Update_Template_2-0.xml   # Update Template 2-0
- XML_UPDATE_TEMPLATE_2-1 = Z:\FME\FME_fmw_files_and_templates\XML_Templates\FGP_XML_Update_Template_2-1.xml   # Update Template 2-1
- XML_UPDATE_TEMPLATE_2-2 = Z:\FME\FME_fmw_files_and_templates\XML_Templates\FGP_XML_Update_Template_2-2.xml   # Update Template 2-2
- XML_UPDATE_TEMPLATE_3-0 = Z:\FME\FME_fmw_files_and_templates\XML_Templates\FGP_XML_Update_Template_3-0.xml   # Update Template 3-0
- XML_UPDATE_TEMPLATE_3-1 = Z:\FME\FME_fmw_files_and_templates\XML_Templates\FGP_XML_Update_Template_3-1.xml   # Update Template 3-1
- XML_UPDATE_TEMPLATE_3-2 = Z:\FME\FME_fmw_files_and_templates\XML_Templates\FGP_XML_Update_Template_3-2.xml   # Update Template 3-2
- XML_UPDATE_TEMPLATE_3-3 = Z:\FME\FME_fmw_files_and_templates\XML_Templates\FGP_XML_Update_Template_3-3.xml   # Update Template 3-3
- XML_UPDATE_TEMPLATE_4-0 = Z:\FME\FME_fmw_files_and_templates\XML_Templates\FGP_XML_Update_Template_4-0.xml   # Update Template 4-0
- XML_UPDATE_TEMPLATE_4-1 = Z:\FME\FME_fmw_files_and_templates\XML_Templates\FGP_XML_Update_Template_4-1.xml   # Update Template 4-1
- XML_UPDATE_TEMPLATE_4-2 = Z:\FME\FME_fmw_files_and_templates\XML_Templates\FGP_XML_Update_Template_4-2.xml   # Update Template 4-2
- XML_UPDATE_TEMPLATE_4-3 = Z:\FME\FME_fmw_files_and_templates\XML_Templates\FGP_XML_Update_Template_4-3.xml   # Update Template 4-3
- XML_UPDATE_TEMPLATE_4-4 = Z:\FME\FME_fmw_files_and_templates\XML_Templates\FGP_XML_Update_Template_4-4.xml   # Update Template 4-4
- XML_UPDATE_TEMPLATE_5-0 = Z:\FME\FME_fmw_files_and_templates\XML_Templates\FGP_XML_Update_Template_5-0.xml   # Update Template 5-0
- XML_UPDATE_TEMPLATE_5-1 = Z:\FME\FME_fmw_files_and_templates\XML_Templates\FGP_XML_Update_Template_5-1.xml   # Update Template 5-1
- XML_UPDATE_TEMPLATE_5-2 = Z:\FME\FME_fmw_files_and_templates\XML_Templates\FGP_XML_Update_Template_5-2.xml   # Update Template 5-2
- XML_UPDATE_TEMPLATE_5-3 = Z:\FME\FME_fmw_files_and_templates\XML_Templates\FGP_XML_Update_Template_5-3.xml   # Update Template 5-3
- XML_UPDATE_TEMPLATE_5-4 = Z:\FME\FME_fmw_files_and_templates\XML_Templates\FGP_XML_Update_Template_5-4.xml   # Update Template 5-4
- XML_UPDATE_TEMPLATE_5-5 = Z:\FME\FME_fmw_files_and_templates\XML_Templates\FGP_XML_Update_Template_5-5.xml   # Update Template 5-5
- XML_UPDATE_TEMPLATE_6-0 = Z:\FME\FME_fmw_files_and_templates\XML_Templates\FGP_XML_Update_Template_6-0.xml   # Update Template 6-0
- XML_UPDATE_TEMPLATE_6-1 = Z:\FME\FME_fmw_files_and_templates\XML_Templates\FGP_XML_Update_Template_6-1.xml   # Update Template 6-1
- XML_UPDATE_TEMPLATE_6-2 = Z:\FME\FME_fmw_files_and_templates\XML_Templates\FGP_XML_Update_Template_6-2.xml   # Update Template 6-2
- XML_UPDATE_TEMPLATE_6-3 = Z:\FME\FME_fmw_files_and_templates\XML_Templates\FGP_XML_Update_Template_6-3.xml   # Update Template 6-3
- XML_UPDATE_TEMPLATE_6-4 = Z:\FME\FME_fmw_files_and_templates\XML_Templates\FGP_XML_Update_Template_6-4.xml   # Update Template 6-4
- XML_UPDATE_TEMPLATE_6-5 = Z:\FME\FME_fmw_files_and_templates\XML_Templates\FGP_XML_Update_Template_6-5.xml   # Update Template 6-5
- XML_UPDATE_TEMPLATE_7-0 = Z:\FME\FME_fmw_files_and_templates\XML_Templates\FGP_XML_Update_Template_7-0.xml   # Update Template 7-0
- XML_UPDATE_TEMPLATE_7-1 = Z:\FME\FME_fmw_files_and_templates\XML_Templates\FGP_XML_Update_Template_7-1.xml   # Update Template 7-1
- XML_UPDATE_TEMPLATE_7-2 = Z:\FME\FME_fmw_files_and_templates\XML_Templates\FGP_XML_Update_Template_7-2.xml   # Update Template 7-2
- XML_UPDATE_TEMPLATE_7-3 = Z:\FME\FME_fmw_files_and_templates\XML_Templates\FGP_XML_Update_Template_7-3.xml   # Update Template 7-3
- XML_UPDATE_TEMPLATE_7-4 = Z:\FME\FME_fmw_files_and_templates\XML_Templates\FGP_XML_Update_Template_7-4.xml   # Update Template 7-4
- XML_UPDATE_TEMPLATE_7-5 = Z:\FME\FME_fmw_files_and_templates\XML_Templates\FGP_XML_Update_Template_7-5.xml   # Update Template 7-5
- XML_UPDATE_TEMPLATE_8-0 = Z:\FME\FME_fmw_files_and_templates\XML_Templates\FGP_XML_Update_Template_8-0.xml   # Update Template 8-0
- XML_UPDATE_TEMPLATE_8-1 = Z:\FME\FME_fmw_files_and_templates\XML_Templates\FGP_XML_Update_Template_8-1.xml   # Update Template 8-1
- XML_UPDATE_TEMPLATE_8-2 = Z:\FME\FME_fmw_files_and_templates\XML_Templates\FGP_XML_Update_Template_8-2.xml   # Update Template 8-2
- XML_UPDATE_TEMPLATE_8-3 = Z:\FME\FME_fmw_files_and_templates\XML_Templates\FGP_XML_Update_Template_8-3.xml   # Update Template 8-3
- XML_UPDATE_TEMPLATE_8-4 = Z:\FME\FME_fmw_files_and_templates\XML_Templates\FGP_XML_Update_Template_8-4.xml   # Update Template 8-4
- XML_UPDATE_TEMPLATE_8-5 = Z:\FME\FME_fmw_files_and_templates\XML_Templates\FGP_XML_Update_Template_8-5.xml   # Update Template 8-5
- XML_UPDATE_TEMPLATE_9-0 = Z:\FME\FME_fmw_files_and_templates\XML_Templates\FGP_XML_Update_Template_9-0.xml   # Update Template 9-0
- XML_UPDATE_TEMPLATE_9-1 = Z:\FME\FME_fmw_files_and_templates\XML_Templates\FGP_XML_Update_Template_9-1.xml   # Update Template 9-1
- XML_UPDATE_TEMPLATE_9-2 = Z:\FME\FME_fmw_files_and_templates\XML_Templates\FGP_XML_Update_Template_9-2.xml   # Update Template 9-2
- XML_UPDATE_TEMPLATE_9-3 = Z:\FME\FME_fmw_files_and_templates\XML_Templates\FGP_XML_Update_Template_9-3.xml   # Update Template 9-3
- XML_UPDATE_TEMPLATE_9-4 = Z:\FME\FME_fmw_files_and_templates\XML_Templates\FGP_XML_Update_Template_9-4.xml   # Update Template 9-4
- XML_UPDATE_TEMPLATE_9-5 = Z:\FME\FME_fmw_files_and_templates\XML_Templates\FGP_XML_Update_Template_9-5.xml   # Update Template 9-5
- XML_UPDATE_TEMPLATE_10-0 = Z:\FME\FME_fmw_files_and_templates\XML_Templates\FGP_XML_Update_Template_10-0.xml   # Update Template 10-0
- XML_UPDATE_TEMPLATE_10-1 = Z:\FME\FME_fmw_files_and_templates\XML_Templates\FGP_XML_Update_Template_10-1.xml   # Update Template 10-1
- XML_UPDATE_TEMPLATE_10-2 = Z:\FME\FME_fmw_files_and_templates\XML_Templates\FGP_XML_Update_Template_10-2.xml   # Update Template 10-2
- XML_UPDATE_TEMPLATE_10-3 = Z:\FME\FME_fmw_files_and_templates\XML_Templates\FGP_XML_Update_Template_10-3.xml   # Update Template 10-3
- XML_UPDATE_TEMPLATE_10-4 = Z:\FME\FME_fmw_files_and_templates\XML_Templates\FGP_XML_Update_Template_10-4.xml   # Update Template 10-4
- XML_UPDATE_TEMPLATE_10-5 = Z:\FME\FME_fmw_files_and_templates\XML_Templates\FGP_XML_Update_Template_10-5.xml   # Update Template 10-5

Note: Initiates instance of tool
Note: This FME Workspace is for daily extraction of new or updated data from the BC Data API, and inserting to the CSW. / It also tests for and removes invalid records in the CSW. / It is intended to run on FME Server on a once daily schedule.
Creator
    GEOMTYPE = Geometry Object
    NUM = 1
    CREATED -> BC_UPDATE_PRETRANSLATE [CSW_QUERY]
    CREATED -> BC_UPDATE_PRETRANSLATE [API_QUERY]
Note: Custom transformer queries the British Columbia open government portal API and exposes returned attributes and filters data by open, geospatial data and date.
BC_UPDATE_PRETRANSLATE
    LOOP_ITERATIONS = $(LOOP_ITERATIONS)
    QUERY_ITERATIONS = $(QUERY_ITERATIONS)
    TIME_FILTER_DAYS = $(TIME_FILTER_DAYS)
    TIME_FILTER_MONTHS = $(TIME_FILTER_MONTHS)
    XML_DELETE_RECORDS_TEMPLATE = $(XML_DELETE_RECORDS_TEMPLATE)
    XML_GET_RECORDS_TEMPLATE = $(XML_GET_RECORDS_TEMPLATE)
    NO_DELETED_RECORDS_COUNT -> NOTIFY_UPDATE [NO_RECORDS_DELETED_COUNT]
    DELETED_RECORDS_COUNT -> NOTIFY_UPDATE [RECORDS_DELETED_COUNT]
    -> AWS_TRANSLATE
    NEW_RECORDS_COUNT -> NOTIFY_UPDATE [NEW_RECORDS_COUNT]
    UPDATED_RECORDS_COUNT -> NOTIFY_UPDATE [UPDATED_RECORDS_COUNT]
    TOTAL_RECORDS_COUNT -> NOTIFY_UPDATE [TOTAL_RECORDS_COUNT]
Note: Custom transformer sends specific extracted attributes to the Amazon translation service to be translated to French.
AWS_TRANSLATE
    CSW_URL_AWS_SELECT_BC = http://ec2-35-182-113-175.ca-central-1.compute.amazonaws.com:80/csw
    DEEPL_KEY = ca46773d-f5a7-d659-8c2e-41c43bad0b71
    NOTES = @Value(notes)
    RESOURCE_NAME_0 = @Value(resource_name_0)
    RESOURCE_NAME_1 = @Value(resource_name_1)
    RESOURCE_NAME_2 = @Value(resource_name_2)
    RESOURCE_NAME_3 = @Value(resource_name_3)
    RESOURCE_NAME_4 = @Value(resource_name_4)
    RESOURCE_NAME_5 = @Value(resource_name_5)
    RESOURCE_NAME_6 = @Value(resource_name_6)
    RESOURCE_NAME_7 = @Value(resource_name_7)
    RESOURCE_NAME_8 = @Value(resource_name_8)
    RESOURCE_NAME_9 = @Value(resource_name_9)
    TAGS_0 = @Value(tags_0)
    TAGS_1 = @Value(tags_1)
    TAGS_2 = @Value(tags_2)
    TAGS_3 = @Value(tags_3)
    TAGS_4 = @Value(tags_4)
    TAGS_5 = @Value(tags_5)
    TAGS_6 = @Value(tags_6)
    TAGS_7 = @Value(tags_7)
    TAGS_8 = @Value(tags_8)
    TITLE = @Value(title)
    -> BC_POSTTRANSLATE_1
Note: Custom transformer performs post translation functions to ensure conformity to ISO 19115 HNAP requirements
BC_POSTTRANSLATE_1
    CONTACT_EMAIL_0 = @Value(contact_email_0)
    CONTACT_NAME_0 = @Value(contact_name_0)
    CONTACT_ROLE_0 = @Value(contact_role_0)
    CONTACT_ROLE_1 = @Value(contact_role_1)
    CSW_URL_AWS_SELECT_BC = $(CSW_URL)
    DATA_COLLECTION_END_DATE_0 = @Value(data_collection_end_date_0)
    RESOURCE_UPDATE_CYCLE_0 = @Value(resource_update_cycle_0)
    -> BC_POSTTRANSLATE_2
Note: Custom transformer performs post translation functions to ensure conformity to ISO 19115 HNAP requirements
BC_POSTTRANSLATE_2
    CSW_URL_AWS_SELECT_BC = $(CSW_URL)
    RESOURCE_FORMAT_0 = @Value(resource_format_0)
    RESOURCE_FORMAT_1 = @Value(resource_format_1)
    RESOURCE_FORMAT_2 = @Value(resource_format_2)
    RESOURCE_FORMAT_3 = @Value(resource_format_3)
    RESOURCE_FORMAT_4 = @Value(resource_format_4)
    RESOURCE_FORMAT_5 = @Value(resource_format_5)
    RESOURCE_FORMAT_6 = @Value(resource_format_6)
    RESOURCE_FORMAT_7 = @Value(resource_format_7)
    RESOURCE_FORMAT_8 = @Value(resource_format_8)
    RESOURCE_FORMAT_9 = @Value(resource_format_9)
    -> POSTTRANSLATE_3
Note: Custom transformer performs post translation functions to ensure conformity to ISO 19115 HNAP requirements
POSTTRANSLATE_3
    CSW_URL_AWS_SELECT_BC = http://ec2-35-182-113-175.ca-central-1.compute.amazonaws.com:80/csw
    SRC_LIST = resource{}.format
    -> BC_POSTTRANSLATE_4
Note: Custom transformer performs post translation functions to ensure conformity to ISO 19115 HNAP requirements
BC_POSTTRANSLATE_4
    CSW_URL_AWS_SELECT_BC = $(CSW_URL)
    DISTRIBUTION_FORMAT_0 = @Value(distribution_format_0)
    DISTRIBUTION_FORMAT_1 = @Value(distribution_format_1)
    DISTRIBUTION_FORMAT_2 = @Value(distribution_format_2)
    DISTRIBUTION_FORMAT_3 = @Value(distribution_format_3)
    DISTRIBUTION_FORMAT_4 = @Value(distribution_format_4)
    DISTRIBUTION_FORMAT_5 = @Value(distribution_format_5)
    METHOD = @Value(method)
    MORE_INFO.LINK_0 = @Value(more_info.link_0)
    OBJECT_NAME = @Value(object_name)
    RESOURCE_FORMAT_0 = @Value(resource_format_0)
    RESOURCE_FORMAT_1 = @Value(resource_format_1)
    RESOURCE_FORMAT_2 = @Value(resource_format_2)
    RESOURCE_FORMAT_3 = @Value(resource_format_3)
    RESOURCE_FORMAT_4 = @Value(resource_format_4)
    RESOURCE_FORMAT_5 = @Value(resource_format_5)
    RESOURCE_FORMAT_6 = @Value(resource_format_6)
    RESOURCE_FORMAT_7 = @Value(resource_format_7)
    RESOURCE_FORMAT_8 = @Value(resource_format_8)
    RESOURCE_FORMAT_9 = @Value(resource_format_9)
    RESOURCE_NAME_1 = @Value(resource_name_1)
    RESOURCE_NAME_1_FR = @Value(resource_name_1_fr)
    RESOURCE_NAME_2 = @Value(resource_name_2)
    RESOURCE_NAME_2_FR = @Value(resource_name_2_fr)
    RESOURCE_NAME_3 = @Value(resource_name_3)
    RESOURCE_NAME_3_FR = @Value(resource_name_3_fr)
    RESOURCE_NAME_4 = @Value(resource_name_4)
    RESOURCE_NAME_4_FR = @Value(resource_name_4_fr)
    RESOURCE_NAME_5 = @Value(resource_name_5)
    RESOURCE_NAME_5_FR = @Value(resource_name_5_fr)
    RESOURCE_NAME_6 = @Value(resource_name_6)
    RESOURCE_NAME_6_FR = @Value(resource_name_6_fr)
    RESOURCE_NAME_7 = @Value(resource_name_7)
    RESOURCE_NAME_7_FR = @Value(resource_name_7_fr)
    RESOURCE_NAME_8 = @Value(resource_name_8)
    RESOURCE_NAME_8_FR = @Value(resource_name_8_fr)
    RESOURCE_NAME_9 = @Value(resource_name_9)
    RESOURCE_NAME_9_FR = @Value(resource_name_9_fr)
    RESOURCE_URL_0 = @Value(resource_url_0)
    RESOURCE_URL_1 = @Value(resource_url_1)
    RESOURCE_URL_2 = @Value(resource_url_2)
    RESOURCE_URL_3 = @Value(resource_url_3)
    RESOURCE_URL_4 = @Value(resource_url_4)
    RESOURCE_URL_5 = @Value(resource_url_5)
    RESOURCE_URL_6 = @Value(resource_url_6)
    RESOURCE_URL_7 = @Value(resource_url_7)
    RESOURCE_URL_8 = @Value(resource_url_8)
    RESOURCE_URL_9 = @Value(resource_url_9)
    TAGS_0 = @Value(tags_0)
    TAGS_0_FR = @Value(tags_0_fr)
    TAGS_1 = @Value(tags_1)
    TAGS_1_FR = @Value(tags_1_fr)
    TAGS_2 = @Value(tags_2)
    TAGS_2_FR = @Value(tags_2_fr)
    TAGS_3 = @Value(tags_3)
    TAGS_3_FR = @Value(tags_3_fr)
    TAGS_4 = @Value(tags_4)
    TAGS_4_FR = @Value(tags_4_fr)
    TAGS_5 = @Value(tags_5)
    TAGS_5_FR = @Value(tags_5_fr)
    TAGS_6 = @Value(tags_6)
    TAGS_6_FR = @Value(tags_6_fr)
    TAGS_7 = @Value(tags_7)
    TAGS_7_FR = @Value(tags_7_fr)
    TAGS_8 = @Value(tags_8)
    TAGS_8_FR = @Value(tags_8_fr)
    TITLE = @Value(title)
    TITLE_FR = @Value(title_fr)
    INSERT -> CSW_INSERT
    UPDATE -> CSW_UPDATE
Note: Custom transformer selects appropriate XML insert template and posts XML to the CSW
CSW_INSERT
    CSW_URL_AWS_SELECT_BC = http://ec2-35-182-113-175.ca-central-1.compute.amazonaws.com:80/csw
    XML_INSERT_TEMPLATE_0-0 = $(XML_INSERT_TEMPLATE_0-0)
    XML_INSERT_TEMPLATE_1-0 = $(XML_INSERT_TEMPLATE_1-0)
    XML_INSERT_TEMPLATE_1-1 = $(XML_INSERT_TEMPLATE_1-1)
    XML_INSERT_TEMPLATE_10-0 = $(XML_INSERT_TEMPLATE_10-0)
    XML_INSERT_TEMPLATE_10-1 = $(XML_INSERT_TEMPLATE_10-1)
    XML_INSERT_TEMPLATE_10-2 = $(XML_INSERT_TEMPLATE_10-2)
    XML_INSERT_TEMPLATE_10-3 = $(XML_INSERT_TEMPLATE_10-3)
    XML_INSERT_TEMPLATE_10-4 = $(XML_INSERT_TEMPLATE_10-4)
    XML_INSERT_TEMPLATE_10-5 = $(XML_INSERT_TEMPLATE_10-5)
    XML_INSERT_TEMPLATE_2-0 = $(XML_INSERT_TEMPLATE_2-0)
    XML_INSERT_TEMPLATE_2-1 = $(XML_INSERT_TEMPLATE_2-1)
    XML_INSERT_TEMPLATE_2-2 = $(XML_INSERT_TEMPLATE_2-2)
    XML_INSERT_TEMPLATE_3-0 = $(XML_INSERT_TEMPLATE_3-0)
    XML_INSERT_TEMPLATE_3-1 = $(XML_INSERT_TEMPLATE_3-1)
    XML_INSERT_TEMPLATE_3-2 = $(XML_INSERT_TEMPLATE_3-2)
    XML_INSERT_TEMPLATE_3-3 = $(XML_INSERT_TEMPLATE_3-3)
    XML_INSERT_TEMPLATE_4-0 = $(XML_INSERT_TEMPLATE_4-0)
    XML_INSERT_TEMPLATE_4-1 = $(XML_INSERT_TEMPLATE_4-1)
    XML_INSERT_TEMPLATE_4-2 = $(XML_INSERT_TEMPLATE_4-2)
    XML_INSERT_TEMPLATE_4-3 = $(XML_INSERT_TEMPLATE_4-3)
    XML_INSERT_TEMPLATE_4-4 = $(XML_INSERT_TEMPLATE_4-4)
    XML_INSERT_TEMPLATE_5-0 = $(XML_INSERT_TEMPLATE_5-0)
    XML_INSERT_TEMPLATE_5-1 = $(XML_INSERT_TEMPLATE_5-1)
    XML_INSERT_TEMPLATE_5-2 = $(XML_INSERT_TEMPLATE_5-2)
    XML_INSERT_TEMPLATE_5-3 = $(XML_INSERT_TEMPLATE_5-3)
    XML_INSERT_TEMPLATE_5-4 = $(XML_INSERT_TEMPLATE_5-4)
    XML_INSERT_TEMPLATE_5-5 = $(XML_INSERT_TEMPLATE_5-5)
    XML_INSERT_TEMPLATE_6-0 = $(XML_INSERT_TEMPLATE_6-0)
    XML_INSERT_TEMPLATE_6-1 = $(XML_INSERT_TEMPLATE_6-1)
    XML_INSERT_TEMPLATE_6-2 = $(XML_INSERT_TEMPLATE_6-2)
    XML_INSERT_TEMPLATE_6-3 = $(XML_INSERT_TEMPLATE_6-3)
    XML_INSERT_TEMPLATE_6-4 = $(XML_INSERT_TEMPLATE_6-4)
    XML_INSERT_TEMPLATE_6-5 = $(XML_INSERT_TEMPLATE_6-5)
    XML_INSERT_TEMPLATE_7-0 = $(XML_INSERT_TEMPLATE_7-0)
    XML_INSERT_TEMPLATE_7-1 = $(XML_INSERT_TEMPLATE_7-1)
    XML_INSERT_TEMPLATE_7-2 = $(XML_INSERT_TEMPLATE_7-2)
    XML_INSERT_TEMPLATE_7-3 = $(XML_INSERT_TEMPLATE_7-3)
    XML_INSERT_TEMPLATE_7-4 = $(XML_INSERT_TEMPLATE_7-4)
    XML_INSERT_TEMPLATE_7-5 = $(XML_INSERT_TEMPLATE_7-5)
    XML_INSERT_TEMPLATE_8-0 = $(XML_INSERT_TEMPLATE_8-0)
    XML_INSERT_TEMPLATE_8-1 = $(XML_INSERT_TEMPLATE_8-1)
    XML_INSERT_TEMPLATE_8-2 = $(XML_INSERT_TEMPLATE_8-2)
    XML_INSERT_TEMPLATE_8-3 = $(XML_INSERT_TEMPLATE_8-3)
    XML_INSERT_TEMPLATE_8-4 = $(XML_INSERT_TEMPLATE_8-4)
    XML_INSERT_TEMPLATE_8-5 = $(XML_INSERT_TEMPLATE_8-5)
    XML_INSERT_TEMPLATE_9-0 = $(XML_INSERT_TEMPLATE_9-0)
    XML_INSERT_TEMPLATE_9-1 = $(XML_INSERT_TEMPLATE_9-1)
    XML_INSERT_TEMPLATE_9-2 = $(XML_INSERT_TEMPLATE_9-2)
    XML_INSERT_TEMPLATE_9-3 = $(XML_INSERT_TEMPLATE_9-3)
    XML_INSERT_TEMPLATE_9-4 = $(XML_INSERT_TEMPLATE_9-4)
    XML_INSERT_TEMPLATE_9-5 = $(XML_INSERT_TEMPLATE_9-5)
    INSERTED -> NOTIFY_UPDATE [INSERTED]
    INSERT_REJECTED -> NOTIFY_UPDATE [INSERT_REJECTED]
Note: Custom transformer selects appropriate XML update template and posts XML to the CSW
CSW_UPDATE
    XML_UPDATE_TEMPLATE_0-0 = $(XML_UPDATE_TEMPLATE_0-0)
    XML_UPDATE_TEMPLATE_1-0 = $(XML_UPDATE_TEMPLATE_1-0)
    XML_UPDATE_TEMPLATE_1-1 = $(XML_UPDATE_TEMPLATE_1-1)
    XML_UPDATE_TEMPLATE_10-0 = $(XML_UPDATE_TEMPLATE_10-0)
    XML_UPDATE_TEMPLATE_10-1 = $(XML_UPDATE_TEMPLATE_10-1)
    XML_UPDATE_TEMPLATE_10-2 = $(XML_UPDATE_TEMPLATE_10-2)
    XML_UPDATE_TEMPLATE_10-3 = $(XML_UPDATE_TEMPLATE_10-3)
    XML_UPDATE_TEMPLATE_10-4 = $(XML_UPDATE_TEMPLATE_10-4)
    XML_UPDATE_TEMPLATE_10-5 = $(XML_UPDATE_TEMPLATE_10-5)
    XML_UPDATE_TEMPLATE_2-0 = $(XML_UPDATE_TEMPLATE_2-0)
    XML_UPDATE_TEMPLATE_2-1 = $(XML_UPDATE_TEMPLATE_2-1)
    XML_UPDATE_TEMPLATE_2-2 = $(XML_UPDATE_TEMPLATE_2-2)
    XML_UPDATE_TEMPLATE_3-0 = $(XML_UPDATE_TEMPLATE_3-0)
    XML_UPDATE_TEMPLATE_3-1 = $(XML_UPDATE_TEMPLATE_3-1)
    XML_UPDATE_TEMPLATE_3-2 = $(XML_UPDATE_TEMPLATE_3-2)
    XML_UPDATE_TEMPLATE_3-3 = $(XML_UPDATE_TEMPLATE_3-3)
    XML_UPDATE_TEMPLATE_4-0 = $(XML_UPDATE_TEMPLATE_4-0)
    XML_UPDATE_TEMPLATE_4-1 = $(XML_UPDATE_TEMPLATE_4-1)
    XML_UPDATE_TEMPLATE_4-2 = $(XML_UPDATE_TEMPLATE_4-2)
    XML_UPDATE_TEMPLATE_4-3 = $(XML_UPDATE_TEMPLATE_4-3)
    XML_UPDATE_TEMPLATE_4-4 = $(XML_UPDATE_TEMPLATE_4-4)
    XML_UPDATE_TEMPLATE_5-0 = $(XML_UPDATE_TEMPLATE_5-0)
    XML_UPDATE_TEMPLATE_5-1 = $(XML_UPDATE_TEMPLATE_5-1)
    XML_UPDATE_TEMPLATE_5-2 = $(XML_UPDATE_TEMPLATE_5-2)
    XML_UPDATE_TEMPLATE_5-3 = $(XML_UPDATE_TEMPLATE_5-3)
    XML_UPDATE_TEMPLATE_5-4 = $(XML_UPDATE_TEMPLATE_5-4)
    XML_UPDATE_TEMPLATE_5-5 = $(XML_UPDATE_TEMPLATE_5-5)
    XML_UPDATE_TEMPLATE_6-0 = $(XML_UPDATE_TEMPLATE_6-0)
    XML_UPDATE_TEMPLATE_6-1 = $(XML_UPDATE_TEMPLATE_6-1)
    XML_UPDATE_TEMPLATE_6-2 = $(XML_UPDATE_TEMPLATE_6-2)
    XML_UPDATE_TEMPLATE_6-3 = $(XML_UPDATE_TEMPLATE_6-3)
    XML_UPDATE_TEMPLATE_6-4 = $(XML_UPDATE_TEMPLATE_6-4)
    XML_UPDATE_TEMPLATE_6-5 = $(XML_UPDATE_TEMPLATE_6-5)
    XML_UPDATE_TEMPLATE_7-0 = $(XML_UPDATE_TEMPLATE_7-0)
    XML_UPDATE_TEMPLATE_7-1 = $(XML_UPDATE_TEMPLATE_7-1)
    XML_UPDATE_TEMPLATE_7-2 = $(XML_UPDATE_TEMPLATE_7-2)
    XML_UPDATE_TEMPLATE_7-3 = $(XML_UPDATE_TEMPLATE_7-3)
    XML_UPDATE_TEMPLATE_7-4 = $(XML_UPDATE_TEMPLATE_7-4)
    XML_UPDATE_TEMPLATE_7-5 = $(XML_UPDATE_TEMPLATE_7-5)
    XML_UPDATE_TEMPLATE_8-0 = $(XML_UPDATE_TEMPLATE_8-0)
    XML_UPDATE_TEMPLATE_8-1 = $(XML_UPDATE_TEMPLATE_8-1)
    XML_UPDATE_TEMPLATE_8-2 = $(XML_UPDATE_TEMPLATE_8-2)
    XML_UPDATE_TEMPLATE_8-3 = $(XML_UPDATE_TEMPLATE_8-3)
    XML_UPDATE_TEMPLATE_8-4 = $(XML_UPDATE_TEMPLATE_8-4)
    XML_UPDATE_TEMPLATE_8-5 = $(XML_UPDATE_TEMPLATE_8-5)
    XML_UPDATE_TEMPLATE_9-0 = $(XML_UPDATE_TEMPLATE_9-0)
    XML_UPDATE_TEMPLATE_9-1 = $(XML_UPDATE_TEMPLATE_9-1)
    XML_UPDATE_TEMPLATE_9-2 = $(XML_UPDATE_TEMPLATE_9-2)
    XML_UPDATE_TEMPLATE_9-3 = $(XML_UPDATE_TEMPLATE_9-3)
    XML_UPDATE_TEMPLATE_9-4 = $(XML_UPDATE_TEMPLATE_9-4)
    XML_UPDATE_TEMPLATE_9-5 = $(XML_UPDATE_TEMPLATE_9-5)
    UPDATED -> NOTIFY_UPDATE [UPDATED]
    UPDATE_REJECTED -> NOTIFY_UPDATE [UPDATE_REJECTED]
Note: Custom transformer e-mails processing results to administrator
NOTIFY_UPDATE
    CSW_ID = @Value(csw_id)
    ID = @Value(id)
    P-T_ABBR = $(P-T_ABBR)
