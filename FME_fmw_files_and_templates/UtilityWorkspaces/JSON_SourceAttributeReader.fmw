FME workspace JSON_SourceAttributeReader.fmw

Parameters:
- SourceDataset_JSON = Z:\FME\JSON\collections.json   # Source JSON (JavaScript Object Notation) File or URL

Readers:
- JSON_1: JSON from $(SourceDataset_JSON)

Note: Doubleclick on box to Open / Click on parameters, then click on first row in Query column. Click on button to expose all attributes available in BC
FeatureReader
    ATTRIBUTES = Results,"sector,preview_zoom_level,maintainer,west_bound_longitude,iso_topic_string,view_audience,private,maintainer_email,num_tags,license_title,org,east_bound_longitude,id,link_to_imap,north_bound_latitude,metadata_modified,author,author_email,preview_map_service_url,preview_latitude,object_name,state,version,metadata_created,license_id,type,resources{}.ofi,resources{}.cache_last_updated,resources{}.data_collection_start_date,resources{}.package_id,resources{}.resource_storage_access_method,resources{}.datastore_active,resources{}.id,resources{}.size,resources{}.format,resources{}.state,resources{}.edc_resource_type,resources{}.hash,resources{}.description,resources{}.cache_url,resources{}.projection_name,resources{}.mimetype_inner,resources{}.url_type,resources{}.data_collection_end_date,resources{}.mimetype,resources{}.resource_storage_location,resources{}.name,resources{}.created,resources{}.url,resources{}.last_modified,resources{}.supplemental_info,resources{}.resource_update_cycle,resources{}.position,resources{}.revision_id,resources{}.resource_type,more_info{}.link,more_info{}.delete,num_resources,tags{}.vocabulary_id,tags{}.state,tags{}.display_name,tags{}.id,tags{}.name,retention_expiry_date,spatial,contacts{}.name,contacts{}.private,contacts{}.role,contacts{}.branch,contacts{}.organization,contacts{}.email,contacts{}.delete,resource_status,south_bound_latitude,record_archive_date,layer_name,creator_user_id,download_audience,preview_image_url,replacement_record,lineage_statement,name,security_class,dates{}.date,dates{}.type,organization.description,organization.created,organization.title,organization.name,organization.is_organization,organization.state,organization.image_url,organization.revision_id,organization.type,organization.id,organization.approval_status,record_publish_date,isopen,preview_longitude,url,source_data_path,notes,owner_org,edc_state,record_last_modified,license_url,data_quality,metadata_visibility,title,revision_id,record_create_date,sub_org,purpose,fme_geometry{0},details{}.data_precision,details{}.column_comments,details{}.data_type,details{}.short_name,details{}.column_name,object_short_name,object_table_comments,spatial_datatypes,image_display_url,image_url,dates{}.delete,groups{}.display_name,groups{}.description,groups{}.image_display_url,groups{}.title,groups{}.id,groups{}.name,metadata_language,odsi_uid,metadata_standard_version,metadata_standard_name,metadata_character_set,extras{}.key,extras{}.value,metastar_uid"
    ATTR_ACCUM_MODE = Only Use Result
    COMBINE_GEOM = Use Result
    DATASET = https://catalogue.data.gov.bc.ca/api/3/action/package_search?start=0&rows=1000
    FORMAT = JSON
    JSON_DECODE_TEXT_STRINGS = Yes
    JSON_FEATURE_TYPE_KEY = json_featuretype
    JSON_FLATTEN_MODE = ALL_LEVELS
    JSON_GEOMETRY_FORMAT = None
    JSON_QUERY_TABLE = Results json["result"]["results"][*]
    JSON_SAVE_FRAGMENTS = NO
    JSON_SCAN_MODE = QUERY
    JSON_USE_BASENAME_AS_DEFAULT_FEATURE_TYPE = No
    JSON_USE_SEARCH_ENVELOPE = NO
    OUTPUT_FEATURES_DISPLAY = Schema and Data Features
