FME workspace Empty_PyCSW.fmw

Parameters:
- FANOUT_DIRECTORY_FAILED = P:\Data\xml_failed   # Fanout Directory
- CSW_URL = http://localhost:8000/csw   # CSW URL

Note: Initiates instance of tool
Creator
    GEOMTYPE = Geometry Object
    NUM = 1
    CREATED -> GetRecords_POST [ROOT]
GetRecords_POST: XMLTemplater
    OUTPUT_XML_HEADER = Yes
    RESULT_ATTRIBUTE = get_data
    ROOT_QUERY_EXPR:
      <?xml version="1.0" encoding="UTF-8"?>
      <csw:GetRecords
          service="CSW"
          version="2.0.2"
          resultType="results"
          outputFormat="application/xml"
          outputSchema="http://www.opengis.net/cat/csw/2.0.2"
          xsi:schemaLocation="http://www.opengis.net/cat/csw/2.0.2 http://schemas.opengis.net/csw/2.0.2/CSW-discovery.xsd"
          xmlns:csw="http://www.opengis.net/cat/csw/2.0.2"
          xmlns:dc="http://purl.org/dc/elements/1.1/"
          xmlns:dct="http://purl.org/dc/terms/"
          xmlns:gmd="http://www.isotc211.org/2005/gmd"
          xmlns:gml="http://www.opengis.net/gml"
          xmlns:ows="http://www.opengis.net/ows"
          xmlns:xs="http://www.w3.org/2001/XMLSchema"
          xmlns:xsi="http://www.w3.org/2001/XMLSchema-instance">
          <csw:Query typeNames="csw:Record">
              <csw:ElementSetName typeNames="gmd:MD_Metadata">full</csw:ElementSetName>
              <csw:Constraint version="1.1.0">
                  <Filter
                      xmlns="http://www.opengis.net/ogc"
                      xmlns:gml="http://www.opengis.net/gml">
                      <PropertyIsLike wildCard="*" singleChar="_" escapeChar="\">
                          <PropertyName>csw:AnyText</PropertyName>
                          <Literal>*</Literal>
                     </PropertyIsLike>
                  </Filter>
              </csw:Constraint>
          </csw:Query>
      </csw:GetRecords>
    VISIBLE_QUERY_VALIDATE = Yes
    -> PyCSW_GETRECORDS
PyCSW_GETRECORDS: PythonCaller
    NEW_ATTRIBUTES = get_response
    PYTHONSOURCE:
      import fme
      import fmeobjects
      import urllib2
      import requests

      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):

          def __init__(self):
              pass

              self.csw_url = fme.macroValues['CSW_URL']

          def input(self,feature):
              self.xml_str = feature.getAttribute('get_data')

              request_str = self.post_xml()

              feature.setAttribute('get_response', request_str)

              self.pyoutput(feature)

          def post_xml(self):
              headers = {'Content-Type': 'application/xml'} # set what your server accepts

              return requests.post(self.csw_url, data=self.xml_str, headers=headers).text

          def close(self):
              pass
              #print "Close!"
    PYTHONSYMBOL = FeatureProcessor
    -> PyCSW_CreateOrXml
PyCSW_CreateOrXml: PythonCaller
    NEW_ATTRIBUTES = or_xml
    PYTHONSOURCE:
      import fme
      import fmeobjects
      import urllib2
      import requests
      import xml.etree.ElementTree as ET

      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):

          def __init__(self):
              pass

              self.csw_url = fme.macroValues['CSW_URL']

          def input(self,feature):
              # Get the XML response from the previous GetRecords POST
              xml_str = feature.getAttribute('get_response')
              #print(xml_str)
              res_xml = ET.fromstring(xml_str.encode('utf-8'))

              # Get all the IDs
              srch_res = res_xml.find('./{http://www.opengis.net/cat/csw/2.0.2}SearchResults')
              results = srch_res.findall('{http://www.opengis.net/cat/csw/2.0.2}Record')
              ids = []
              for r in results:
                  id_tag = r.find('{http://purl.org/dc/elements/1.1/}identifier')
                  ids.append(id_tag.text)

              print("ids: %s" % ids)

              # Create an XML Or statement for each ID
              or_xml = ''
              for i in ids:
                  or_xml += '''
      					<ogc:PropertyIsLike escapeChar="\" singleChar="?" wildCard="*">
      						<ogc:PropertyName>apiso:Identifier</ogc:PropertyName>
      						<ogc:Literal>%s</ogc:Literal>
      					</ogc:PropertyIsLike>
      				''' % i

              feature.setAttribute('or_xml', or_xml)

              self.pyoutput(feature)

          def close(self):
              pass
              #print "Close!"
    PYTHONSYMBOL = FeatureProcessor
    -> PyCSW_DELETE_2
PyCSW_DELETE_2: PythonCaller
    NEW_ATTRIBUTES = delete_response
    PYTHONSOURCE:
      import fme
      import fmeobjects
      import urllib2
      import requests

      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):

          def __init__(self):
              pass

              self.csw_url = fme.macroValues['CSW_URL']

          def input(self,feature):
              or_xml = feature.getAttribute('or_xml')

              print("or_xml: %s" % or_xml)

              self.xml_str = '''<csw:Transaction xmlns:csw="http://www.opengis.net/cat/csw/2.0.2" xmlns:ogc="http://www.opengis.net/ogc" xmlns:apiso="http://www.opengis.net/cat/csw/apiso/1.0" xmlns:xsi="http://www.w3.org/2001/XMLSchema-instance" service="CSW" version="2.0.2" xsi:schemaLocation="http://www.opengis.net/cat/csw/2.0.2 http://schemas.opengis.net/csw/2.0.2/CSW-publication.xsd">
      		<csw:Delete>
      			<csw:Constraint version="1.1.0">
      				<ogc:Filter>
      					<ogc:Or>
      						%s
      					</ogc:Or>
      				</ogc:Filter>
      			</csw:Constraint>
      		</csw:Delete>
      	</csw:Transaction>
      	''' % or_xml

              request_str = self.post_xml()

              feature.setAttribute('delete_response', request_str)

              self.pyoutput(feature)

          def post_xml(self):
              headers = {'Content-Type': 'application/xml'} # set what your server accepts

              return requests.post(self.csw_url, data=self.xml_str, headers=headers).text

          def close(self):
              pass
              #print "Close!"
    PYTHONSYMBOL = FeatureProcessor
