FME workspace AB_Data_ClearCSW_STG07_1.fmw

Parameters:
- CLEAR_CSW_ITERATIONS = 100
- CLEAR_CSW_ITERATION_COUNT = 0
- CSW_URL = $(CSW_URL_AWS_SELECT_AB)   # CSW URL
- CSW_URL_AWS_SELECT_AB = http://http://ec2-35-183-211-115.ca-central-1.compute.amazonaws.com/csw   # CSW URL AWS
- CSW_URL_AWS_SELECT_BC = http://ec2-35-182-113-175.ca-central-1.compute.amazonaws.com:80/csw   # CSW URL AWS
- CSW_URL_LOCAL_SELECT = http://localhost:8000/csw   # CSW URL LOCAL

Creator
    GEOMTYPE = Geometry Object
    NUM = 1
    CREATED -> Clear_PyCSW [GetRecords_POST_Root]
Note: This is a custom transformer built on a loop. The transformer is located in the FME Transformers folder and must be copied to any new FME environments in order for this tool to load. Any edits required to this tool are performed by opening up the transformer itself in its home directory using FME Desktop. The loop is required because the sqlLite database which hosts the data for the CSW is limited in the number of records it can delete at a time. This tool will delete the number of records that is set in the maxrecords property in default.cfg stored in the pycsw-2.2.0 directory. The default setting for maxrecords is 100. The default setting for number of loop iterations for this tool is 100, which allows for deletion of a maximum of 10000 records in the CSW database.
Clear_PyCSW
    CSW_URL = $(CSW_URL)
    ITERATION_COUNT_ATTR = $(CLEAR_CSW_ITERATION_COUNT)
    MAX_LOOP_ITERATIONS = $(CLEAR_CSW_ITERATIONS)
