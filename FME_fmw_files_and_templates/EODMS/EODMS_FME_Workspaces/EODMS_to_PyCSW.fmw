FME workspace EODMS_to_PyCSW.fmw

Parameters:
- CLEAR_CSW_ITERATIONS = 100   # Enter number of loops. Each loop clears 100 records
- CLEAR_CSW_ITERATION_COUNT = 0   # Enter 0
- CSW_URL = http://ec2-35-182-113-175.ca-central-1.compute.amazonaws.com:80/csw   # CSW URL
- FANOUT_DIRECTORY_FAILED = C:\Data\xml_failed   # Fanout Directory
- FANOUT_DIRECTORY_PASSED = C:\Data\xml_result   # Fanout Directory
- XML_INSERT_TEMPLATE_0 = C:\FME\XML_Templates\EODMS_XML_Templates\Aerial-Photo_XML_Insert_Template.xml   # Select XML Insert Template
- XML_INSERT_TEMPLATE_1 = C:\FME\XML_Templates\EODMS_XML_Templates\CCRS-Thematic-Datasets_XML_Insert_Template.xml   # Select XML Insert Template
- XML_INSERT_TEMPLATE_2 = C:\FME\XML_Templates\EODMS_XML_Templates\Radarsat-1-Raw_XML_Insert_Template.xml   # Select XML Insert Template
- XML_INSERT_TEMPLATE_3 = C:\FME\XML_Templates\EODMS_XML_Templates\Radarsat-2-Raw_XML_Insert_Template.xml   # Select XML Insert Template

Writers:
- TEXTLINE_1: TEXTLINE to $(FANOUT_DIRECTORY_PASSED)
- TEXTLINE_2: TEXTLINE to $(FANOUT_DIRECTORY_FAILED)

Note: Initiates instance of tool
Note: This FME Workspace is for resetting and reloading the CSW. It clears all data from the CSW and local directories (if they exist), and reloads CSW and local directories with all current data. It is intended for adminisrative use only. It is dependent on another workspace (BC_Data_ClearCSW) that is initiated from the workspace runner.
Creator_2
    GEOMTYPE = Geometry Object
    NUM = 1
    CREATED -> WorkspaceRunner
Note: This workspace runner initiates a workspace containing a custom transformer built on a loop. The workspace runner is required to allow the loops to complete before initiating the rest of the processes in this tool. / The custom transformer (Clear_PyCSW) is located in the FME Transformers folder and must be copied to any new FME environments in order for this tool to load. Any edits required to this tool are performed by opening up the transformer itself in its home directory using FME Desktop. / The loop is required because the sqlLite database which hosts the data for the CSW is limited in the number of records it can delete at a time. This tool will delete the number of records that is set in the maxrecords property in default.cfg stored in the pycsw-2.2.0 directory. The default setting for maxrecords is 100. The default setting for number of loop iterations for this tool is 100, which allows for deletion of a maximum of 10000 records in the CSW database.
WorkspaceRunner
    BLOCKING = Yes
    WORKSPACE_FILE = $(FME_MF_DIR)BC_Data_ClearCSW_VM_DEV44_1.fmw
    WORKSPACE_PARAMETERS = CSW_URL,$(CSW_URL),CLEAR_CSW_ITERATIONS,$(CLEAR_CSW_ITERATIONS),CLEAR_CSW_ITERATION_COUNT,$(CLEAR_CSW_ITERATION_COUNT)
    SUCCEEDED -> AttributeCreator_3
Note: Creates directory attribute to access XML_Results directory
AttributeCreator_3
    ATTR_TABLE = SET_TO directory = $(FANOUT_DIRECTORY_PASSED)
    -> SystemCaller
Note: Clears XML_Results directory. This directory is not mandatory for the CSW, but creates local copies of XML files that were successfully published to the CSW. Used primarily in development and could be disabled in a production environment by disabling the writers found in the Local Directory Writers bookmark
SystemCaller
    ATTR = _XML_Delete_CMD
    CMD = rmdir @Value(directory) /S /Q
    -> AttributeCreator_38
Note: Creates directory attribute to access XML_Failed folder
AttributeCreator_38
    ATTR_TABLE = SET_TO failed_directory = $(FANOUT_DIRECTORY_FAILED)
    -> SystemCaller_2
Note: Clears XML_Failed directory. This directory is not mandatory for the CSW, but creates local copies of XML files that failed to publish to the CSW. Used primarily in development and could be disabled in a production environment by disabling the writers found in the Local Directory Writers bookmark
SystemCaller_2
    ATTR = XML_Failed_CMD
    CMD = rmdir @Value(failed_directory) /S /Q
    -> UUIDGenerator
    -> UUIDGenerator_2
    -> UUIDGenerator_3
    -> UUIDGenerator_4
Note: Shows count of inserted XML files
Tester_2_Passed: Inspector
Note: Outputs good XML to local directory XML_Result
text_line (writer TEXTLINE_1)
    attributes: text_line_data buffer
Note: Outputs failed XML to local directory XML_Failed
text_line (writer TEXTLINE_2)
    attributes: text_line_data buffer
Note: Shows count of XML files that failed to insert
Tester_2_Failed: Inspector

Bookmark: PyCSW Record INSERT
UUIDGenerator
    UUID_ATTR = id
    -> HNAP_XML_Templater_2 [ROOT]
Note: Formats XML and places extracted attributes
HNAP_XML_Templater_2: XMLTemplater
    OUTPUT_XML_HEADER = Yes
    RESULT_ATTRIBUTE = text_line_data
    ROOT_QUERY_FILE = $(XML_INSERT_TEMPLATE_0)
    VISIBLE_QUERY_VALIDATE = Yes
    -> XMLFormatter
UUIDGenerator_2
    UUID_ATTR = id
    -> HNAP_XML_Templater_3 [ROOT]
HNAP_XML_Templater_3: XMLTemplater
    OUTPUT_XML_HEADER = Yes
    RESULT_ATTRIBUTE = text_line_data
    ROOT_QUERY_FILE = $(XML_INSERT_TEMPLATE_1)
    VISIBLE_QUERY_VALIDATE = Yes
    -> XMLFormatter
UUIDGenerator_3
    UUID_ATTR = id
    -> HNAP_XML_Templater_4 [ROOT]
HNAP_XML_Templater_4: XMLTemplater
    OUTPUT_XML_HEADER = Yes
    RESULT_ATTRIBUTE = text_line_data
    ROOT_QUERY_FILE = $(XML_INSERT_TEMPLATE_2)
    VISIBLE_QUERY_VALIDATE = Yes
    -> XMLFormatter
UUIDGenerator_4
    UUID_ATTR = id
    -> HNAP_XML_Templater_5 [ROOT]
HNAP_XML_Templater_5: XMLTemplater
    OUTPUT_XML_HEADER = Yes
    RESULT_ATTRIBUTE = text_line_data
    ROOT_QUERY_FILE = $(XML_INSERT_TEMPLATE_3)
    VISIBLE_QUERY_VALIDATE = Yes
    -> XMLFormatter
Note: Cleans up XML documents
XMLFormatter
    COLLAPSE_EMPTY_ELEMENT = No
    FORMATTING_CHOICE = Pretty-Print XML
    LIST_NAME = _xml_error
    NAMESPACE_CLEANUP = Yes
    SCHEMALOC_CLEANUP = Yes
    XML_ATTR_TEXT = text_line_data
    XML_INPUT_TYPE = Attribute Specifying XML Text
    XML_OUTPUT_ATTR = _xml_output
    XML_OUTPUT_TYPE = Attribute
    PASSED -> XMLValidator
Note: Validates XML syntax
XMLValidator
    LIMIT_ERRORS = No
    LIST_NAME = _xml_error
    VAL_MODE_1 = Syntax Only
    XML_ATTR_TEXT = text_line_data
    XML_INPUT_TYPE = Attribute Specifying XML Text
    PASSED -> PyCSW_POST_1
Note: Python script to post XML to CSW
PyCSW_POST_1: PythonCaller
    NEW_ATTRIBUTES = insert_response
    PYTHONSOURCE:
      import fme
      import fmeobjects
      import urllib2
      import requests

      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):

          def __init__(self):
              pass

              self.csw_url = fme.macroValues['CSW_URL']

          def input(self,feature):
              self.xml_str = feature.getAttribute('_xml_output')
              self.xml_str = self.xml_str.encode('utf-8')

              request_str = self.post_xml()

              feature.setAttribute('insert_response', request_str)

              self.pyoutput(feature)

          def post_xml(self):
              headers = {'Content-Type': 'text/xml; charset=utf-8'} # set what your server accepts

              return requests.post(self.csw_url, data=self.xml_str, headers=headers).text

          def close(self):
              pass
    PYTHONSYMBOL = FeatureProcessor
    -> AttributeExposer_2
Note: Exposes attributes with XML Response string
AttributeExposer_2
    ATTR_LIST = insert_response,delete_response
    -> Tester_2
Note: Tests for load success or failure
Tester_2
    BOOL_OP = OR
    TEST_CLAUSE = CASE_INSENSITIVE_TEST @Value(insert_response) CONTAINS <csw:totalInserted>1</csw:totalInserted>
    PASSED -> text_line (writer TEXTLINE_1)
    PASSED -> Tester_2_Passed
    FAILED -> text_line (writer TEXTLINE_2)
    FAILED -> Tester_2_Failed
