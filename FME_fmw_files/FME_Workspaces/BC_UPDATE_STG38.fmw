FME workspace BC_UPDATE_STG38.fmw

Parameters:
- CSW_URL = $(CSW_URL_AWS_SELECT_BC)   # CSW URL
- CSW_URL_AWS_SELECT_AB = http://ec2-35-183-211-115.ca-central-1.compute.amazonaws.com:80/csw   # CSW URL AWS_SELECT_AB
- CSW_URL_AWS_SELECT_BC = http://ec2-35-182-113-175.ca-central-1.compute.amazonaws.com:80/csw   # CSW URL AWS_SELECT_BC
- DestDataset_FFS = C:\Data\ATTRIBUTE_MAPPING_ERRORS\AttributeMappingErrors.ffs   # Destination FME Feature Store (FFS) File
- DestDataset_TEXTLINE = C:\Data\bc_xml_result   # Destination Text File
- EMAIL_ADMIN = robert.bennett@canada.ca   # Enter Admin eMail
- EMAIL_HOST = smtp.mail.yahoo.com
- EMAIL_PORT = 465
- EMAIL_ENCRYPTION = SSL
- EMAIL_SENDER = robbennett@rocketmail.com
- EMAIL_SENDER_PASSWORD =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
- IN_XLS_DEFAULTVALUE_FILE = C:\Data\LOOKUP_TABLES\BC_DefaultAttributeMapper.xlsx
- FANOUT_DIRECTORY_FAILED = C:\Data\bc_xml_failed   # Fanout Directory
- FANOUT_DIRECTORY_PASSED = C:\Data\bc_xml_result   # Fanout Directory
- IN_XLS_LOOKUPTABLE_ROLE_FILE = C:\Data\LOOKUP_TABLES\RoleAttributeMapper.xlsx
- IN_XLS_LOOKUPTABLE_UPDATECYCLE_FILE = C:\Data\LOOKUP_TABLES\UpdateCycleAttributeMapper.xlsx
- IN_XLS_LOOKUPTABLE_FORMAT_FILE = C:\Data\LOOKUP_TABLES\FormatAttributeMapper.xlsx
- IN_XLS_LOOKUPTABLE_SPATIALREP_FILE = C:\Data\LOOKUP_TABLES\SpatialRepresentationAttributeMapper.xlsx
- IN_XLS_LOOKUPTABLE_PROGSTATUS_FILE = C:\Data\LOOKUP_TABLES\ProgressStatusAttributeMapper.xlsx
- IN_XLS_LOOKUPTABLE_SPATIALREF_FILE = C:\Data\LOOKUP_TABLES\SpatialReferenceMapper.xlsx
- IN_XLS_XML_PUBLISHER_CONFIG_FILE = C:\Data\LOOKUP_TABLES\Config_BC_XML_Publisher.xlsx
- LOG_FILE = C:\Data\BC_Create.log   # Log File
- LOOP_ITERATIONS = 10   # Enter number of loops to query source data
- METHOD_SELECT = Auto   # Select XML Creation Method
- P-T_ABBR = BC   # Province-Territory Abbreviation
- QUERY_ITERATIONS = 1000   # Enter number of rows per iteration to query source data
- SourceDataset_XLSXR = C:\Data\LOOKUP_TABLES\Keyword.xlsx   # Source Microsoft Excel File(s)
- TIME_FILTER_DAYS = 0   # Enter preceding number of days to filter
- TIME_FILTER_MONTHS = 0   # Enter preceding number of months to filter
- TEMPLATE_GMD_MDMETADATA = C:\Data\XML_TEMPLATE\GMD_MDMETADATA.xml
- TEMPLATE_GMD_CITEDRESPONSIBLEPARTY = C:\Data\XML_TEMPLATE\GMD_CITEDRESPONSIBLEPARTY.xml
- TEMPLATE_GMD_DISTRIBUTIONFORMAT = C:\Data\XML_TEMPLATE\GMD_DISTRIBUTIONFORMAT.xml
- TEMPLATE_GMD_ONLINERESOURCE = C:\Data\XML_TEMPLATE\GMD_ONLINERESOURCE.xml
- TEMPLATE_GMD_REFERENCESYSTEMINFO = C:\Data\XML_TEMPLATE\GMD_REFERENCESYSTEMINFO.xml
- TEMPLATE_GMD_RESOURCEMAINTENANCE = C:\Data\XML_TEMPLATE\GMD_RESOURCEMAINTENANCE.xml
- TEMPALTE_GMD_TOPICCATEGORY = C:\Data\XML_TEMPLATE\GMD_TOPICCATEGORY.xml
- TEMPLATE_GMD_KEYWORDS = C:\Data\XML_TEMPLATE\GMD_KEYWORDS.xml
- TEMPLATE_GMD_DISTRIBUTOR = C:\Data\XML_TEMPLATE\GMD_DISTRIBUTOR.xml
- TEMPLATE_GMD_TRANSFEROPTIONS = C:\Data\XML_TEMPLATE\GMD_TRANSFEROPTIONS.xml
- TEMPLATE_GMD_CONTACT = C:\Data\XML_TEMPLATE\GMD_CONTACT.xml

Readers:
- XLSXR_1: XLSXR from $(IN_XLS_LOOKUPTABLE_ROLE_FILE)
- XLSXR_2: XLSXR from $(IN_XLS_LOOKUPTABLE_UPDATECYCLE_FILE)
- XLSXR_3: XLSXR from $(IN_XLS_LOOKUPTABLE_FORMAT_FILE)
- XLSXR_4: XLSXR from $(IN_XLS_LOOKUPTABLE_SPATIALREP_FILE)
- XLSXR_5: XLSXR from $(IN_XLS_LOOKUPTABLE_PROGSTATUS_FILE)
- XLSXR_6: XLSXR from $(IN_XLS_LOOKUPTABLE_SPATIALREF_FILE)
- XLSXR_7: XLSXR from $(IN_XLS_DEFAULTVALUE_FILE)
- XLSXR_8: XLSXR from $(IN_XLS_XML_PUBLISHER_CONFIG_FILE)
- XLSXR_9: XLSXR from $(SourceDataset_XLSXR)

Writers:
- TEXTLINE_1: TEXTLINE to $(FANOUT_DIRECTORY_PASSED)
- TEXTLINE_2: TEXTLINE to $(FANOUT_DIRECTORY_FAILED)
- FFS_1: FFS to $(DestDataset_FFS)
- TEXTLINE_3: TEXTLINE to $(DestDataset_TEXTLINE)

text_line (writer TEXTLINE_3)
    attributes: text_line_data buffer
text_line (writer TEXTLINE_1)
    attributes: text_line_data buffer
text_line (writer TEXTLINE_2)
    attributes: text_line_data buffer
NOTIFY_UPDATE
    CSW_ID = @Value(csw_id)
    EMAIL_ADMIN = $(EMAIL_ADMIN)
    EMAIL_ENCRYPTION = $(EMAIL_ENCRYPTION)
    EMAIL_HOST = $(EMAIL_HOST)
    EMAIL_PORT = $(EMAIL_PORT)
    EMAIL_SENDER = $(EMAIL_SENDER)
    EMAIL_SENDER_PASSWORD = $(EMAIL_SENDER_PASSWORD)
    ID = @Value(id)
    P-T_ABBR = $(P-T_ABBR)

Bookmark: Data extraction and french translation
Creator
    GEOMTYPE = Geometry Object
    NUM = 1
    CREATED -> BC_UPDATE_PRETRANSLATE [CSW_QUERY]
    CREATED -> BC_UPDATE_PRETRANSLATE [API_QUERY]
BC_UPDATE_PRETRANSLATE
    EMAIL_ADMIN = $(EMAIL_ADMIN)
    EMAIL_ENCRYPTION = $(EMAIL_ENCRYPTION)
    EMAIL_HOST = $(EMAIL_HOST)
    EMAIL_PORT = $(EMAIL_PORT)
    EMAIL_SENDER = $(EMAIL_SENDER)
    EMAIL_SENDER_PASSWORD = $(EMAIL_SENDER_PASSWORD)
    LOOP_ITERATIONS = $(LOOP_ITERATIONS)
    QUERY_ITERATIONS = $(QUERY_ITERATIONS)
    TIME_FILTER_DAYS = $(TIME_FILTER_DAYS)
    TIME_FILTER_MONTHS = $(TIME_FILTER_MONTHS)
    NO_DELETED_RECORDS_COUNT -> NOTIFY_UPDATE [NO_RECORDS_DELETED_COUNT]
    DELETED_RECORDS_COUNT -> NOTIFY_UPDATE [RECORDS_DELETED_COUNT]
    NEW_RECORDS_COUNT -> NOTIFY_UPDATE [NEW_RECORDS_COUNT]
    -> BC_GEOWAREHOUSE_URL_BUILDER
    UPDATED_RECORDS_COUNT -> NOTIFY_UPDATE [UPDATED_RECORDS_COUNT]
    TOTAL_RECORDS_COUNT -> NOTIFY_UPDATE [TOTAL_RECORDS_COUNT]
Note: Translating to french
AWS_TRANSLATE
    -> DEFAULT_ATTRIBUTE_MAPPER

Bookmark: BC resource formatter
BC_GEOWAREHOUSE_URL_BUILDER
    ADMIN_EMAIL = robert.bennett@canada.ca
    EMAIL_ENCRYPTION = SSL
    EMAIL_HOST = smtp.mail.yahoo.com
    EMAIL_PORT = 465
    EMAIL_SENDER = robbennett@rocketmail.com
    EMAIL_SENDER_PASSWORD =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
    -> BC_WMS_FORMATTER
Note: Recreating URL for WMS call
BC_WMS_FORMATTER
    -> BC_RESOURCE_NAME_CORRECTION [AttributeExposer_Input]
BC_RESOURCE_NAME_CORRECTION
    -> AWS_TRANSLATE

Bookmark: Default value and date management
BC_DEFAULT_ATTRIBUTES (reader XLSXR_7)
    attributes: default_key char(28), default_value char(134)
    -> DEFAULT_ATTRIBUTE_MAPPER [XLS_INPUT]
DEFAULT_ATTRIBUTE_MAPPER
    -> TEMPORAL_EXTENTS_MAPPER
TEMPORAL_EXTENTS_MAPPER
    -> TOPIC_PARSER

Bookmark: Topic extraction
TOPIC_PARSER
    DELIMITER = ,
    -> METADATA_VALUE_MAPPER_7 [DATA_INPUT]

Bookmark: Attribute value mapper
Keyword (reader XLSXR_9)
    attributes: original_value char(22), real_value_english char(23)
    -> METADATA_VALUE_MAPPER_7 [LOOKUP_TABLE_INPUT]
Note: Keyword
METADATA_VALUE_MAPPER_7
    Att_To_map = iso_topic{}.topic_value
    CODE_REFRESH = NO
    ENGLISH_REFRESH = YES
    ERROR_NOT_MAPPED = YES
    FRENCH_REFRESH = NO
    -> METADATA_VALUE_MAPPER [DATA_INPUT]
    -> MAPPING_ERROR_LIST_CREATOR
Role (reader XLSXR_1)
    attributes: original_value char(22), real_value_english char(22), real_value_french char(21), code_value char(7)
    -> METADATA_VALUE_MAPPER [LOOKUP_TABLE_INPUT]
Note: Role
METADATA_VALUE_MAPPER
    Att_To_map = contacts{}.role
    CODE_REFRESH = YES
    ENGLISH_REFRESH = YES
    ERROR_NOT_MAPPED = YES
    FRENCH_REFRESH = YES
    -> METADATA_VALUE_MAPPER_2 [DATA_INPUT]
    -> MAPPING_ERROR_LIST_CREATOR
Update (reader XLSXR_2)
    attributes: original_value char(12), real_value_english char(12), real_value_french char(14), code_value char(7)
    -> METADATA_VALUE_MAPPER_2 [LOOKUP_TABLE_INPUT]
Note: Update cycle
METADATA_VALUE_MAPPER_2
    Att_To_map = resources{}.resource_update_cycle
    CODE_REFRESH = YES
    ENGLISH_REFRESH = YES
    ERROR_NOT_MAPPED = YES
    FRENCH_REFRESH = YES
    -> METADATA_VALUE_MAPPER_3 [DATA_INPUT]
    -> MAPPING_ERROR_LIST_CREATOR
Format (reader XLSXR_3)
    attributes: original_value char(24), real_value_english char(10)
    -> METADATA_VALUE_MAPPER_3 [LOOKUP_TABLE_INPUT]
Note: Format
METADATA_VALUE_MAPPER_3
    Att_To_map = resources{}.format
    CODE_REFRESH = NO
    ENGLISH_REFRESH = YES
    ERROR_NOT_MAPPED = YES
    FRENCH_REFRESH = NO
    -> METADATA_VALUE_MAPPER_5 [DATA_INPUT]
    -> MAPPING_ERROR_LIST_CREATOR
Progress (reader XLSXR_5)
    attributes: original_value char(18), real_value_english char(18), real_value_french char(18), code_value char(7)
    -> METADATA_VALUE_MAPPER_5 [LOOKUP_TABLE_INPUT]
Note: Progress
METADATA_VALUE_MAPPER_5
    Att_To_map = progress_code
    CODE_REFRESH = YES
    ENGLISH_REFRESH = YES
    ERROR_NOT_MAPPED = YES
    FRENCH_REFRESH = YES
    -> METADATA_VALUE_MAPPER_6 [DATA_INPUT]
    -> MAPPING_ERROR_LIST_CREATOR
SpatialRepresentation (reader XLSXR_4)
    attributes: original_value char(12), real_value_english char(12), real_value_french char(13), code_value char(7)
    -> METADATA_VALUE_MAPPER_6 [LOOKUP_TABLE_INPUT]
METADATA_VALUE_MAPPER_6
    Att_To_map = spatial_representation_type
    CODE_REFRESH = YES
    ENGLISH_REFRESH = YES
    ERROR_NOT_MAPPED = YES
    FRENCH_REFRESH = YES
    -> METADATA_VALUE_MAPPER_4 [DATA_INPUT]
    -> MAPPING_ERROR_LIST_CREATOR
SpatialRef (reader XLSXR_6)
    attributes: original_value char(47), real_value_english char(12)
    -> METADATA_VALUE_MAPPER_4 [LOOKUP_TABLE_INPUT]
METADATA_VALUE_MAPPER_4
    Att_To_map = resources{}.projection_name
    CODE_REFRESH = NO
    ENGLISH_REFRESH = YES
    ERROR_NOT_MAPPED = YES
    FRENCH_REFRESH = NO
    -> GMD_SECTION_DATA_EXTRACTION
    -> MAPPING_ERROR_LIST_CREATOR
MAPPING_ERROR_LIST_CREATOR
    LIST_ATTR = mapping_errors{}
    LIST_NAME = mapping_errors{}
    -> ATTRIBUTE_MAPPING_ERRORS (writer FFS_1)
ATTRIBUTE_MAPPING_ERRORS (writer FFS_1)

Bookmark: Data prepartion for medadata section
Note: Creating list for GMD_Section
GMD_SECTION_DATA_EXTRACTION
    -> BC_MORE_INFO_MANAGER [ListSearcher_Input]
Note: Managing more info list
BC_MORE_INFO_MANAGER
    -> REMOVE_UNWORKING_URL_WMS_ESRI_REST [ListSearcher_Input]

Bookmark: Data cleanup. Droping not working webservice
Note: Removing unworking WMS/ESRI_REST from resources
REMOVE_UNWORKING_URL_WMS_ESRI_REST
    -> WMS_REST_LANGUAGE_FORMATTER

Bookmark: HNAP Rules- 1 web service per language.
WMS_REST_LANGUAGE_FORMATTER
    ADMIN_EMAIL = robert.bennett@canada.ca
    EMAIL_ENCRYPTION = SSL
    EMAIL_HOST = smtp.mail.yahoo.com
    EMAIL_PORT = 465
    EMAIL_SENDER = robbennett@rocketmail.com
    EMAIL_SENDER_PASSWORD =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
    -> DUPLICATE_SERVICE_REMOVER
DUPLICATE_SERVICE_REMOVER
    -> XML_PUBLISHER

Bookmark: XML CREATION ANS WRITING
Feuil1 (reader XLSXR_8)
    attributes: HNAP_ATTRIBUTES char(55), FEATURE_ATTRIBUTES char(40), METADATA_SECTION char(210)
    -> XML_PUBLISHER [CONFIG_FILE]
XML_PUBLISHER
    CSW_URL = $(CSW_URL_AWS_SELECT_BC)
    CSW_URL_AWS_SELECT_AB = $(CSW_URL_AWS_SELECT_AB)
    CSW_URL_AWS_SELECT_BC = $(CSW_URL_AWS_SELECT_BC)
    METHOD_SELECT = $(METHOD_SELECT)
    TEMPALTE_GMD_TOPICCATEGORY = $(TEMPALTE_GMD_TOPICCATEGORY)
    TEMPLATE_GMD_CITEDRESPONSIBLEPARTY = $(TEMPLATE_GMD_CITEDRESPONSIBLEPARTY)
    TEMPLATE_GMD_CONTACT = $(TEMPLATE_GMD_CONTACT)
    TEMPLATE_GMD_DISTRIBUTIONFORMAT = $(TEMPLATE_GMD_DISTRIBUTIONFORMAT)
    TEMPLATE_GMD_DISTRIBUTOR = $(TEMPLATE_GMD_DISTRIBUTOR)
    TEMPLATE_GMD_KEYWORDS = $(TEMPLATE_GMD_KEYWORDS)
    TEMPLATE_GMD_MDMETADATA = $(TEMPLATE_GMD_MDMETADATA)
    TEMPLATE_GMD_ONLINERESOURCE = $(TEMPLATE_GMD_ONLINERESOURCE)
    TEMPLATE_GMD_REFERENCESYSTEMINFO = $(TEMPLATE_GMD_REFERENCESYSTEMINFO)
    TEMPLATE_GMD_RESOURCEMAINTENANCE = $(TEMPLATE_GMD_RESOURCEMAINTENANCE)
    TEMPLATE_GMD_TRANSFEROPTIONS = $(TEMPLATE_GMD_TRANSFEROPTIONS)
    LOCAL -> text_line (writer TEXTLINE_3)
    INSERT_PASSED -> text_line (writer TEXTLINE_1)
    INSERT_PASSED -> NOTIFY_UPDATE [INSERTED]
    INSERT_FAILED -> text_line (writer TEXTLINE_2)
    INSERT_FAILED -> NOTIFY_UPDATE [INSERT_REJECTED]
    UPDATE_PASSED -> text_line (writer TEXTLINE_1)
    UPDATE_PASSED -> NOTIFY_UPDATE [UPDATED]
    UPDATE_FAILED -> text_line (writer TEXTLINE_2)
    UPDATE_FAILED -> NOTIFY_UPDATE [UPDATE_REJECTED]
