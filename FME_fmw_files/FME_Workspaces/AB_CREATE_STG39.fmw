FME workspace AB_CREATE_STG39.fmw

Parameters:
- ISO_19139_QUERY_ITERATIONS = 2000   # Enter
- LOOP_ITERATIONS = 20   # Enter number of loops to query source data
- QUERY_ITERATIONS = 1000   # Enter number of rows per iteration to query source data
- TIME_FILTER_DAYS = 0   # Enter preceding number of days to filter
- TIME_FILTER_MONTHS = 0   # Enter preceding number of months to filter
- SourceDataset_XLSXR = C:\Data\LOOKUP_TABLES\AB_DefaultAttributeMapper.xlsx   # Source Microsoft Excel File(s)
- IN_XLS_LOOKUPTABLE_ROLE_FILE = C:\Data\LOOKUP_TABLES\RoleAttributeMapper.xlsx
- IN_XLS_LOOKUPTABLE_FORMAT_FILE = C:\Data\LOOKUP_TABLES\FormatAttributeMapper.xlsx
- IN_XLS_LOOKUPTABLE_SPATIALREP_FILE = C:\Data\LOOKUP_TABLES\SpatialRepresentationAttributeMapper.xlsx
- IN_XLS_LOOKUPTABLE_PROGSTATUS_FILE = C:\Data\LOOKUP_TABLES\ProgressStatusAttributeMapper.xlsx
- IN_XLS_LOOKUPTABLE_SPATIALREF_FILE = C:\Data\LOOKUP_TABLES\SpatialReferenceMapper.xlsx
- DestDataset_FFS = C:\Data\ATTRIBUTE_MAPPING_ERRORS\AttributeMappingErrors.ffs   # Destination FME Feature Store (FFS) File
- SourceDataset_XLSXR_12 = C:\Data\LOOKUP_TABLES\SpatialReferenceCodespaceAttributeMapper.xlsx   # Source Microsoft Excel File(s)
- SourceDataset_XLSXR_10 = C:\Data\LOOKUP_TABLES\UpdateCycleAttributeMapper.xlsx   # Source Microsoft Excel File(s)
- CSW_URL_AWS_SELECT_BC = http://ec2-35-182-113-175.ca-central-1.compute.amazonaws.com:80/csw   # CSW URL AWS
- P-T_ABBR = AB   # Province-Territory Abbreviation
- FANOUT_DIRECTORY_FAILED = C:\Data\ab_xml_failed   # Fanout Directory
- FANOUT_DIRECTORY_PASSED = C:\Data\ab_xml_result   # Fanout Directory
- DestDataset_TEXTLINE = C:\Data\ab_xml_result   # Destination Text File
- IN_XLS_XML_PUBLISHER_CONFIG_FILE = C:\Data\LOOKUP_TABLES\Config_BC_XML_Publisher.xlsx
- TEMPLATE_GMD_MDMETADATA = C:\Data\XML_TEMPLATE\GMD_MDMETADATA.xml
- TEMPLATE_GMD_CITEDRESPONSIBLEPARTY = C:\Data\XML_TEMPLATE\GMD_CITEDRESPONSIBLEPARTY.xml
- TEMPLATE_GMD_DISTRIBUTIONFORMAT = C:\Data\XML_TEMPLATE\GMD_DISTRIBUTIONFORMAT.xml
- TEMPLATE_GMD_ONLINERESOURCE = C:\Data\XML_TEMPLATE\GMD_ONLINERESOURCE.xml
- TEMPLATE_GMD_REFERENCESYSTEMINFO = C:\Data\XML_TEMPLATE\GMD_REFERENCESYSTEMINFO.xml
- TEMPLATE_GMD_RESOURCEMAINTENANCE = C:\Data\XML_TEMPLATE\GMD_RESOURCEMAINTENANCE.xml
- TEMPALTE_GMD_TOPICCATEGORY = C:\Data\XML_TEMPLATE\GMD_TOPICCATEGORY.xml
- TEMPLATE_GMD_KEYWORDS = C:\Data\XML_TEMPLATE\GMD_KEYWORDS.xml
- TEMPLATE_GMD_DISTRIBUTOR = C:\Data\XML_TEMPLATE\GMD_DISTRIBUTOR.xml
- TEMPLATE_GMD_TRANSFEROPTIONS = C:\Data\XML_TEMPLATE\GMD_TRANSFEROPTIONS.xml
- TEMPLATE_GMD_CONTACT = C:\Data\XML_TEMPLATE\GMD_CONTACT.xml
- SourceDataset_FFS = Z:\Data\FFS\AB_AllData_Translated.ffs   # Source FME Feature Store (FFS) File(s)
- CSW_URL_AWS_SELECT_AB = http://ec2-35-183-211-115.ca-central-1.compute.amazonaws.com:80/csw   # CSW URL AWS
- CSW_URL = $(CSW_URL_AWS_SELECT_AB)   # CSW URL

Readers:
- XLSXR_1: XLSXR from $(SourceDataset_XLSXR)
- XLSXR_2: XLSXR from $(IN_XLS_LOOKUPTABLE_ROLE_FILE)
- XLSXR_3: XLSXR from $(IN_XLS_LOOKUPTABLE_FORMAT_FILE)
- XLSXR_4: XLSXR from $(IN_XLS_LOOKUPTABLE_SPATIALREP_FILE)
- XLSXR_5: XLSXR from $(IN_XLS_LOOKUPTABLE_PROGSTATUS_FILE)
- XLSXR_6: XLSXR from $(IN_XLS_LOOKUPTABLE_SPATIALREF_FILE)
- XLSXR_7: XLSXR from $(SourceDataset_XLSXR_12)
- XLSXR_8: XLSXR from $(SourceDataset_XLSXR_10)
- XLSXR_9: XLSXR from $(IN_XLS_XML_PUBLISHER_CONFIG_FILE)
- FFS_1: FFS from $(SourceDataset_FFS)

Writers:
- FFS_2: FFS to $(DestDataset_FFS)
- TEXTLINE_1: TEXTLINE to $(FANOUT_DIRECTORY_PASSED)
- TEXTLINE_2: TEXTLINE to $(FANOUT_DIRECTORY_FAILED)
- TEXTLINE_3: TEXTLINE to $(DestDataset_TEXTLINE)

Creator [off]
    GEOMTYPE = Geometry Object
    NUM = 1
    CREATED -> AB_CREATE_PRETRANSLATE [INPUT_AB_GEO_QUERY]
    CREATED -> AB_CREATE_PRETRANSLATE [INPUT_AB_OPEN_QUERY]
AB_DEFAULT_ATTRIBUTES (reader XLSXR_1) [off]
    attributes: default_key char(32), default_value char(89)
    -> DEFAULT_ATTRIBUTE_MAPPER [XLS_INPUT]
DEFAULT_ATTRIBUTE_MAPPER [off]
    ADMIN_EMAIL = robert.bennett@canada.ca
    DATA_COLLECTION_END_DATE_0 = @Value(data_collection_end_date_0)
    DATA_COLLECTION_START_DATE_0 = @Value(data_collection_start_date_0)
    EAST_BOUND_LONGITUDE = @Value(east_bound_longitude)
    EMAIL_ENCRYPTION = SSL
    EMAIL_HOST = smtp.mail.yahoo.com
    EMAIL_PORT = 465
    EMAIL_SENDER = robbennett@rocketmail.com
    EMAIL_SENDER_PASSWORD =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
    END_FEATURE = @Value(end_feature)
    GET_BY_ID = @Value(get_by_id)
    ID = @Value(id)
    ISO_19139_QUERY_STRING = @Value(iso_19139_query_string)
    METADATA_STANDARD_NAME = @Value(metadata_standard_name)
    METADATA_STANDARD_VERSION = @Value(metadata_standard_version)
    METHOD = @Value(method)
    MORE_INFO.LINK_0 = @Value(more_info.link_0)
    MORE_INFO_0_.LINK = @Value(more_info{0}.link)
    NORTH_BOUND_LATITUDE = @Value(north_bound_latitude)
    NOTES = @Value(notes)
    PROGRESS_CODE = @Value(progress_code)
    RECORD_CREATE_DATE = @Value(record_create_date)
    RECORD_LAST_MODIFIED = @Value(record_last_modified)
    RECORD_PUBLISH_DATE = @Value(record_publish_date)
    REFERENCE_SYSTEM = @Value(reference_system)
    REFERENCE_VERSION = @Value(reference_system_version)
    RESOURCE_UPDATE_CYCLE_0 = @Value(resource_update_cycle_0)
    RESOURCE_URL_ALT = @Value(resource_url_alt)
    SECTOR = @Value(sector)
    SOUTH_BOUND_LATITUDE = @Value(south_bound_latitude)
    SPATIAL_REPRESENTATION_TYPE = @Value(spatial_representation_type)
    TITLE = @Value(title)
    WEST_BOUND_LONGITUDE = @Value(west_bound_longitude)
    ZIP_LINK = @Value(zip_link)
    -> AB_MISSING_ATTRIBUTE_MANAGER
AB_MISSING_ATTRIBUTE_MANAGER [off]
    -> AB_WMS_FORMATTER
AB_WMS_FORMATTER [off]
    RESOURCES_2_.FORMAT = @Value(resources{2}.format)
    RESOURCES_2_.URL = @Value(resources{2}.url)
    RESOURCES_3_.FORMAT = @Value(resources{3}.format)
    RESOURCES_3_.URL = @Value(resources{3}.url)
    TITLE = @Value(title)
    -> AWS_TRANSLATE
AWS_TRANSLATE [off]
    -> AB_TRANSLATION_CORRECTION
AB_AllData_Translated (reader FFS_1)
    attributes: id varchar(200), progress_code varchar(200), spatial_representation_type varchar(200), method varchar(200), projectionList{}.projection_name varchar(200), reference_system varchar(200), reference_system_version varchar(200), data_collection_start_date_0 varchar(200), record_last_modified varchar(200), record_create_date varchar(200), tags{}.display_name varchar(200), _creation_instance varchar(200), iso_19139_query_string varchar(200), xml_fragment varchar(200), xml_id varchar(200), xml_matched_element varchar(200), xml_parent_id varchar(200), xml_parent_child_pos varchar(200), get_by_id varchar(200), text_line_data varchar(200), east_bound_longitude varchar(200), west_bound_longitude varchar(200), south_bound_latitude varchar(200), north_bound_latitude varchar(200), title varchar(200), sector varchar(200), metadata_standard_name varchar(200), metadata_standard_version varchar(200), notes varchar(200), resource_update_cycle_0 varchar(200),
      record_publish_date varchar(200), more_info.link_0 varchar(200), resource_url_alt varchar(200), data_collection_end_date_0 varchar(200), more_info{}.link varchar(200), zip_link varchar(200), start_feature varchar(200), end_feature varchar(200), start_feature2 varchar(200), _list_index varchar(200), projectionList{}.codespace varchar(200), projectionList{}.version varchar(200), reference_version varchar(200), default_key varchar(32), default_value varchar(89), zip_url varchar(200), role varchar(200), name varchar(200), email varchar(200), contacts{}.role varchar(200), contacts{}.name varchar(200), contacts{}.email varchar(200), contacts{}.default_role_value varchar(200), resource_update_cycle varchar(200), format varchar(200), url varchar(200), data_collection_start_date varchar(200), data_collection_end_date varchar(200), iso_topic{}.topic_value varchar(200), protocol varchar(200),
      name_fr varchar(200), _element_index varchar(200), resources{}.protocol varchar(200), resources{}.format varchar(200), resources{}.url varchar(200), resources{}.name varchar(200), resources{}.name_fr varchar(200), resources{}._uuid varchar(200), resources{}.resource_update_cycle varchar(200), resources{}.data_collection_start_date varchar(200), resources{}.data_collection_end_date varchar(200), resources{}.default_update_value varchar(200), resources{}._element_index varchar(200), title_fr varchar(200), sector_fr varchar(200), notes_fr varchar(200), tags{}.display_name_fr varchar(200), xtitle varchar(200), object_name varchar(200)
    -> AB_TRANSLATION_CORRECTION
AB_TRANSLATION_CORRECTION
    -> TEMPORAL_EXTENTS_MAPPER
TEMPORAL_EXTENTS_MAPPER
    -> AB_RESOURCE_LIST_MANAGER
AB_RESOURCE_LIST_MANAGER
    -> METADATA_VALUE_MAPPER [DATA_INPUT]
text_line (writer TEXTLINE_3)
    attributes: text_line_data buffer
NOTIFY_CREATE
    ADMIN_EMAIL = robert.bennett@canada.ca
    CSW_URL_AWS_SELECT_BC = http://ec2-35-182-113-175.ca-central-1.compute.amazonaws.com:80/csw
    EMAIL_ENCRYPTION = SSL
    EMAIL_HOST = smtp.mail.yahoo.com
    EMAIL_PORT = 465
    EMAIL_SENDER = robbennett@rocketmail.com
    EMAIL_SENDER_PASSWORD =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
    ID = @Value(id)
    P-T_ABBR = $(P-T_ABBR)
text_line (writer TEXTLINE_1)
    attributes: text_line_data buffer
text_line (writer TEXTLINE_2)
    attributes: text_line_data buffer

Bookmark: New Bookmark
AB_CREATE_PRETRANSLATE [off]
    ISO_19139_QUERY_ITERATIONS = $(ISO_19139_QUERY_ITERATIONS)
    LOOP_ITERATIONS = $(LOOP_ITERATIONS)
    QUERY_ITERATIONS = $(QUERY_ITERATIONS)
    TIME_FILTER_DAYS = $(TIME_FILTER_DAYS)
    TIME_FILTER_MONTHS = $(TIME_FILTER_MONTHS)
    -> DEFAULT_ATTRIBUTE_MAPPER

Bookmark: Attribute value mapper
Role (reader XLSXR_2)
    attributes: original_value char(22), real_value_english char(22), real_value_french char(21), code_value char(7)
    -> METADATA_VALUE_MAPPER [LOOKUP_TABLE_INPUT]
Note: Role
METADATA_VALUE_MAPPER
    Att_To_map = contacts{}.role
    CODE_REFRESH = YES
    ENGLISH_REFRESH = YES
    ERROR_NOT_MAPPED = YES
    FRENCH_REFRESH = YES
    -> METADATA_VALUE_MAPPER_2 [DATA_INPUT]
    -> MAPPING_ERROR_LIST_CREATOR
Update (reader XLSXR_8)
    attributes: original_value char(12), real_value_english char(12), real_value_french char(14), code_value char(7)
    -> METADATA_VALUE_MAPPER_2 [LOOKUP_TABLE_INPUT]
METADATA_VALUE_MAPPER_2
    Att_To_map = resources{}.resource_update_cycle
    CODE_REFRESH = YES
    ENGLISH_REFRESH = YES
    ERROR_NOT_MAPPED = YES
    FRENCH_REFRESH = YES
    -> MAPPING_ERROR_LIST_CREATOR
    -> METADATA_VALUE_MAPPER_3 [DATA_INPUT]
Format (reader XLSXR_3)
    attributes: original_value char(24), real_value_english char(10)
    -> METADATA_VALUE_MAPPER_3 [LOOKUP_TABLE_INPUT]
Note: Format
METADATA_VALUE_MAPPER_3
    Att_To_map = resources{}.format
    CODE_REFRESH = NO
    ENGLISH_REFRESH = YES
    ERROR_NOT_MAPPED = YES
    FRENCH_REFRESH = NO
    -> METADATA_VALUE_MAPPER_5 [DATA_INPUT]
    -> MAPPING_ERROR_LIST_CREATOR
Progress (reader XLSXR_5)
    attributes: original_value char(18), real_value_english char(18), real_value_french char(18), code_value char(7)
    -> METADATA_VALUE_MAPPER_5 [LOOKUP_TABLE_INPUT]
Note: Progress
METADATA_VALUE_MAPPER_5
    Att_To_map = progress_code
    CODE_REFRESH = YES
    ENGLISH_REFRESH = YES
    ERROR_NOT_MAPPED = NO
    FRENCH_REFRESH = YES
    -> METADATA_VALUE_MAPPER_6 [DATA_INPUT]
    -> MAPPING_ERROR_LIST_CREATOR
SpatialRepresentation (reader XLSXR_4)
    attributes: original_value char(12), real_value_english char(12), real_value_french char(13), code_value char(7)
    -> METADATA_VALUE_MAPPER_6 [LOOKUP_TABLE_INPUT]
METADATA_VALUE_MAPPER_6
    Att_To_map = spatial_representation_type
    CODE_REFRESH = YES
    ENGLISH_REFRESH = YES
    ERROR_NOT_MAPPED = NO
    FRENCH_REFRESH = YES
    -> MAPPING_ERROR_LIST_CREATOR
    -> METADATA_VALUE_MAPPER_4 [DATA_INPUT]
SpatialRef (reader XLSXR_6)
    attributes: original_value char(47), real_value_english char(12)
    -> METADATA_VALUE_MAPPER_4 [LOOKUP_TABLE_INPUT]
METADATA_VALUE_MAPPER_4
    Att_To_map = projectionList{}.projection_name
    CODE_REFRESH = NO
    ENGLISH_REFRESH = YES
    ERROR_NOT_MAPPED = YES
    FRENCH_REFRESH = NO
    -> MAPPING_ERROR_LIST_CREATOR
    -> METADATA_VALUE_MAPPER_7 [DATA_INPUT]
Codespace (reader XLSXR_7)
    attributes: original_value char(30), real_value_english char(5)
    -> METADATA_VALUE_MAPPER_7 [LOOKUP_TABLE_INPUT]
METADATA_VALUE_MAPPER_7
    Att_To_map = spatial_reference
    CODE_REFRESH = NO
    ENGLISH_REFRESH = YES
    ERROR_NOT_MAPPED = NO
    FRENCH_REFRESH = NO
    -> MAPPING_ERROR_LIST_CREATOR
    -> GMD_SECTION_DATA_EXTRACTION
MAPPING_ERROR_LIST_CREATOR
    LIST_ATTR = mapping_errors{}
    LIST_NAME = mapping_errors{}
    -> ATTRIBUTE_MAPPING_ERRORS (writer FFS_2)
ATTRIBUTE_MAPPING_ERRORS (writer FFS_2)

Bookmark: Data prepartion for medadata section
Note: Creating list for GMD_Section
GMD_SECTION_DATA_EXTRACTION
    -> MORE_INFO_MANAGER [ListSearcher_Input]
Note: Managing more info list
MORE_INFO_MANAGER: BC_MORE_INFO_MANAGER
    -> REMOVE_UNWORKING_URL_WMS_ESRI_REST [ListSearcher_Input]

Bookmark: Data cleanup. Dropping not working webservice
Note: Removing unworking WMS/ESRI_REST from resources
REMOVE_UNWORKING_URL_WMS_ESRI_REST
    -> WMS_REST_LANGUAGE_FORMATTER

Bookmark: HNAP Rules- 1 web service per language.
WMS_REST_LANGUAGE_FORMATTER
    ADMIN_EMAIL = robert.bennett@canada.ca
    EMAIL_ENCRYPTION = SSL
    EMAIL_HOST = smtp.mail.yahoo.com
    EMAIL_PORT = 465
    EMAIL_SENDER = robbennett@rocketmail.com
    EMAIL_SENDER_PASSWORD =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
    -> DUPLICATE_SERVICE_REMOVER
DUPLICATE_SERVICE_REMOVER
    -> XML_PUBLISHER

Bookmark: XML CREATION AND WRITING
Feuil1 (reader XLSXR_9)
    attributes: HNAP_ATTRIBUTES char(55), FEATURE_ATTRIBUTES char(40), METADATA_SECTION char(210)
    -> XML_PUBLISHER [CONFIG_FILE]
XML_PUBLISHER
    CSW_URL = $(CSW_URL_AWS_SELECT_AB)
    CSW_URL_AWS_SELECT_BC = $(CSW_URL_AWS_SELECT_AB)
    METHOD = Local
    TEMPALTE_GMD_TOPICCATEGORY = $(TEMPALTE_GMD_TOPICCATEGORY)
    TEMPLATE_GMD_CITEDRESPONSIBLEPARTY = $(TEMPLATE_GMD_CITEDRESPONSIBLEPARTY)
    TEMPLATE_GMD_CONTACT = $(TEMPLATE_GMD_CONTACT)
    TEMPLATE_GMD_DISTRIBUTIONFORMAT = $(TEMPLATE_GMD_DISTRIBUTIONFORMAT)
    TEMPLATE_GMD_DISTRIBUTOR = $(TEMPLATE_GMD_DISTRIBUTOR)
    TEMPLATE_GMD_KEYWORDS = $(TEMPLATE_GMD_KEYWORDS)
    TEMPLATE_GMD_MDMETADATA = $(TEMPLATE_GMD_MDMETADATA)
    TEMPLATE_GMD_ONLINERESOURCE = $(TEMPLATE_GMD_ONLINERESOURCE)
    TEMPLATE_GMD_REFERENCESYSTEMINFO = $(TEMPLATE_GMD_REFERENCESYSTEMINFO)
    TEMPLATE_GMD_RESOURCEMAINTENANCE = $(TEMPLATE_GMD_RESOURCEMAINTENANCE)
    TEMPLATE_GMD_TRANSFEROPTIONS = $(TEMPLATE_GMD_TRANSFEROPTIONS)
    LOCAL -> text_line (writer TEXTLINE_3)
    INSERT_PASSED -> NOTIFY_CREATE [INSERTED]
    INSERT_PASSED -> text_line (writer TEXTLINE_1)
    INSERT_FAILED -> NOTIFY_CREATE [INSERT_FAILED]
    INSERT_FAILED -> text_line (writer TEXTLINE_2)
