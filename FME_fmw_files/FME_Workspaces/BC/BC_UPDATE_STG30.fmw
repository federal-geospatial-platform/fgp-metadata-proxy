FME workspace BC_UPDATE_STG30.fmw

Parameters:
- CSW_URL = $(CSW_URL_AWS_SELECT_BC)   # CSW URL
- CSW_URL_AWS_SELECT_BC = http://ec2-35-182-113-175.ca-central-1.compute.amazonaws.com:80/csw   # CSW URL AWS
- LOOP_ITERATIONS = 10   # Enter number of loops to query source data
- P-T_ABBR = BC   # Province-Territory Abbreviation
- QUERY_ITERATIONS = 1000   # Enter number of rows per iteration to query source data
- TIME_FILTER_DAYS = 1   # Enter preceding number of days to filter
- TIME_FILTER_MONTHS = 0   # Enter preceding number of months to filter
- LOG_FILE = BC_Update   # Log File
- SourceDataset_XLSXR_9 = C:\Data\LOOKUP_TABLES\RoleAttributeMapper.xlsx   # Source Microsoft Excel File(s)
- SourceDataset_XLSXR_7 = C:\Data\LOOKUP_TABLES\ProgressStatusAttributeMapper.xlsx   # Source Microsoft Excel File(s)
- SourceDataset_XLSXR_11 = C:\Data\LOOKUP_TABLES\SpatialReferenceAttributeMapper.xlsx   # Source Microsoft Excel File(s)
- SourceDataset_XLSXR_8 = C:\Data\LOOKUP_TABLES\UpdateCycleAttributeMapper.xlsx   # Source Microsoft Excel File(s)
- SourceDataset_XLSXR = C:\Data\LOOKUP_TABLES\FormatAttributeMapper.xlsx   # Source Microsoft Excel File(s)
- SourceDataset_XLSXR_10 = C:\Data\LOOKUP_TABLES\SpatialRepresentationAttributeMapper.xlsx   # Source Microsoft Excel File(s)

Readers:
- XLSXR_1: XLSXR from $(SourceDataset_XLSXR_9)
- XLSXR_2: XLSXR from $(SourceDataset_XLSXR_7)
- XLSXR_3: XLSXR from $(SourceDataset_XLSXR_11)
- XLSXR_4: XLSXR from $(SourceDataset_XLSXR_8)
- XLSXR_5: XLSXR from $(SourceDataset_XLSXR)
- XLSXR_6: XLSXR from $(SourceDataset_XLSXR_10)

Note: Initiates instance of tool
Note: This FME Workspace is for daily extraction of new or updated data from the BC Data API, and inserting to the CSW. / It also tests for and removes invalid records in the CSW. / It is intended to run on FME Server on a once daily schedule.
Creator
    GEOMTYPE = Geometry Object
    NUM = 1
    CREATED -> BC_UPDATE_PRETRANSLATE [CSW_QUERY]
    CREATED -> BC_UPDATE_PRETRANSLATE [API_QUERY]
Note: Custom transformer queries the British Columbia open government portal API and exposes returned attributes and filters data by open, geospatial data and date.
BC_UPDATE_PRETRANSLATE
    CSW_URL = $(CSW_URL_AWS_SELECT_BC)
    CSW_URL_AWS_SELECT_BC = $(CSW_URL)
    LOOP_ITERATIONS = $(LOOP_ITERATIONS)
    QUERY_ITERATIONS = $(QUERY_ITERATIONS)
    TIME_FILTER_DAYS = $(TIME_FILTER_DAYS)
    TIME_FILTER_MONTHS = $(TIME_FILTER_MONTHS)
    NO_DELETED_RECORDS_COUNT -> NOTIFY_UPDATE [NO_RECORDS_DELETED_COUNT]
    DELETED_RECORDS_COUNT -> NOTIFY_UPDATE [RECORDS_DELETED_COUNT]
    -> AWS_TRANSLATE
    NEW_RECORDS_COUNT -> NOTIFY_UPDATE [NEW_RECORDS_COUNT]
    UPDATED_RECORDS_COUNT -> NOTIFY_UPDATE [UPDATED_RECORDS_COUNT]
    TOTAL_RECORDS_COUNT -> NOTIFY_UPDATE [TOTAL_RECORDS_COUNT]
Note: Custom transformer sends specific extracted attributes to the Amazon translation service to be translated to French.
AWS_TRANSLATE
    CSW_URL_AWS_SELECT_BC = http://ec2-35-182-113-175.ca-central-1.compute.amazonaws.com:80/csw
    DEEPL_KEY = ca46773d-f5a7-d659-8c2e-41c43bad0b71
    NOTES = @Value(notes)
    RESOURCE_NAME_0 = @Value(resource_name_0)
    RESOURCE_NAME_1 = @Value(resource_name_1)
    RESOURCE_NAME_2 = @Value(resource_name_2)
    RESOURCE_NAME_3 = @Value(resource_name_3)
    RESOURCE_NAME_4 = @Value(resource_name_4)
    RESOURCE_NAME_5 = @Value(resource_name_5)
    RESOURCE_NAME_6 = @Value(resource_name_6)
    RESOURCE_NAME_7 = @Value(resource_name_7)
    RESOURCE_NAME_8 = @Value(resource_name_8)
    RESOURCE_NAME_9 = @Value(resource_name_9)
    TAGS_0 = @Value(tags_0)
    TAGS_1 = @Value(tags_1)
    TAGS_2 = @Value(tags_2)
    TAGS_3 = @Value(tags_3)
    TAGS_4 = @Value(tags_4)
    TAGS_5 = @Value(tags_5)
    TAGS_6 = @Value(tags_6)
    TAGS_7 = @Value(tags_7)
    TAGS_8 = @Value(tags_8)
    TAGS_9 = @Value(tags_9)
    TITLE = @Value(title)
    -> BC_POSTTRANSLATE_1
Note: Custom transformer performs post translation functions to ensure conformity to ISO 19115 HNAP requirements
BC_POSTTRANSLATE_1
    CONTACT_EMAIL_0 = @Value(contact_email_0)
    CONTACT_NAME_0 = @Value(contact_name_0)
    CONTACT_ROLE_0 = @Value(contact_role_0)
    CONTACT_ROLE_1 = @Value(contact_role_1)
    CSW_URL_AWS_SELECT_BC = $(CSW_URL)
    DATA_COLLECTION_END_DATE_0 = @Value(data_collection_end_date_0)
    P-T_ABBR_EN = BC
    P-T_ABBR_FR = CB
    RESOURCE_UPDATE_CYCLE_0 = @Value(resource_update_cycle_0)
    SRC_LIST_2 = resource{}.projection
    -> ATTRIBUTE_MAPPER [DATA_INPUT]
Format (reader XLSXR_5)
    attributes: original_value char(24), real_value_english char(10)
    -> ATTRIBUTE_MAPPER [LOOKUP_TABLE_INPUT]
ATTRIBUTE_MAPPER
    Attribute_series = resource_format
    CODE_REFRESH = NO
    CaseSensitive = NO
    ENGLISH_REFRESH = YES
    ERROR_NOT_MAPPED = NO
    FRENCH_REFRESH = NO
    REF_CODESPACE_REFRESH = NO
    REF_CODE_REFRESH = NO
    -> ATTRIBUTE_MAPPER_2 [DATA_INPUT]
Role (reader XLSXR_1)
    attributes: original_value char(22), real_value_english char(22), real_value_french char(21), code_value char(7)
    -> ATTRIBUTE_MAPPER_2 [LOOKUP_TABLE_INPUT]
ATTRIBUTE_MAPPER_2
    Attribute_series = contact_role
    CODE_REFRESH = YES
    CaseSensitive = NO
    ENGLISH_REFRESH = YES
    ERROR_NOT_MAPPED = NO
    FRENCH_REFRESH = YES
    REF_CODESPACE_REFRESH = NO
    REF_CODE_REFRESH = NO
    -> ATTRIBUTE_MAPPER_3 [DATA_INPUT]
Progress (reader XLSXR_2)
    attributes: original_value char(18), real_value_english char(18), real_value_french char(18), code_value char(7)
    -> ATTRIBUTE_MAPPER_3 [LOOKUP_TABLE_INPUT]
ATTRIBUTE_MAPPER_3
    Attribute_series = progress_code
    CODE_REFRESH = YES
    CaseSensitive = NO
    ENGLISH_REFRESH = YES
    ERROR_NOT_MAPPED = NO
    FRENCH_REFRESH = YES
    REF_CODESPACE_REFRESH = NO
    REF_CODE_REFRESH = NO
    -> ATTRIBUTE_MAPPER_4 [DATA_INPUT]
SpatialRef (reader XLSXR_3)
    attributes: original_value char(47), reference_code_value char(11)
    -> ATTRIBUTE_MAPPER_4 [LOOKUP_TABLE_INPUT]
ATTRIBUTE_MAPPER_4
    Attribute_series = reference
    CODE_REFRESH = NO
    CaseSensitive = NO
    ENGLISH_REFRESH = NO
    ERROR_NOT_MAPPED = NO
    FRENCH_REFRESH = NO
    REF_CODESPACE_REFRESH = NO
    REF_CODE_REFRESH = YES
    -> ATTRIBUTE_MAPPER_5 [DATA_INPUT]
Update (reader XLSXR_4)
    attributes: original_value char(12), real_value_english char(12), real_value_french char(14), code_value char(7)
    -> ATTRIBUTE_MAPPER_5 [LOOKUP_TABLE_INPUT]
ATTRIBUTE_MAPPER_5
    Attribute_series = resource_update_cycle
    CODE_REFRESH = YES
    CaseSensitive = NO
    ENGLISH_REFRESH = YES
    ERROR_NOT_MAPPED = NO
    FRENCH_REFRESH = YES
    REF_CODESPACE_REFRESH = NO
    REF_CODE_REFRESH = NO
    -> ATTRIBUTE_MAPPER_6 [DATA_INPUT]
SpatialRepresentation (reader XLSXR_6)
    attributes: original_value char(12), real_value_english char(12), real_value_french char(13), code_value char(7)
    -> ATTRIBUTE_MAPPER_6 [LOOKUP_TABLE_INPUT]
ATTRIBUTE_MAPPER_6
    Attribute_series = spatial_representation_type
    CODE_REFRESH = YES
    CaseSensitive = NO
    ENGLISH_REFRESH = YES
    ERROR_NOT_MAPPED = NO
    FRENCH_REFRESH = YES
    REF_CODESPACE_REFRESH = NO
    REF_CODE_REFRESH = NO
    -> POSTTRANSLATE_3
Note: Custom transformer performs post translation functions to ensure conformity to ISO 19115 HNAP requirements
POSTTRANSLATE_3
    CSW_URL_AWS_SELECT_BC = http://ec2-35-182-113-175.ca-central-1.compute.amazonaws.com:80/csw
    SRC_LIST = resource{}.format
    SRC_LIST_2 = resource{}.projection
    -> BC_POSTTRANSLATE_4
Note: Custom transformer performs post translation functions to ensure conformity to ISO 19115 HNAP requirements
BC_POSTTRANSLATE_4
    DISTRIBUTION_FORMAT_0 = @Value(distribution_format_0)
    DISTRIBUTION_FORMAT_1 = @Value(distribution_format_1)
    DISTRIBUTION_FORMAT_2 = @Value(distribution_format_2)
    DISTRIBUTION_FORMAT_3 = @Value(distribution_format_3)
    DISTRIBUTION_FORMAT_4 = @Value(distribution_format_4)
    DISTRIBUTION_FORMAT_5 = @Value(distribution_format_5)
    ID = @Value(id)
    MORE_INFO.LINK_0 = @Value(more_info.link_0)
    NAME = @Value(name)
    OBJECT_NAME = @Value(object_name)
    REFERENCE_0 = @Value(reference_0)
    REFERENCE_1 = @Value(reference_1)
    REFERENCE_2 = @Value(reference_2)
    REFERENCE_3 = @Value(reference_3)
    REFERENCE_4 = @Value(reference_4)
    REFERENCE_5 = @Value(reference_5)
    REFERENCE_6 = @Value(reference_6)
    REFERENCE_7 = @Value(reference_7)
    REFERENCE_8 = @Value(reference_8)
    REFERENCE_9 = @Value(reference_9)
    RESOURCE_FORMAT_0 = @Value(resource_format_0)
    RESOURCE_FORMAT_1 = @Value(resource_format_1)
    RESOURCE_FORMAT_2 = @Value(resource_format_2)
    RESOURCE_FORMAT_3 = @Value(resource_format_3)
    RESOURCE_FORMAT_4 = @Value(resource_format_4)
    RESOURCE_FORMAT_5 = @Value(resource_format_5)
    RESOURCE_FORMAT_6 = @Value(resource_format_6)
    RESOURCE_FORMAT_7 = @Value(resource_format_7)
    RESOURCE_FORMAT_8 = @Value(resource_format_8)
    RESOURCE_FORMAT_9 = @Value(resource_format_9)
    RESOURCE_ID_0 = @Value(resource_id_0)
    RESOURCE_ID_2 = @Value(resource_id_2)
    RESOURCE_ID_3 = @Value(resource_id_3)
    RESOURCE_ID_4 = @Value(resource_id_4)
    RESOURCE_NAME_1 = @Value(resource_name_1)
    RESOURCE_NAME_1_FR = @Value(resource_name_1_fr)
    RESOURCE_NAME_2 = @Value(resource_name_2)
    RESOURCE_NAME_2_FR = @Value(resource_name_2_fr)
    RESOURCE_NAME_3 = @Value(resource_name_3)
    RESOURCE_NAME_3_FR = @Value(resource_name_3_fr)
    RESOURCE_NAME_4 = @Value(resource_name_4)
    RESOURCE_NAME_4_FR = @Value(resource_name_4_fr)
    RESOURCE_NAME_5 = @Value(resource_name_5)
    RESOURCE_NAME_5_FR = @Value(resource_name_5_fr)
    RESOURCE_NAME_6 = @Value(resource_name_6)
    RESOURCE_NAME_6_FR = @Value(resource_name_6_fr)
    RESOURCE_NAME_7 = @Value(resource_name_7)
    RESOURCE_NAME_7_FR = @Value(resource_name_7_fr)
    RESOURCE_NAME_8 = @Value(resource_name_8)
    RESOURCE_NAME_8_FR = @Value(resource_name_8_fr)
    RESOURCE_NAME_9 = @Value(resource_name_9)
    RESOURCE_NAME_9_FR = @Value(resource_name_9_fr)
    RESOURCE_URL_0 = @Value(resource_url_0)
    RESOURCE_URL_1 = @Value(resource_url_1)
    RESOURCE_URL_2 = @Value(resource_url_2)
    RESOURCE_URL_3 = @Value(resource_url_3)
    RESOURCE_URL_4 = @Value(resource_url_4)
    RESOURCE_URL_5 = @Value(resource_url_5)
    RESOURCE_URL_6 = @Value(resource_url_6)
    RESOURCE_URL_7 = @Value(resource_url_7)
    RESOURCE_URL_8 = @Value(resource_url_8)
    RESOURCE_URL_9 = @Value(resource_url_9)
    TITLE = @Value(title)
    TITLE_FR = @Value(title_fr)
    -> TOPIC_PARSER
TOPIC_PARSER
    CSW_URL_AWS_SELECT_AB = http://ec2-35-183-211-115.ca-central-1.compute.amazonaws.com:80/csw
    ID = @Value(id)
    -> XML_PUBLISHER
XML_PUBLISHER
    ID = @Value(id)
    METHOD = @Value(method)
    INSERTED -> NOTIFY_UPDATE [INSERTED]
    INSERT_FAILED -> NOTIFY_UPDATE [INSERT_REJECTED]
    UPDATED -> NOTIFY_UPDATE [UPDATED]
    UPDATE_FAILED -> NOTIFY_UPDATE [UPDATE_REJECTED]
Note: Custom transformer e-mails processing results to administrator
NOTIFY_UPDATE
    CSW_ID = @Value(csw_id)
    ID = @Value(id)
    P-T_ABBR = $(P-T_ABBR)
